// =========================================================================
//                          CISCO-IOS NED
// =========================================================================

module ned {
  namespace "http://cisco.com/ns/yang/ned/ios";
  prefix ios;

  import tailf-common {
    prefix tailf;
  }
  import ietf-inet-types {
    prefix inet;
  }
  import ietf-yang-types {
    prefix yang;
  }

  organization "Cisco Systems";
  description
    "NED YANG module for IOS
     Copyright (c) 2016 by Cisco Systems, Inc.
     All rights reserved.";

  // =========================================================================
  // REVISION
  // =========================================================================
  revision 2016-09-19 {
    description
      "Polaris 16.3 release candidate 2";
  }
  revision 2016-07-01 {
    description
      "Polaris 16.3 release candidate 1";
  }

  // =========================================================================
  // TYPEDEF
  // =========================================================================
  
  typedef percentage-type {
    type uint8 {
      range "1..100";
    }
  }

  typedef ipv4-prefix {
    type string {
      pattern "(([0-9]|[1-9][0-9]|1[0-9][0-9]|2[0-4][0-9]|25[0-5])\\.){3}([0-9]|[1-9][0-9]|1[0-9][0-9]|2[0-4][0-9]|25[0-5])/(([0-9])|([1-2][0-9])|(3[0-2]))";
    }
  }

  typedef ipv6-prefix {
    type string {
      pattern "((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(/(([0-9])|([0-9]{2})|(1[0-1][0-9])|(12[0-8])))";
      pattern "(([^:]+:){6}(([^:]+:[^:]+)|(.*\\..*)))|((([^:]+:)*[^:]+)?::(([^:]+:)*[^:]+)?)(/.+)";
    }
  }

  typedef host-type {
    type union {
      type inet:ip-address;
      type inet:domain-name;
    }
  }

  typedef ipv4-host-type {
    type union {
      type inet:ipv4-address;
      type inet:domain-name;
    }
  }

  typedef host-v4v6-type {
    type union {
      type inet:ipv4-address;
      type inet:domain-name;
      type inet:ipv6-address;
    }
  }

  // Router Distinguisher
  typedef rd-type {
    type string {
      pattern "(\\d*(.\\d*)*)?:(\\d*(.\\d*)*)?";
    }
  }

  typedef vpn-id-type {
    type string {
      pattern "[0-9a-fA-F][0-9a-fA-F]?[0-9a-fA-F]?:[0-9a-fA-F][0-9a-fA-F]?[0-9a-fA-F]?[0-9a-fA-F]?";
    }
  }

  typedef asn-ip-type {
    type string {
      pattern "(([0-9]+)|((([0-9]|[1-9][0-9]|1[0-9][0-9]|2[0-4][0-9]|25[0-5])\\.){3}([0-9]|[1-9][0-9]|1[0-9][0-9]|2[0-4][0-9]|25[0-5]))):[0-9]+";
    }
  }

  // Hour&minute type
  typedef hhmm-type {
    type string {
      pattern "([0-1]?[0-9]|2[0-4]):([0-5][0-9])(:[0-5][0-9])?";
    }
  }  
  // Hour&minute&seconds type
  typedef hhmmss-type {
    type string {
      pattern "([0-1]?[0-9]|2[0-4]):([0-5][0-9])(:[0-5][0-9]):([0-5][0-9])(:[0-5][0-9])";
    }
  }
  typedef weekday-type {
    type enumeration {
      enum "Mon";
      enum "Tue";
      enum "Wed";
      enum "Thu";
      enum "Fri";
      enum "Sat";
      enum "Sun";
    }
  }

  typedef month-type {
    type enumeration {
      enum "Jan";
      enum "Feb";
      enum "Mar";
      enum "Apr";
      enum "May";
      enum "Jun";
      enum "Jul";
      enum "Aug";
      enum "Sep";
      enum "Oct";
      enum "Nov";
      enum "Dec";
    }
  }

  typedef std-acl-type {
    type union {
      type uint16 {
        range "1..99";
      }
      type uint16 {
        range "1300..1999";
      }
      type string {
        pattern "[a-zA-Z].*";
      }
    }
  }

  // Extended access list type
  typedef ext-acl-type {
    type union {
      type uint16 {
        range "100..199";
      }
      type uint16 {
        range "2000..2699";
      }
      type string {
        pattern "[a-zA-Z].*";
      }
    }
  }

  // Expanded access list type
  typedef exp-acl-type {
    type union {
      type uint16 {
        range "1..199";
      }
      type uint16 {
        range "1300..2699";
      }
      type string {
        pattern "[a-zA-Z].*";
      }
    }
  }

  typedef mdt-data-list-type {
    type union {
      type uint16 {
        range "100..199";
      }
      type uint16 {
        range "2000..2699";
      }
      type string {
        pattern "[a-fA-F].*";
      }
    }
  }

  typedef ldp-discovery-address-type {
    type union {
      type enumeration {
        enum "interface" {
          tailf:code-name "ldp_interface";
        }
      }
      type inet:ipv4-address;
    }
  }

  typedef mst-cost-type {
    type union {
      type uint32 {
        range "1..200000000";
      }
      type enumeration {
        enum "auto" {
          tailf:code-name "mst_cost_type_auto";
        }
      }
    }
  }

  typedef spanning-tree-cost-type {
    type union {
      type uint32 {
        range "1..200000000";
      }
      type enumeration {
        enum "auto" {
          tailf:code-name "spanning-tree-cost-type-auto";
        }
      }
    }
  }

  typedef dscp-type {
    type union {
      type uint8 {
        range "0..63";
      }
      type enumeration {
        enum "af11" {
          value 10;
        }
        enum "af12" {
          value 12;
        }
        enum "af13" {
          value 14;
        }
        enum "af21" {
          value 18;
        }
        enum "af22" {
          value 20;
        }
        enum "af23" {
          value 22;
        }
        enum "af31" {
          value 26;
        }
        enum "af32" {
          value 28;
        }
        enum "af33" {
          value 30;
        }
        enum "af41" {
          value 34;
        }
        enum "af42" {
          value 36;
        }
        enum "af43" {
          value 38;
        }
        enum "cs1" {
          tailf:code-name "dscp_cs1";
          value 8;
        }
        enum "cs2" {
          tailf:code-name "dscp_cs2";
          value 16;
        }
        enum "cs3" {
          tailf:code-name "dscp_cs3";
          value 24;
        }
        enum "cs4" {
          tailf:code-name "dscp_cs4";
          value 32;
        }
        enum "cs5" {
          tailf:code-name "dscp_cs5";
          value 40;
        }
        enum "cs6" {
          tailf:code-name "dscp_cs6";
          value 48;
        }
        enum "cs7" {
          tailf:code-name "dscp_cs7";
          value 56;
        }
        enum "default" {
          tailf:code-name "dscp_default";
          value 0;
        }
        enum "dscp";
        enum "ef" {
          tailf:code-name "dscp_ef";
          value 46;
        }
        enum "precedence";
      }
    }
  }

  typedef precedence-type {
    type union {
      type uint8 {
        range "0..7";
      }
      type enumeration {
        enum "critical";
        enum "flash";
        enum "flash-override";
        enum "immediate";
        enum "internet" {
          tailf:code-name "prec_internet";
        }
        enum "network";
        enum "priority" {
          tailf:code-name "prec_priority";
        }
        enum "routine";
      }
    }
  }

  typedef precedence-type2 {
    type union {
      type uint8 {
        range "0..7";
      }
      type enumeration {
        enum "rsvp" {
          tailf:code-name "prec_rsvp";
        }
      }
    }
  }

  typedef cos_value-type {
    type union {
      type uint8 {
        range "0..7";
      }
      type enumeration {
        enum "cos";
        enum "dscp";
        enum "exp";
        enum "precedence";
      }
    }
  }

  typedef qos_value-type {
    type union {
      type uint8 {
        range "0..99";
      }
      type enumeration {
        enum "cos";
        enum "dscp";
        enum "exp";
        enum "precedence";
      }
    }
  }

  typedef exp_value-type {
    type union {
      type uint8 {
        range "0..7";
      }
      type enumeration {
        enum "cos";
        enum "dscp";
        enum "exp";
        enum "precedence";
      }
    }
  }

  typedef prec_value-type {
    type union {
      type uint8 {
        range "0..7";
      }
      type enumeration {
        enum "cos";
        enum "dscp";
        enum "exp";
        enum "precedence";
      }
    }
  }

  typedef policy-action-type {
    type enumeration {
      enum "bandwidth" {
        tailf:code-name "policy_bandwidth";
      }
      enum "compression";
      enum "drop";
      enum "estimate";
      enum "fair-queue";
      enum "forward";
      enum "netflow-sampler";
      enum "police";
      enum "priority" {
        tailf:code-name "policy_priority";
      }
      enum "queue-limit";
      enum "random-detect";
      enum "service-policy";
      enum "set";
      enum "shape" {
        tailf:code-name "policy_shape";
      }
      enum "trust";
      enum "dbl";
      enum "queue-buffers";
    }
  }

  typedef access-list-standard-id-type {
    type union {
      type default-access-list-standard-id-type;
      type string;
    }
  }

  typedef default-access-list-standard-id-type {
    type union {
      type uint8 {
        range "1..99";
      }
      type uint16 {
        range "1300..1999";
      }
    }
  }

  typedef access-list-in-out-type {
    type enumeration {
      enum "in";
      enum "out";
    }
  }

  typedef redist-ospf-external-type {
    type enumeration {
      enum "1";
      enum "2";
    }
  }

  typedef class-name-type {
    type union {
      type string;
      // Note: leafref can't be used here due to part of union.
      //path "/ios:native/class-map/name";
      type enumeration {
        enum "class-default";
      }
    }
  }

  typedef access-list-type {
    type union {
      type uint16 {
        range "1..199";
      }
      type uint16 {
        range "1300..2699";
      }
    }
  }

  typedef bgp-distribute-list-type {
    type union {
      type uint16 {
        range "100..199";
      }
      type uint16 {
        range "2000..2699";
      }
      type string {
        pattern "[a-zA-Z].*";
      }
    }
  }

  typedef bgp-distribute-list-type2 {
    type union {
      type uint16 {
        range "1..199";
      }
      type uint16 {
        range "1300..2699";
      }
      type string {
        pattern "[a-zA-Z].*";
      }
    }
  }

  typedef ospf-area-type {
    type union {
      type uint32 {
        range "0 .. 4294967295";
      }
      type inet:ipv4-address;
    }
  }

  typedef ospf-metric-type {
    type uint32 {
      range "1 .. 2";
    }
  }

  typedef limit-dc-non-dc-type {
    type union {
      type uint32 {
        range "1 .. 255";
      }
      type enumeration {
        enum "disable";
      }
    }
  }

  typedef default-access-list-id-type {
    type union {
      type uint32 {
        range "1 .. 199";
      }
      type uint32 {
        range "1300 .. 2699";
      }
    }
  }

  typedef access-list-id-type {
    type union {
      type default-access-list-id-type;
      type string {
        pattern "[a-zA-Z].*";
      }
    }
  }

  typedef default-offset-list-id-type {
    type union {
      type uint32 {
        range "0 .. 99";
      }
      type uint32 {
        range "1300 .. 1999";
      }
    }
  }

  typedef offset-list-id-type {
    type union {
      type default-offset-list-id-type;
      type string {
        pattern "[a-zA-Z].*";
      }
    }
  }

  typedef offset-list-in-out-type {
    type enumeration {
      enum "in";
      enum "out";
    }
  }

  typedef isis-net {
    type string;
    //pattern "(([0-9a-fA-F]{2}\.[0-9a-fA-F]{4})|[0-9a-fA-F]{4})"
    //+"\.([0-9a-fA-F]{4}\.){2,10}00";
  }

  typedef isis-level-type {
    type enumeration {
      enum "level-1";
      enum "level-1-2";
      enum "level-2";
    }
  }

  typedef isis-routes-level-type {
    type enumeration {
      enum "level-1";
      enum "level-1-2";
      enum "level-2";
    }
  }

  typedef authentication-level-type {
    type enumeration {
      enum "level-1";
      enum "level-2";
    }
  }

  typedef logging-level-type {
    type union {
      type uint16 {
        range "0..7";
      }
      type enumeration {
        enum "alerts";
        enum "critical";
        enum "debugging";
        enum "emergencies";
        enum "errors";
        enum "informational";
        enum "notifications";
        enum "warnings";
        enum "bogus";
      }
    }
  }

  typedef syslog-level-type {
    type enumeration {
      enum "alert";
      enum "crit";
      enum "debug";
      enum "emerg";
      enum "err";
      enum "info";
      enum "notice";
      enum "warning";
    }
  }

  typedef operator-type {
    type enumeration {
      enum "eq";
      enum "ge";
      enum "gt";
      enum "le";
      enum "lt";
      enum "ne";
    }
  }

  typedef police-packets-bytes-type {
    type enumeration {
      enum "packets";
      enum "bytes";
    }
  }

  typedef police-pps-bps-type {
    type enumeration {
      enum "pps";
      enum "bps";
    }
  }

  typedef police-bps-type {
    type uint64 {
      range "8000..64000000000";
    }
  }

  typedef police-burst-type {
    type uint32 {
      range "1000..512000000";
    }
  }

  typedef mobility-type {
    type union {
      type uint8;
      type enumeration {
        enum "bind-acknowledgement";
        enum "bind-error";
        enum "bind-refresh";
        enum "bind-update";
        enum "cot";
        enum "coti";
        enum "hot";
        enum "hoti";
      }
    }
  }

  typedef bgp_ipv4_af_type {
    type enumeration {
      enum "unicast" {
        tailf:code-name "bgp_af_ipv4_unicast";
      }
      enum "multicast" {
        tailf:code-name "bgp_af_ipv4_multicast";
      }
      enum "mdt";
      enum "tunnel";
      enum "labeled-unicast";
      enum "flowspec";
      enum "mvpn";
    }
  }

  typedef bgp_ipv6_af_type {
    type enumeration {
      enum "unicast" {
        tailf:code-name "bgp_af_ipv6_unicast";
      }
      enum "multicast" {
        tailf:code-name "bgp_af_ipv6_multicast";
      }
      enum "mdt";
      enum "flowspec";
      enum "mvpn";
    }
  }

  typedef community-number-type {
    type union {
      type uint32 {
        range "1..4294967295";
      }
      type string {
        pattern "(\\d+:\\d+)";
      }
    }
  }

  typedef community-well-known-type {
    type enumeration {
      enum "gshut";
      enum "internet" {
        tailf:code-name "op_internet";
      }
      enum "local-AS";
      enum "no-advertise";
      enum "no-export";
    }
  }

  typedef acl-udp-port-type {
    type union {
      type uint16;
      type enumeration {
        enum "biff";
        enum "bootpc";
        enum "bootps";
        enum "discard";
        enum "dnsix";
        enum "domain";
        enum "echo";
        enum "isakmp";
        enum "mobile-ip";
        enum "nameserver";
        enum "netbios-dgm";
        enum "netbios-ns";
        enum "netbios-ss";
        enum "non500-isakmp";
        enum "ntp";
        enum "pim-auto-rp";
        enum "rip";
        enum "ripv6";
        enum "snmp";
        enum "snmptrap";
        enum "sunrpc";
        enum "syslog";
        enum "tacacs";
        enum "talk";
        enum "tftp";
        enum "time";
        enum "who";
        enum "xdmcp";
      }
    }
  }

  typedef acl-tcp-port-type {
    type union {
      type uint16;
      type enumeration {
        enum "bgp";
        enum "chargen";
        enum "cmd";
        enum "connectedapps-plain";
        enum "connectedapps-tls";
        enum "daytime";
        enum "discard";
        enum "domain";
        enum "echo";
        enum "exec";
        enum "finger";
        enum "ftp";
        enum "ftp-data";
        enum "gopher";
        enum "hostname";
        enum "ident";
        enum "irc";
        enum "klogin";
        enum "kshell";
        enum "login";
        enum "lpd";
        enum "msrpc";
        enum "nntp";
        enum "pim-auto-rp";
        enum "pop2";
        enum "pop3";
        enum "smtp";
        enum "sunrpc";
        enum "syslog";
        enum "tacacs";
        enum "talk";
        enum "telnet";
        enum "time";
        enum "uucp";
        enum "whois";
        enum "www";
      }
    }
  }

  typedef acl-port-type {
    type union {
      type uint16;
      type enumeration {
        enum "bgp" {value 179;}
        enum "chargen" {value 19;}
        enum "daytime" {value 13;}
        enum "discard" {value 9;}
        enum "domain" {value 53;}
        enum "echo" {value 7;}
        enum "finger" {value 79;}
        enum "ftp" {value 21;}
        enum "ftp-data" {value 20;}
        enum "gopher" {value 70;}
        enum "hostname" {value 101;}
        enum "ident" {value 113;}
        enum "irc" {value 194;}
        enum "klogin" {value 543;}
        enum "kshell" {value 544;}
        enum "lpd" {value 515;}
        enum "msrpc" {value 135;}
        enum "nntp" {value 119;}
        enum "pim-auto-rp" {value 496;}
        enum "pop2" {value 109;}
        enum "pop3" {value 110;}
        enum "smtp" {value 25;}
        enum "sunrpc" {value 111;}
        enum "tacacs" {value 49;}
        enum "talk" {value 517;}
        enum "telnet" {value 23;}
        enum "time" {value 37;}
        enum "uucp" {value 540;}
        enum "whois" {value 43;}
        enum "www" {value 80;}
        enum "biff" {value 512;}
        enum "bootpc" {value 68;}
        enum "bootps" {value 67;}
        enum "dnsix" {value 195;}
        enum "isakmp" {value 500;}
        enum "mobile-ip" {value 434;}
        enum "nameserver" {value 42;}
        enum "netbios-dgm" {value 138;}
        enum "netbios-ns" {value 137;}
        enum "netbios-ss" {value 139;}
        enum "non500-isakmp" {value 4500;}
        enum "ntp" {value 123;}
        enum "rip" {value 520;}
        enum "ripv6" {value 521;}
        enum "snmp" {value 161;}
        enum "snmptrap" {value 162;}
        enum "syslog" {value 514;}
        enum "tftp" {value 69;}
        enum "who" {value 513;}
        enum "xdmcp" {value 177;}
      }
    }
  }

  typedef bgp-as-number-type {
    type union {
      type uint32 {
        range "1..4294967295";
      }
      type string;
    }
  }

  typedef cisco-mac-address-type {
    type string {
      pattern "[0-9a-fA-F]+\\.[0-9a-fA-F]+\\.[0-9a-fA-F]+";
    }
  }
  
  typedef storm-control-threshold-type {
    type string {
      pattern "[0-9]+.?[0-9]*[k|m|g]?";
    }
  }
  // =========================================================================
  // GROUPING
  // =========================================================================
  grouping class-map-match-result-type-grouping {
    leaf aaa-timeout{
      description 
        "aaa timeout type";
      type empty;
    }
    leaf agent-not-found{
      description 
      "agent not found type";
      type empty;
    }
    leaf authoritative{
      description 
      "failure type";
      type empty;
    }
    leaf method-timeout{
      description 
      "method_timeout type";
      type empty;
    }
    leaf none{
      description 
      "no type";
      type empty;
    }
    leaf success{
      description 
      "success type";
      type empty;
    }
  }
  grouping class-map-control-filter-grouping {    
    list activated-service-template {
      description "match name of service template activated on session";
      key "service-name";
      leaf service-name {
        description "Enter service name";
        type string;
      }
    }
    container authorization-status {
      description "match the authorization status of the session";
      leaf authorized {
          description "authorized";
          type empty;
      }
      leaf unauthorized {
          description "unauthorized";
          type empty;
      }
    }
    container authorizing-method-priority {
      description "match the priority against the authorizing method's priority";
      leaf eq {
        description "equal to";
        type uint8{            
          range 1..254;
        }
      }
      leaf gt {
        description "greater than";
        type uint8{            
          range 1..254;
        }
      }
      leaf lt {
        description "less than";
        type uint8{            
          range 1..254;
        }
      }
    }
    container method {
      description "match the type of authentication method from an event";
      leaf dot1x {
          description "dot1x";
          type empty;
      }
      leaf mab {
          description "mab";
          type empty;
      }
      leaf webauth {
          description "webauth";
          type empty;
      }
    }
    container result-type {
      description "match the result type, optionally for a specific method";
      container method {
        description "match the result of a particular method";
        container dot1x {
          description "dot1x result";
          uses class-map-match-result-type-grouping;
        }
        container mab {
          description "mab result";
          uses class-map-match-result-type-grouping;
        }
        container webauth {
          description "webauth result";
          uses class-map-match-result-type-grouping;
        }          
      }
      uses class-map-match-result-type-grouping;
    }
  }
  grouping service-list-match-grouping{
    container match {
      description "Configure parameters for service-list name";
      leaf learnt-interface {
        description "match the interface where service is learnt";
        type empty;
      }
      container location {
        description "match location information";
        presence true;
        leaf civic {
          description "Civic location";
          type string;
        }
      }
      container message-type {
        description "To set the message type";
        presence true;
        leaf announcement {
          description "Match Announcement/Responses";
          type empty;
        }
        leaf query {
          description "Match Query";
          type empty;
        }
        leaf any {
          description "Match Any";
          type empty;
        }
      }
      leaf service-instance {
        description "To set the Service Instance";
        type string;
      }
      leaf service-type {
        description "match mDNS service type string";
        type string;
      }
    }
  }  
  grouping call-home-profile-periodic{
    container periodic {
      choice periodic-choice {
        description
          "Periodic call-home message";
        container daily {
          description
            "Daily call-home message";
          leaf begin-time{
            tailf:cli-drop-node-name;
            description
              "Begin time";
            type hhmm-type;
          }
        }
        container monthly {
          description
            "Monthly call-home message";
          tailf:cli-compact-syntax;
          tailf:cli-sequence-commands;
          leaf date {
            tailf:cli-drop-node-name;
            description
                "Day of month";
            type uint8 {
              range "1..31";
            }
          }
          leaf begin-time {
            tailf:cli-drop-node-name;
            description
              "Begin time";
            type hhmm-type;
          }
        }
        container weekly {
          description
            "Weekly call-home message";
          tailf:cli-compact-syntax;
          tailf:cli-sequence-commands;
          leaf day {
            description
              "Day of the week";
            tailf:cli-drop-node-name;            
            type weekday-type;
          }        
          leaf begin-time{
            tailf:cli-drop-node-name;
            description
              "Begin time";
            type hhmm-type;
          }                        
        }
      }
    }
  }
  grouping cfg-call-home-profile {
    leaf active {
      description
        "Activate the current profile";
      tailf:cli-boolean-no;
      tailf:cli-trim-default;
      type boolean;
    }
    container destination {
      description
        "Message destination related configuration";
      leaf transport-method {
        description
          "To specify transport method for this profile";
        type enumeration {
          enum "http";
          enum "email";
        }
      }
      container address {
        description
          "To add destination address to this profile";
        leaf email {
          description
            "Use email address";          
          type string;
        }
        leaf http {
          description
            "To add http address to this profile";
          type string;
        }
      }
    }
    container subscribe-to-alert-group {
      description
        "Subscribe to alert-group";
      container diagnostic {
        description
          "diagnostic info";        
        presence true;
        leaf severity {
          description
            "Severity";
          type enumeration {            
            enum "catastrophic";
            enum "critical";
            enum "debugging";
            enum "disaster";
            enum "fatal";
            enum "major";
            enum "minor";
            enum "normal";
            enum "notification";
            enum "warning";
          }
        }
      }
      container environment {
        description
          "environmental info";
        presence true;
        leaf severity {
          description
            "Severity";
          type enumeration {            
            enum "catastrophic";
            enum "critical";
            enum "debugging";
            enum "disaster";
            enum "fatal";
            enum "major";
            enum "minor";
            enum "normal";
            enum "notification";
            enum "warning";
          }
        }
      }
      container inventory {
        description
          "inventory info";
        presence true;
        uses call-home-profile-periodic;
      }
      container syslog {
        description
          "syslog info";
        presence true;
        list severity {
          description "severity";
          tailf:cli-compact-syntax;
          tailf:cli-suppress-mode;
          key value;
          leaf value {
            type enumeration {            
              enum "catastrophic";
              enum "critical";
              enum "debugging";
              enum "disaster";
              enum "fatal";
              enum "major";
              enum "minor";
              enum "normal";
              enum "notification";
              enum "warning";
            }
          }
          leaf pattern{
            description
              "Syslog message pattern";
            type string;
          }
        }
      }
      container configuration {
        description
          "configuration info";
        presence true;
        uses call-home-profile-periodic;
      }
    }
  }
  grouping ap-port-grouping {
      leaf poe {
          description 
            "Enable/Disable LAN PoE";
          type empty;
      }
      leaf remote-lan {
          description 
            "Enter Remote-LAN Name";
          type string;
      }
      leaf shutdown {
          description 
            "Enable/Disable port";
          type empty;
      }
  }
  grouping ap-wlan-grouping {
      container airtime-fairness {
          description 
            "Configure airtime-fairness to the current AP group";
          container dot11 {
              description 
                "Configures airtime-fairness parameters for the AP group";
              container _24GHz {
                  tailf:alt-name "24GHz";
                  description 
                    "Configures 2.4 GHz airtime-fairness policy";
                  leaf policy {
                      description 
                        "Specify name of the airtime-fairness policy to assign";
                      type string;
                  }
              }
              container _5GHz {
                  tailf:alt-name "5GHz";
                  description 
                    "Configures 5 GHz airtime-fairness policy";
                  leaf policy {
                      description 
                        "Specify name of the airtime-fairness policy to assign";
                      type string;
                  }
             }
         }
     }
     leaf radio-policy {
       description 
         "Configures Radio Policy on given AP-Group";
       type enumeration{
         enum "all";
         enum "dot11a";
         enum "dot11bg";
         enum "dot11g";
       }
     }
     leaf vlan {
         description 
           "Specify the vlan name or vlan id";
         type string;
     }
  }

  grouping vrf-route-target-grouping {
    list export {
      description
        "Export Target-VPN community";
      tailf:cli-suppress-mode;
      tailf:cli-delete-when-empty;
      key "asn-ip";
      leaf asn-ip {
        type asn-ip-type;
      }
    }
    list import {
      description
        "Import Target-VPN community";
      tailf:cli-suppress-mode;
      tailf:cli-delete-when-empty;
      key "asn-ip";
      leaf asn-ip {
        type asn-ip-type;
      }
    }
  }

  // police {conform|exceed|violate}-action groupings
  grouping police-action-transmit-grouping {
    leaf transmit {
      description
        "transmit packet";
      type empty;
    }
  }

  grouping police-action-drop-grouping {
    leaf drop {
      description
        "drop packet";
      type empty;
    }
  }

  grouping police-conform-action-grouping {
    container conform-set-clp-transmit {
      tailf:cli-no-keyword;
      tailf:cli-drop-node-name;
      tailf:cli-flatten-container;
      container conform-action {
        description
          "action when rate is less than conform burst";
        tailf:cli-flatten-container;
        leaf set-clp-transmit {
          description
            "set atm clp and send it";
          type empty;
        }
      }
    }
    container conform-set-cos-transmit {
      tailf:cli-no-keyword;
      tailf:cli-drop-node-name;
      tailf:cli-flatten-container;
      container conform-action {
        description
          "action when rate is less than conform burst";
        tailf:cli-flatten-container;
        leaf set-cos-transmit {
          description
            "rewrite packet cos and send it";
          type cos_value-type;
        }
      }
    }
    container conform-set-cos-transmit-table {
      tailf:cli-no-keyword;
      tailf:cli-drop-node-name;
      tailf:cli-flatten-container;
      container conform-action {
        description
          "action when rate is less than conform burst";
        tailf:cli-compact-syntax;
        tailf:cli-flatten-container;
        tailf:cli-sequence-commands;
        leaf set-cos-transmit {
          description
            "rewrite packet cos and send it";
          type cos_value-type;
        }
        leaf table {
          description
            "Specify table-map";
          type leafref {
            path "/ios:native/table-map/name";
          }
        }
      }
    }
    container conform-set-discard-class-transmit {
      tailf:cli-no-keyword;
      tailf:cli-drop-node-name;
      tailf:cli-flatten-container;
      container conform-action {
        description
          "action when rate is less than conform burst";
        tailf:cli-flatten-container;
        leaf set-discard-class-transmit {
          description
            "set discard-class and send it";
          type uint8 {
            range "0..7";
          }
        }
      }
    }
    container conform-set-dscp-transmit {
      tailf:cli-no-keyword;
      tailf:cli-drop-node-name;
      tailf:cli-flatten-container;
      container conform-action {
        description
          "action when rate is less than conform burst";
        tailf:cli-flatten-container;
        leaf set-dscp-transmit {
          description
            "set dscp and send it";
          type dscp-type;
        }
      }
    }
    container conform-set-dscp-transmit-table {
      tailf:cli-no-keyword;
      tailf:cli-drop-node-name;
      tailf:cli-flatten-container;
      container conform-action {
        description
          "action when rate is less than conform burst";
        tailf:cli-compact-syntax;
        tailf:cli-flatten-container;
        tailf:cli-sequence-commands;
        leaf set-dscp-transmit {
          description
            "set dscp and send it";
          type dscp-type;
        }
        leaf table {
          description
            "Specify table-map";
          type leafref {
            path "/ios:native/table-map/name";
          }
        }
      }
    }
    container conform-set-frde-transmit {
      tailf:cli-no-keyword;
      tailf:cli-drop-node-name;
      tailf:cli-flatten-container;
      container conform-action {
        description
          "action when rate is less than conform burst";
        tailf:cli-flatten-container;
        leaf set-frde-transmit {
          description
            "set FR DE and send it";
          type empty;
        }
      }
    }
    container conform-set-mpls-exp-imposition-transmit {
      tailf:cli-no-keyword;
      tailf:cli-drop-node-name;
      tailf:cli-flatten-container;
      container conform-action {
        description
          "action when rate is less than conform burst";
        tailf:cli-flatten-container;
        leaf set-mpls-exp-imposition-transmit {
          description
            "set exp at tag imposition and send it";
          type exp_value-type;
        }
      }
    }
    container conform-set-mpls-exp-imposition-transmit-table {
      tailf:cli-no-keyword;
      tailf:cli-drop-node-name;
      tailf:cli-flatten-container;
      container conform-action {
        description
          "action when rate is less than conform burst";
        tailf:cli-compact-syntax;
        tailf:cli-flatten-container;
        tailf:cli-sequence-commands;
        leaf set-mpls-exp-imposition-transmit {
          description
            "set exp at tag imposition and send it";
          type exp_value-type;
        }
        leaf table {
          description
            "Specify table-map";
          type leafref {
            path "/ios:native/table-map/name";
          }
        }
      }
    }
    container conform-set-mpls-exp-topmost-transmit {
      tailf:cli-no-keyword;
      tailf:cli-drop-node-name;
      tailf:cli-flatten-container;
      container conform-action {
        description
          "action when rate is less than conform burst";
        tailf:cli-flatten-container;
        leaf set-mpls-exp-topmost-transmit {
          description
            "set exp on topmost label and send it";
          type exp_value-type;
        }
      }
    }
    container conform-set-mpls-exp-topmost-transmit-table {
      tailf:cli-no-keyword;
      tailf:cli-drop-node-name;
      tailf:cli-flatten-container;
      container conform-action {
        description
          "action when rate is less than conform burst";
        tailf:cli-compact-syntax;
        tailf:cli-flatten-container;
        tailf:cli-sequence-commands;
        leaf set-mpls-exp-topmost-transmit {
          description
            "set exp on topmost label and send it";
          type exp_value-type;
        }
        leaf table {
          description
            "Specify table-map";
          type leafref {
            path "/ios:native/table-map/name";
          }
        }
      }
    }
    container conform-set-prec-transmit {
      tailf:cli-no-keyword;
      tailf:cli-drop-node-name;
      tailf:cli-flatten-container;
      container conform-action {
        description
          "action when rate is less than conform burst";
        tailf:cli-flatten-container;
        leaf set-prec-transmit {
          description
            "rewrite packet precedence and send it";
          type prec_value-type;
        }
      }
    }
    container conform-set-prec-transmit-table {
      tailf:cli-no-keyword;
      tailf:cli-drop-node-name;
      tailf:cli-flatten-container;
      container conform-action {
        description
          "action when rate is less than conform burst";
        tailf:cli-compact-syntax;
        tailf:cli-flatten-container;
        tailf:cli-sequence-commands;
        leaf set-prec-transmit {
          description
            "rewrite packet precedence and send it";
          type prec_value-type;
        }
        leaf table {
          description
            "Specify table-map";
          type leafref {
            path "/ios:native/table-map/name";
          }
        }
      }
    }
    container conform-set-qos-transmit {
      tailf:cli-no-keyword;
      tailf:cli-drop-node-name;
      tailf:cli-flatten-container;
      container conform-action {
        description
          "action when rate is less than conform burst";
        tailf:cli-flatten-container;
        leaf set-qos-transmit {
          description
            "set qos-group and send it";
          type qos_value-type;
        }
      }
    }
    container conform-set-qos-transmit-table {
      tailf:cli-no-keyword;
      tailf:cli-drop-node-name;
      tailf:cli-flatten-container;
      container conform-action {
        description
          "action when rate is less than conform burst";
        tailf:cli-compact-syntax;
        tailf:cli-flatten-container;
        tailf:cli-sequence-commands;
        leaf set-qos-transmit {
          description
            "set qos-group and send it";
          type qos_value-type;
        }
        leaf table {
          description
            "Specify table-map";
          type leafref {
            path "/ios:native/table-map/name";
          }
        }
      }
    }
    container conform-transmit {
      tailf:cli-no-keyword;
      tailf:cli-drop-node-name;
      tailf:cli-flatten-container;
      container conform-action {
        description
          "action when rate is less than conform burst";
        tailf:cli-flatten-container;
        uses police-action-transmit-grouping;
      }
    }
    container conform-drop {
      tailf:cli-no-keyword;
      tailf:cli-drop-node-name;
      tailf:cli-flatten-container;
      container conform-action {
        description
          "action when rate is less than conform burst";
        tailf:cli-flatten-container;
        uses police-action-drop-grouping;
      }
    }
  }

  grouping police-exceed-action-grouping {
    container exceed-dscp {
      tailf:cli-no-keyword;
      tailf:cli-drop-node-name;
      tailf:cli-flatten-container;
      container exceed-action {
        description
          "action when rate is within conform and conform + exceed burst";
        tailf:cli-flatten-container;
        leaf dscp {
          type dscp-type;
        }
      }
    }
    container exceed-set-clp-transmit {
      tailf:cli-no-keyword;
      tailf:cli-drop-node-name;
      tailf:cli-flatten-container;
      container exceed-action {
        description
          "action when rate is within conform and conform + exceed burst";
        tailf:cli-flatten-container;
        leaf set-clp-transmit {
          description
            "set atm clp and send it";
          type empty;
        }
      }
    }
    container exceed-set-cos-transmit {
      tailf:cli-no-keyword;
      tailf:cli-drop-node-name;
      tailf:cli-flatten-container;
      container exceed-action {
        description
          "action when rate is within conform and conform + exceed burst";
        tailf:cli-compact-syntax;
        tailf:cli-flatten-container;
        tailf:cli-sequence-commands;
        leaf set-cos-transmit {
          description
            "rewrite packet cos and send it";
          type cos_value-type;
        }
        leaf table {
          description
            "Specify table-map";
          tailf:cli-optional-in-sequence;
          type leafref {
            path "/ios:native/table-map/name";
          }
        }
      }
    }
    container exceed-set-discard-class-transmit {
      tailf:cli-no-keyword;
      tailf:cli-drop-node-name;
      tailf:cli-flatten-container;
      container exceed-action {
        description
          "action when rate is within conform and conform + exceed burst";
        tailf:cli-flatten-container;
        leaf set-discard-class-transmit {
          description
            "set discard-class and send it";
          type uint8 {
            range "0..7";
          }
        }
      }
    }
    container exceed-set-dscp-transmit {
      tailf:cli-no-keyword;
      tailf:cli-drop-node-name;
      tailf:cli-flatten-container;
      container exceed-action {
        description
          "action when rate is within conform and conform + exceed burst";
        tailf:cli-flatten-container;
        container set-dscp-transmit {
          tailf:cli-flatten-container;
          container dscp {
            tailf:cli-flatten-container;
            leaf table {
              type enumeration {
                enum "policed-dscp";
              }
            }
          }
        }
      }
    }
    container exceed-set-dscp-transmit-table {
      tailf:cli-no-keyword;
      tailf:cli-drop-node-name;
      tailf:cli-flatten-container;
      container exceed-action {
        description
          "action when rate is within conform and conform + exceed burst";
        tailf:cli-compact-syntax;
        tailf:cli-flatten-container;
        tailf:cli-sequence-commands;
        leaf set-dscp-transmit {
          description
            "set dscp and send it";
          type dscp-type;
        }
        leaf table {
          description
            "Specify table-map";
          tailf:cli-optional-in-sequence;
          type leafref {
            path "/ios:native/table-map/name";
          }
        }
      }
    }
    container exceed-set-frde-transmit {
      tailf:cli-no-keyword;
      tailf:cli-drop-node-name;
      tailf:cli-flatten-container;
      container exceed-action {
        description
          "action when rate is within conform and conform + exceed burst";
        tailf:cli-flatten-container;
        leaf set-frde-transmit {
          description
            "set FR DE and send it";
          type empty;
        }
      }
    }
    container exceed-set-mpls-exp-imposition-transmit {
      tailf:cli-no-keyword;
      tailf:cli-drop-node-name;
      tailf:cli-flatten-container;
      container exceed-action {
        description
          "action when rate is within conform and conform + exceed burst";
        tailf:cli-flatten-container;
        leaf set-mpls-exp-imposition-transmit {
          description
            "set exp at tag imposition and send it";
          type exp_value-type;
        }
      }
    }
    container exceed-set-mpls-exp-topmost-transmit {
      tailf:cli-no-keyword;
      tailf:cli-drop-node-name;
      tailf:cli-flatten-container;
      container exceed-action {
        description
          "action when rate is within conform and conform + exceed burst";
        tailf:cli-flatten-container;
        leaf set-mpls-exp-topmost-transmit {
          description
            "set exp on topmost label and send it";
          type exp_value-type;
        }
      }
    }
    container exceed-set-prec-transmit {
      tailf:cli-no-keyword;
      tailf:cli-drop-node-name;
      tailf:cli-flatten-container;
      container exceed-action {
        description
          "action when rate is within conform and conform + exceed burst";
        tailf:cli-flatten-container;
        tailf:cli-compact-syntax;
        tailf:cli-sequence-commands;
        leaf set-prec-transmit {
          description
            "rewrite packet precedence and send it";
          type prec_value-type;
        }
        leaf table {
          description
            "Specify table-map";
          tailf:cli-optional-in-sequence;
          type leafref {
            path "/ios:native/table-map/name";
          }
        }
      }
    }
    container exceed-set-qos-transmit {
      tailf:cli-no-keyword;
      tailf:cli-drop-node-name;
      tailf:cli-flatten-container;
      container exceed-action {
        description
          "action when rate is within conform and conform + exceed burst";
        tailf:cli-flatten-container;
        leaf set-qos-transmit {
          description
            "set qos-group and send it";
          type qos_value-type;
        }
      }
    }
    container exceed-transmit {
      tailf:cli-no-keyword;
      tailf:cli-drop-node-name;
      tailf:cli-flatten-container;
      container exceed-action {
        description
          "action when rate is within conform and conform + exceed burst";
        tailf:cli-flatten-container;
        uses police-action-transmit-grouping;
      }
    }
    container exceed-drop {
      tailf:cli-no-keyword;
      tailf:cli-drop-node-name;
      tailf:cli-flatten-container;
      container exceed-action {
        description
          "action when rate is within conform and conform + exceed burst";
        tailf:cli-flatten-container;
        uses police-action-drop-grouping;
      }
    }
  }

  grouping police-violate-action-grouping {
    container violate-set-clp-transmit {
      tailf:cli-no-keyword;
      tailf:cli-drop-node-name;
      tailf:cli-flatten-container;
      container violate-action {
        description
          "action when rate is greater than conform + exceed burst";
        tailf:cli-flatten-container;
        leaf set-clp-transmit {
          description
            "set atm clp and send it";
          type empty;
        }
      }
    }
    container violate-set-cos-transmit {
      tailf:cli-no-keyword;
      tailf:cli-drop-node-name;
      tailf:cli-flatten-container;
      container violate-action {
        description
          "action when rate is greater than conform + exceed burst";
        tailf:cli-compact-syntax;
        tailf:cli-flatten-container;
        tailf:cli-sequence-commands;
        leaf set-cos-transmit {
          description
            "rewrite packet cos and send it";
          type cos_value-type;
        }
        leaf table {
          description
            "Specify table-map";
          tailf:cli-optional-in-sequence;
          type leafref {
            path "/ios:native/table-map/name";
          }
        }
      }
    }
    container violate-set-discard-class-transmit {
      tailf:cli-no-keyword;
      tailf:cli-drop-node-name;
      tailf:cli-flatten-container;
      container violate-action {
        description
          "action when rate is greater than conform + exceed burst";
        tailf:cli-flatten-container;
        leaf set-discard-class-transmit {
          description
            "set discard-class and send it";
          type uint8 {
            range "0..7";
          }
        }
      }
    }
    container violate-set-dscp-transmit {
      tailf:cli-no-keyword;
      tailf:cli-drop-node-name;
      tailf:cli-flatten-container;
      container violate-action {
        description
          "action when rate is greater than conform + exceed burst";
        tailf:cli-flatten-container;
        tailf:cli-compact-syntax;
        tailf:cli-sequence-commands;
        leaf set-dscp-transmit {
          description
            "set dscp and send it";
          type dscp-type;
        }
        leaf table {
          description
            "Specify table-map";
          tailf:cli-optional-in-sequence;
          type leafref {
            path "/ios:native/table-map/name";
          }
        }
      }
    }
    container violate-set-frde-transmit {
      tailf:cli-no-keyword;
      tailf:cli-drop-node-name;
      tailf:cli-flatten-container;
      container violate-action {
        description
          "action when rate is greater than conform + exceed burst";
        tailf:cli-flatten-container;
        leaf set-frde-transmit {
          description
            "set FR DE and send it";
          type empty;
        }
      }
    }
    container violate-set-mpls-exp-imposition-transmit {
      tailf:cli-no-keyword;
      tailf:cli-drop-node-name;
      tailf:cli-flatten-container;
      container violate-action {
        description
          "action when rate is greater than conform + exceed burst";
        tailf:cli-flatten-container;
        leaf set-mpls-exp-imposition-transmit {
          description
            "set exp at tag imposition and send it";
          type exp_value-type;
        }
      }
    }
    container violate-set-mpls-exp-topmost-transmit {
      tailf:cli-no-keyword;
      tailf:cli-drop-node-name;
      tailf:cli-flatten-container;
      container violate-action {
        description
          "action when rate is greater than conform + exceed burst";
        tailf:cli-flatten-container;
        leaf set-mpls-exp-topmost-transmit {
          description
            "set exp on topmost label and send it";
          type exp_value-type;
        }
      }
    }
    container violate-set-prec-transmit {
      tailf:cli-no-keyword;
      tailf:cli-drop-node-name;
      tailf:cli-flatten-container;
      container violate-action {
        description
          "action when rate is greater than conform + exceed burst";
        tailf:cli-flatten-container;
        tailf:cli-compact-syntax;
        tailf:cli-sequence-commands;
        leaf set-prec-transmit {
          description
            "rewrite packet precedence and send it";
          type prec_value-type;
        }
        leaf table {
          description
            "Specify table-map";
          tailf:cli-optional-in-sequence;
          type leafref {
            path "/ios:native/table-map/name";
          }
        }
      }
    }
    container violate-set-qos-transmit {
      tailf:cli-no-keyword;
      tailf:cli-drop-node-name;
      tailf:cli-flatten-container;
      container violate-action {
        description
          "action when rate is greater than conform + exceed burst";
        tailf:cli-flatten-container;
        leaf set-qos-transmit {
          description
            "set qos-group and send it";
          type qos_value-type;
        }
      }
    }
    container violate-transmit {
      tailf:cli-no-keyword;
      tailf:cli-drop-node-name;
      tailf:cli-flatten-container;
      container violate-action {
        description
          "action when rate is greater than conform + exceed burst";
        tailf:cli-flatten-container;
        uses police-action-transmit-grouping;
      }
    }
    container violate-drop {
      tailf:cli-no-keyword;
      tailf:cli-drop-node-name;
      tailf:cli-flatten-container;
      container violate-action {
        description
          "action when rate is greater than conform + exceed burst";
        tailf:cli-flatten-container;
        uses police-action-drop-grouping;
      }
    }
  }

  grouping police-action-grouping {
    container actions {
      tailf:cli-break-sequence-commands;
      tailf:cli-no-keyword;
      tailf:cli-drop-node-name;
      tailf:cli-flatten-container;
      // policy-map * / class * / police ? / conform-action
      uses police-conform-action-grouping;
      // policy-map * / class * / police ? / exceed-action
      uses police-exceed-action-grouping;
      // policy-map * / class * / police ? / violate-action
      uses police-violate-action-grouping;
    }
  }

  grouping password-grouping {
    container password-container {
      tailf:cli-compact-syntax;
      tailf:cli-flatten-container;
      tailf:cli-sequence-commands;
      tailf:cli-drop-node-name;
      leaf encryption {
        tailf:cli-drop-node-name;
        tailf:cli-incomplete-command;
        tailf:cli-optional-in-sequence;
        type uint8 {
          range "0..7";
        }
      }
      leaf password {
        tailf:cli-drop-node-name;
        tailf:cli-trim-default;
        type string {
          pattern "([1-680-9a-zA-Z].*)|(0.+)|(7.+)";
          //length "1..80";
        }
      }
    }
  }

  grouping distribute-list-grouping {
    container distribute-list {
      description
        "Filter networks in routing updates";
      list accesslist {
        tailf:cli-drop-node-name;
        tailf:cli-compact-syntax;
        tailf:cli-suppress-mode;
        tailf:cli-delete-when-empty;
        tailf:cli-suppress-list-no;
        key "in-out";
        leaf in-out {
          type access-list-in-out-type;
        }
      }
      list accesslist-ifname {
        tailf:cli-drop-node-name;
        tailf:cli-compact-syntax;
        tailf:cli-suppress-mode;
        tailf:cli-delete-when-empty;
        tailf:cli-suppress-list-no;
        tailf:cli-diff-dependency "/ios:native/interface";
        key "in-out interface";
        leaf in-out {
          type access-list-in-out-type;
        }
        leaf interface {
          // Note: interface name must be type string since part of key
          type string;
        }
        leaf interface-routing-id {
          tailf:cli-drop-node-name;
          type uint8;
        }
        leaf isis-tag {
          tailf:cli-drop-node-name;
          type string;
        }
        leaf vrf {
          description
            "VPN Routing/Forwarding Instance";
          type string;
        }
      }
      list accesslist-prefix-gateway {
        tailf:cli-drop-node-name;
        tailf:cli-compact-syntax;
        tailf:cli-suppress-mode;
        tailf:cli-delete-when-empty;
        tailf:cli-suppress-list-no;
        tailf:cli-sequence-commands;
        key "in-out";
        leaf in-out {
          type access-list-in-out-type;
        }
        leaf prefix-gateway {
          tailf:cli-drop-node-name;
          tailf:cli-incomplete-command;
          mandatory true;
          tailf:cli-prefix-key;
          type enumeration {
            enum "prefix";
            enum "gateway";
            enum "route-map";
          }
        }
        leaf name {
          tailf:cli-drop-node-name;
          mandatory true;
          tailf:cli-prefix-key;
          tailf:cli-disallow-value "in|out";
          type string;
        }
      }
      list accesslist-prefix-gateway-ifname {
        tailf:cli-drop-node-name;
        tailf:cli-compact-syntax;
        tailf:cli-suppress-mode;
        tailf:cli-delete-when-empty;
        tailf:cli-suppress-list-no;
        key "in-out interface";
        leaf in-out {
          type access-list-in-out-type;
        }
        leaf interface {
          type string;
        }
        leaf prefix-gateway {
          tailf:cli-drop-node-name;
          tailf:cli-incomplete-command;
          mandatory true;
          tailf:cli-prefix-key;
          type enumeration {
            enum "prefix";
            enum "gateway";
            enum "route-map";
          }
        }
        leaf name {
          tailf:cli-drop-node-name;
          mandatory true;
          tailf:cli-prefix-key;
          tailf:cli-disallow-value "in|out";
          type string;
        }
        leaf interface-routing-id {
          tailf:cli-drop-node-name;
          type uint8;
        }
        leaf isis-tag {
          tailf:cli-drop-node-name;
          type string;
        }
        leaf vrf {
          description
            "VPN Routing/Forwarding Instance";
          type string;
        }
      }
    }
  }

  grouping ipv6-router-distribute-list-grouping {
    container distribute-list {
      description
        "Filter networks in routing updates";
      list prefix-list {
        description
          "Filter connections based on an IPv6 prefix-list";
        tailf:cli-suppress-mode;
        key "name";
        leaf name {
          type string;
        }
        leaf in {
          description
            "Filter incoming routing updates";
          type string;
        }
        leaf out {
          description
            "Filter outgoing routing updates";
          type string;
        }
      }
    }
  }

  grouping passive-interface-grouping {
    container passive-interface {
      description
        "Suppress routing updates on an interface";
      choice passive-interface-choice {
        leaf default {
          description
            "Suppress routing updates on all interfaces";
          type empty;
        }
        leaf interface {
          tailf:cli-drop-node-name;
          tailf:cli-multi-value;
          type string;
        }
      }
    }
    container disable {
      when "../passive-interface/default";
      list passive-interface {
        tailf:cli-suppress-mode;
        tailf:cli-delete-when-empty;
        tailf:cli-compact-syntax;
        key "interface";
        leaf interface {
          tailf:cli-drop-node-name;
          tailf:cli-multi-word-key;
          type string;
        }
      }
    }
  }

  grouping interface-grouping {
    choice interface-choice {
      leaf AppNav-Compress {
        description
          "Service-Context Virtual Interface Compress";
        tailf:cli-allow-join-with-value {
          tailf:cli-display-joined;
        }
        type uint16;
        tailf:non-strict-leafref {
          path "/ios:native/interface/AppNav-Compress/name";
        }
      }
      leaf AppNav-UnCompress {
        description
          "Service-Context Virtual Interface UnCompress";
        tailf:cli-allow-join-with-value {
          tailf:cli-display-joined;
        }
        type uint16;
        tailf:non-strict-leafref {
          path "/ios:native/interface/AppNav-UnCompress/name";
        }
      }
      //  Async               Async interface
      //  Auto-Template       Auto-Template interface
      //  CTunnel             CTunnel interface
      //  Dialer              Dialer interface
      //  EsconPhy            ESCON interface
      
      leaf ATM {
        description
          "ATM interface";
        tailf:cli-allow-join-with-value {
          tailf:cli-display-joined;
        }
        type string {
          pattern "([0-9]/){2}([0-9]|(ima[0-9]))(:[0-9])?";
        }
        tailf:non-strict-leafref {
          path "/ios:native/interface/ATM/name";
        }
      }
      container ATM-subinterface {
        tailf:cli-no-keyword;
        tailf:cli-drop-node-name;
        tailf:cli-flatten-container;
        tailf:cli-compact-syntax;
        leaf ATM {
          tailf:cli-allow-join-with-value {
            tailf:cli-display-joined;
          }
          type string {
            pattern "([0-9]/){2}[0-9]\\.([0-9]/){3}[0-9]";
          }
          tailf:non-strict-leafref {
            path "/ios:native/interface/ATM-subinterface/ATM/name";
          }
        }
      }
      leaf ATM-ACR {
        description
          "ATM-ACR interface";
        tailf:cli-allow-join-with-value {
          tailf:cli-display-joined;
        }
        type string {
          pattern "[0-9]";
        }
        tailf:non-strict-leafref {
          path "/ios:native/interface/ATM-ACR/name";
        }
      }
      container ATM-ACRsubinterface {
        tailf:cli-no-keyword;
        tailf:cli-drop-node-name;
        tailf:cli-flatten-container;
        tailf:cli-compact-syntax;
        leaf ATM-ACR {
          tailf:cli-allow-join-with-value {
            tailf:cli-display-joined;
          }
          type string {
            pattern "[0-9]\\.([0-9]/){3}[0-9]";
          }
          tailf:non-strict-leafref {
            path "/ios:native/interface/ATM-ACRsubinterface/ATM-ACR/name";
          }
        }
      }
      leaf BDI {
        description
          "Bridge-Domain interface";
        tailf:cli-allow-join-with-value {
          tailf:cli-display-joined;
        }
        type string;
        tailf:non-strict-leafref {
          path "/ios:native/interface/BDI/name";
        }
      }
      leaf CEM {
        description
          "CEM interface";
        tailf:cli-allow-join-with-value {
          tailf:cli-display-joined;
        }
        type string {
          pattern "([0-9]/){2}[0-9]";
        }
        tailf:non-strict-leafref {
          path "/ios:native/interface/CEM/name";
        }
      }
      leaf CEM-ACR {
        description
          "CEM-ACR interface";
        tailf:cli-allow-join-with-value {
          tailf:cli-display-joined;
        }
        type uint8 {
          range "0..255";
        }
        tailf:non-strict-leafref {
          path "/ios:native/interface/CEM-ACR/name";
        }
      }
      leaf Embedded-Service-Engine {
        description
          "cisco embedded service engine module";
        tailf:cli-allow-join-with-value {
          tailf:cli-display-joined;
        }
        type string;
        tailf:non-strict-leafref {
          path "/ios:native/interface/Embedded-Service-Engine/name";
        }
      }


      leaf FastEthernet {
        description
          "FastEthernet IEEE 802.3";
        tailf:cli-allow-join-with-value {
          tailf:cli-display-joined;
        }
        type string;
        tailf:non-strict-leafref {
          path "/ios:native/interface/FastEthernet/name";
        }
      }
      //  Fcpa                Fiber Channel
      //  Filter              Filter interface
      //  Filtergroup         Filter Group interface
      //  GMPLS               MPLS interface
      
      leaf GigabitEthernet {
        description
          "GigabitEthernet IEEE 802.3z";
        tailf:cli-allow-join-with-value {
          tailf:cli-display-joined;
        }
        type string;
        tailf:non-strict-leafref {
          path "/ios:native/interface/GigabitEthernet/name";
        }
      }
      //  LongReachEthernet   Long-Reach Ethernet interface
     
      leaf Loopback {
        description
          "Loopback interface";
        tailf:cli-allow-join-with-value {
          tailf:cli-display-joined;
        }
        type uint32;
        tailf:non-strict-leafref {
          path "/ios:native/interface/Loopback/name";
        }
      }
      //  Lspvif              LSP virtual interface
      //  MFR                 Multilink Frame Relay bundle interface


      leaf LISP {
        description
          "Locator/ID Separation Protocol Virtual Interface";
        tailf:cli-allow-join-with-value {
          tailf:cli-display-joined;
        }
        type decimal64 {
          fraction-digits 10;
          range "0..65520";
        }
        tailf:non-strict-leafref {
          path "/ios:native/interface/LISP/name";
        }
      }
      leaf Multilink {
        description
          "Multilink-group interface";
        tailf:cli-allow-join-with-value {
          tailf:cli-display-joined;
        }
        type uint16;
        tailf:non-strict-leafref {
          path "/ios:native/interface/Multilink/name";
        }
      }
      // Null                Null interface      
      leaf nve {
        description
          "Network virtualization endpoint interface";
        tailf:cli-allow-join-with-value {
          tailf:cli-display-joined;
        }
        type uint16;
//        tailf:non-strict-leafref {
//          path "/ios:native/interface/nve/name";
//        }        
      }
      leaf overlay {
        description
          "Overlay interface";
        tailf:cli-allow-join-with-value {
          tailf:cli-display-joined;
        }
        type uint16;
        tailf:non-strict-leafref {
          path "/ios:native/interface/overlay/name";
        }
      }


      leaf Port-channel {
        description
          "Ethernet Channel of interfaces";
        tailf:cli-allow-join-with-value {
          tailf:cli-display-joined;
        }
        type uint32;
        tailf:non-strict-leafref {
          path "/ios:native/interface/Port-channel/name";
        }
      }
      container Port-channel-subinterface {
        tailf:cli-no-keyword;
        tailf:cli-drop-node-name;
        tailf:cli-flatten-container;
        tailf:cli-compact-syntax;
        leaf Port-channel {
          tailf:cli-allow-join-with-value {
            tailf:cli-display-joined;
          }
          type string;
          tailf:non-strict-leafref {
            path "/ios:native/interface/Port-channel-subinterface/Port-channel/name";
          }
        }
      }
      //  Portgroup           Portgroup interface
      //  Pos-channel         POS Channel of interfaces
      //  SYSCLOCK            Telecom-Bus Clock Controlle



      leaf pseudowire {
        description
          "Pseudowire Interface";
        tailf:cli-allow-join-with-value {
          tailf:cli-display-joined;
        }
        type uint32;
        tailf:non-strict-leafref {
          path "/ios:native/interface/pseudowire/name";
        }
      }
      leaf SM {
        description
          "SM Interface";
        tailf:cli-allow-join-with-value {
          tailf:cli-display-joined;
        }
        type string;
        tailf:non-strict-leafref {
          path "/ios:native/interface/SM/name";
        }
      }
      leaf Cellular {
        description
          "Cellular Interface";
        tailf:cli-allow-join-with-value {
          tailf:cli-display-joined;
        }
        type string;
        tailf:non-strict-leafref {
          path "/ios:native/interface/Cellular/name";
        }
      }
      leaf Serial {
        description
          "Serial interface";
        tailf:cli-allow-join-with-value {
          tailf:cli-display-joined;
        }
        type string;
        tailf:non-strict-leafref {
          path "/ios:native/interface/Serial/name";
        }
      }


      leaf TenGigabitEthernet {
        description
          "Ten Gigabit Ethernet";
        tailf:cli-allow-join-with-value {
          tailf:cli-display-joined;
        }
        type string;
        tailf:non-strict-leafref {
          path "/ios:native/interface/TenGigabitEthernet/name";
        }
      }
      //  Tunnel              Tunnel interface
      //  Vif                 PGM Multicast Host interface
      //  Virtual-Ethernet    Virtual Ethernet interface
      
      leaf Tunnel {
        description
          "Tunnel interface";
        tailf:cli-allow-join-with-value {
          tailf:cli-display-joined;
        }
        type uint32;
        tailf:non-strict-leafref {
          path "/ios:native/interface/Tunnel/name";
        }
      }


      leaf Virtual-Template {
        description
          "Virtual Template interface";
        tailf:cli-allow-join-with-value {
          tailf:cli-display-joined;
        }
        type uint16;
        tailf:non-strict-leafref {
          path "/ios:native/interface/Virtual-Template/name";
        }
      }
 
       
      //  Virtual-TokenRing   Virtual TokenRing
      
      leaf Vlan {
        description
          "Iosxr Vlans";
        tailf:cli-allow-join-with-value {
          tailf:cli-display-joined;
        }
        type uint16;
        tailf:non-strict-leafref {
          path "/ios:native/interface/Vlan/name";
        }
      }
      

      leaf VirtualPortGroup {
        description
          "Virtual Port Group";
        tailf:cli-allow-join-with-value {
          tailf:cli-display-joined;
        }
        type uint16;
        tailf:non-strict-leafref {
          path "/ios:native/interface/VirtualPortGroup/name";
        }
      }
      leaf vasileft {
        description
          "vasileft";
        tailf:cli-allow-join-with-value {
          tailf:cli-display-joined;
        }
        type uint16;
        tailf:non-strict-leafref {
          path "/ios:native/interface/vasileft/name";
        }
      }
      leaf vasiright {
        description
          "vasiright";
        tailf:cli-allow-join-with-value {
          tailf:cli-display-joined;
        }
        type uint16;
        tailf:non-strict-leafref {
          path "/ios:native/interface/vasiright/name";
        }
      }
      //  VoaBypassIn         VOA-Bypass-In interface
      //  VoaBypassOut        VOA-Bypass-Out interface
      //  VoaFilterIn         VOA-Filter-In interface
      //  VoaFilterOut        VOA-Filter-Out interface
      //  VoaIn               VOA-In interface
      //  VoaOut              VOA-Out interface

    }
  }// interface-grouping - all interface lists collected

  grouping ethernet-grouping {
    choice ethernet-choice {
      leaf FastEthernet {
        description
          "FastEthernet IEEE 802.3";
        tailf:cli-allow-join-with-value {
          tailf:cli-display-joined;
        }
        type string;
        tailf:non-strict-leafref {
          path "/ios:native/interface/FastEthernet/name";
        }
      }
      leaf GigabitEthernet {
        description
          "GigabitEthernet IEEE 802.3z";
        tailf:cli-allow-join-with-value {
          tailf:cli-display-joined;
        }
        type string;
        tailf:non-strict-leafref {
          path "/ios:native/interface/GigabitEthernet/name";
        }
      }
      leaf Port-channel {
        description
          "Ethernet Channel of interfaces";
        tailf:cli-allow-join-with-value {
          tailf:cli-display-joined;
        }
        type uint32;
        tailf:non-strict-leafref {
          path "/ios:native/interface/Port-channel/name";
        }
      }
      leaf TenGigabitEthernet {
        description
          "Ten Gigabit Ethernet";
        tailf:cli-allow-join-with-value {
          tailf:cli-display-joined;
        }
        type string;
        tailf:non-strict-leafref {
          path "/ios:native/interface/TenGigabitEthernet/name";
        }
      }
      leaf vlan {
        description
          "Catalyst Vlans";
        tailf:cli-allow-join-with-value {
          tailf:cli-display-joined;
        }
        type uint16 {
          range "1..4094";
        }
        tailf:non-strict-leafref {
          path "/ios:native/interface/Vlan/name";
        }
      }
    }
  }

  grouping ip-community-list-standard-grouping {
    container deny {
      description
        "Specify community to reject";
      leaf-list deny-list {
        tailf:cli-drop-node-name;
        tailf:cli-optional-in-sequence;
        tailf:cli-flat-list-syntax;
        type union {
          type community-number-type;
          type community-well-known-type;
        }
      }
    }
    container permit {
      description
        "Specify community to accept";
      leaf-list permit-list {
        tailf:cli-drop-node-name;
        tailf:cli-optional-in-sequence;
        tailf:cli-flat-list-syntax;
        type union {
          type community-number-type;
          type community-well-known-type;
        }
      }
    }
  }

  grouping ip-community-list-expanded-grouping {
    container deny {
      description
        "Specify community to reject";
      leaf-list deny-list {
        tailf:cli-drop-node-name;
        tailf:cli-list-syntax;
        ordered-by user;
        type string;
      }
    }
    container permit {
      description
        "Specify community to accept";
      leaf-list permit-list {
        tailf:cli-drop-node-name;
        tailf:cli-list-syntax;
        ordered-by user;
        type string;
      }
    }
  }

  grouping ip-extcommunity-list-standard-grouping {
    container deny {
      description
        "Specify community to reject";
      list rt {
        description
          "Route Target extended community";
        tailf:cli-suppress-mode;
        tailf:cli-delete-when-empty;
        tailf:cli-suppress-list-no;
        key "name";
        leaf name {
          type string;
        }
      }
      list soo {
        description
          "Site-of-Origin extended community";
        tailf:cli-suppress-mode;
        tailf:cli-delete-when-empty;
        tailf:cli-suppress-list-no;
        key "name";
        leaf name {
          type string;
        }
      }
      list vpn-distinguisher {
        description
          "VPN Distinguisher extcomm";
        tailf:cli-suppress-mode;
        tailf:cli-delete-when-empty;
        tailf:cli-suppress-list-no;
        key "name";
        leaf name {
          type string;
        }
      }
    }
    container permit {
      description
        "Specify community to accept";
      list rt {
        description
          "Route Target extended community";
        tailf:cli-suppress-mode;
        tailf:cli-delete-when-empty;
        tailf:cli-suppress-list-no;
        key "name";
        leaf name {
          type string;
        }
      }
      list soo {
        description
          "Site-of-Origin extended community";
        tailf:cli-suppress-mode;
        tailf:cli-delete-when-empty;
        tailf:cli-suppress-list-no;
        key "name";
        leaf name {
          type string;
        }
      }
      list vpn-distinguisher {
        description
          "VPN Distinguisher extcomm";
        tailf:cli-suppress-mode;
        tailf:cli-delete-when-empty;
        tailf:cli-suppress-list-no;
        key "name";
        leaf name {
          type string;
        }
      }
    }
  }

  grouping ip-route-options-grouping {
    leaf metric {
      tailf:cli-drop-node-name;
      tailf:cli-break-sequence-commands;
      type uint8 {
        range "1..255";
      }
    }
    leaf forwarding-router-adr {
      tailf:cli-drop-node-name;
      type inet:ipv4-address;
    }
    leaf global {
      description
        "Next hop address is global";
      type empty;
    }
    leaf name {
      description
        "Specify name of the next hop";
      type string;
    }
    leaf permanent {
      description
        "permanent route";
      type empty;
    }
    leaf multicast {
      description
        "multicast route";
      type empty;
    }
    leaf dhcp {
      description
        "Default Gateway obtained from DHCP";
      tailf:cli-case-insensitive;
      type empty;
    }
    leaf tag {
      description
        "Set tag for this route";
      type uint32 {
        range "1..4294967295";
      }
    }
    leaf track {
      description
        "Install route depending on tracked item";
      type uint16 {
        range "1..1000";
      }
    }
  }

  grouping ip-route-grouping { 
    list ip-route-interface-forwarding-list {
      tailf:cli-drop-node-name;
      tailf:cli-suppress-mode;
      tailf:cli-delete-when-empty;
      tailf:cli-compact-syntax;
      tailf:cli-sequence-commands {
        tailf:cli-reset-all-siblings;
      }
      key "prefix mask";
      leaf prefix {
        tailf:cli-disallow-value "vrf";
        type inet:ipv4-address;
      }
      leaf mask {
        type inet:ipv4-address;
      }
      list fwd-list {
          tailf:cli-drop-node-name;
          tailf:cli-suppress-mode;
          tailf:cli-delete-when-empty;
          tailf:cli-compact-syntax;
          key fwd;
          leaf fwd {
              type union {
                 type enumeration {
                    enum "Null0";
                 }
                 type inet:ipv4-address;
                 type string;
              }
          }
          uses ip-route-options-grouping;
      }
    }
  }

  grouping ip-pim-grouping {
    // ip pim accept-register
    container accept-register {
      description
        "Registers accept filter";
      leaf list {
        description
          "Access list";
        type ext-acl-type;
      }
    }
    container autorp {
      description
        "Configure AutoRP global operations";
      presence "true";
      leaf listener {
        description
          "Allow AutoRP packets across sparse mode interface";
        type empty;
      }
    }
    leaf register-source {
      description
        "Source address for PIM Register";
      tailf:cli-full-command;
      type string;
    }
    list rp-address {
      description
        "PIM RP-address (Rendezvous Point)";
      tailf:cli-compact-syntax;
      tailf:cli-suppress-mode;
      key address;
      leaf address {
        type inet:ipv4-address;
      }
      leaf access-list {
        tailf:cli-drop-node-name;
        type std-acl-type;
      }
      leaf override {
        description
          "Overrides dynamically learnt RP mappings";
        type empty;
      }
    }
    //ip pim spt-threshold
    list spt-threshold {
      description
        "Source-tree switching threshold";
      tailf:cli-suppress-mode;
      tailf:cli-compact-syntax;
      key "how group-list";
      leaf how {
        type enumeration {
          enum 0;
          enum infinity;
        }
      }
      leaf group-list {
        description
          "Group address access-list";
        tailf:cli-expose-key-name;
        type std-acl-type;
      }
    }
    container spt-threshold-container {
      tailf:cli-drop-node-name;
      container spt-threshold {
        description
          "Source-tree switching threshold";
        leaf how {
          tailf:cli-drop-node-name;
          type enumeration {
            enum 0;
            enum infinity;
          }
        }
      }
    }
    container send-rp-announce {
      description
        "Auto-RP send RP announcement";
      list Port-channel {
        description
          "Ethernet Channel of interfaces";
          tailf:cli-allow-join-with-key {
          tailf:cli-display-joined;
        }
        tailf:cli-suppress-mode;
        tailf:cli-compact-syntax;
        key "name";
        leaf name { 
          tailf:cli-diff-dependency "/ios:native/interface/Port-channel";
          type uint32 {
            range "1..512";
          }
        }
        leaf scope {
          description
            "RP announcement scope";
          type uint8{
            range "1..255";
          }
        } 
      }
    }
    // ip pim ssm
    container ssm {
      description
        "Configure Source Specific Multicast";
      leaf range {
        type union {
          type uint16 {
            range "1..99";
          }
          type string {
            pattern "[a-zA-Z].*";
          }
        }
      }
    }
  }

  grouping ip-sla-path-jitter-grouping {
    leaf frequency {
      description
        "Frequency of an operation";
      tailf:cli-full-command;
      type uint32 {
        range "1..604800";
      }
    }
    leaf-list lsr-path {
      description
        "Loose Source Routing Path";
      tailf:cli-flat-list-syntax;
      tailf:cli-full-command;
      type union {
        type string;
        type inet:ipv4-address;
      }
    }
    leaf owner {
      description
        "Owner of Entry";
      tailf:cli-multi-value;
      tailf:cli-full-command;
      type string;
    }
    leaf request-data-size {
      description
        "Request data size";
      tailf:cli-full-command;
      type uint32 {
        range "0..16384";
      }
    }
    leaf tag {
      description
        "User defined tag";
      tailf:cli-multi-value;
      tailf:cli-full-command;
      type string;
    }
    leaf threshold {
      description
        "Operation threshold in milliseconds";
      tailf:cli-full-command;
      type uint32 {
        range "0..60000";
      }
    }
    leaf timeout {
      description
        "Timeout of an operation";
      tailf:cli-full-command;
      type uint32 {
        range "0..604800000";
      }
    }
    leaf tos {
      description
        "Type Of Service";
      tailf:cli-full-command;
      type uint8;
    }
    leaf verify-data {
      description
        "Verify data";
      tailf:cli-full-command;
      type empty;
    }
    leaf vrf {
      description
        "Configure IP SLAs for a VPN Routing/Forwarding instance";
      tailf:cli-full-command;
      type string;
    }
  }

  grouping ip-sla-default-path-jitter-grouping {
    leaf frequency {
      description
        "Frequency of an operation";
      tailf:cli-full-command;
      type empty;
    }
    leaf lsr-path {
      description
        "Loose Source Routing Path";
      tailf:cli-full-command;
      type empty;
    }
    leaf owner {
      description
        "Owner of Entry";
      tailf:cli-full-command;
      type empty;
    }
    leaf request-data-size {
      description
        "Request data size";
      tailf:cli-full-command;
      type empty;
    }
    leaf tag {
      description
        "User defined tag";
      tailf:cli-full-command;
      type empty;
    }
    leaf threshold {
      description
        "Operation threshold in milliseconds";
      tailf:cli-full-command;
      type empty;
    }
    leaf timeout {
      description
        "Timeout of an operation";
      tailf:cli-full-command;
      type empty;
    }
    leaf tos {
      description
        "Type Of Service";
      tailf:cli-full-command;
      type empty;
    }
    leaf verify-data {
      description
        "Verify data";
      tailf:cli-full-command;
      type empty;
    }
    leaf vrf {
      description
        "Configure IP SLAs for a VPN Routing/Forwarding instance";
      tailf:cli-full-command;
      type empty;
    }
  }

  grouping ipv6-pim-grouping {
    container rp-address {
      description
        "Configure Sparse-Mode Rendezvous Point";
      tailf:cli-compact-syntax;
      tailf:cli-sequence-commands {
        tailf:cli-reset-siblings;
      }
      leaf address {
        tailf:cli-drop-node-name;
        type union {
          type string;
          type inet:ipv6-address;
        }
      }
      leaf access-list {
        tailf:cli-drop-node-name;
        tailf:cli-break-sequence-commands;
        type union {
          type string;
        }
      }
      leaf bidir {
        description
          "Specify keyword bidir to configure a bidir RP";
        tailf:cli-full-command;
        type empty;
      }
    }
  }

  grouping ipv6-route-options-grouping {
    leaf next-hop {
      tailf:cli-drop-node-name;
      description
        "IPv6 address of next-hop";
      type inet:ipv6-address;
    }
    leaf distance {
      tailf:cli-drop-node-name;
      type uint8;
    }
    choice type-choice {
      leaf multicast {
        description
          "Route only usable by multicast";
        tailf:cli-full-command;
        type empty;
      }
      leaf unicast {
        description
          "Route only usable by unicast";
        type empty;
      }
    }
    leaf tag {
      description
        "Tag value";
      tailf:cli-full-command;
      type uint32;
    }
    leaf track {
      description
        "Tracked";
      type uint32;
    }
  }

  grouping ipv6-route-grouping {
    list ipv6-route-list {
      tailf:cli-drop-node-name;
      tailf:cli-suppress-mode;
      tailf:cli-delete-when-empty;
      tailf:cli-compact-syntax;
      tailf:cli-reset-container;
      tailf:cli-incomplete-command;
      key "prefix";
      leaf prefix {
        type ipv6-prefix;
      }
      list ipv6-fwd-list {
          tailf:cli-drop-node-name;
          tailf:cli-suppress-mode;
          tailf:cli-delete-when-empty;
          tailf:cli-compact-syntax;
          key fwd;
          leaf fwd {
             tailf:cli-diff-dependency "/ios:native/interface/Port-channel";
             type union {
                 type enumeration {
                     enum "Null0";
                 }
                 type inet:ipv6-address;
                 type string;
             }
          }
          uses ipv6-route-options-grouping;
      }
    }
  }

  grouping random-detect-grouping {
    leaf min-threshold {
      tailf:cli-drop-node-name;
      tailf:cli-incomplete-command;
      type uint16 {
        range "1..4096";
      }
    }
    leaf max-threshold {
      tailf:cli-drop-node-name;
      tailf:cli-incomplete-command;
      type uint16 {
        range "1..4096";
      }
    }
    leaf denominator {
      tailf:cli-drop-node-name;
      type uint32 {
        range "1..65535";
      }
    }
  }

  grouping class-map-match-grouping {
    // class-map * / match current-method-priority
    container current-method-priority {
      description 
        "match the priority against the current method's priority";
      leaf eq {
        description 
          "equal to";
        type uint8 {
          range "1..254";
        }
      }
      leaf gt {
        description 
          "greater than";
        type uint8 {
          range "1..254";
        }
      }
      leaf lt {
        description 
          "less than";
        type uint8 {
          range "1..254";
        }
      }
    }
    // class-map * / match application
    container application {
      description
        "Application to match";
      container application-group {
        description
          "Application Group to match";
        leaf telepresence-group {
          description
            "Telepresence Group";
          tailf:cli-full-command;
          type empty;
        }
        leaf vmware-group {
          description
            "VMWARE Group";
          tailf:cli-full-command;
          type empty;
        }
        leaf webex-group {
          description
            "WebEx Group";
          tailf:cli-full-command;
          type empty;
        }
      }
      container attribute {
        description
          "Application attribute to match";
        leaf media-type {
          description
            "Media type attribute to match";
          type enumeration {
            enum "audio";
            enum "audio-video";
            enum "control";
            enum "data";
            enum "video";
          }
        }
      }
    }
    // class-map * / match access-group
    container access-group {
      description
        "Access group";
      leaf index {
        tailf:cli-drop-node-name;
        type uint32 {
          range "1..2699";
        }
      }
      leaf-list name {
        description
          "Named Access List";
        tailf:cli-list-syntax;
        type string;
      }
    }
    // class-map * / match any
    leaf any {
      description
        "Any packets";
      type empty;
    }
    // class-map * / match class-map
    leaf-list class-map {
      description
        "Class map";
      tailf:cli-list-syntax;
      type string;
//      type leafref {
//        path "/ios:native/class-map/name";
//        // tailf:info "WORD;;Match class-map name";
//      }      
    }
    // class-map * / match cos
    leaf-list cos {
      description
        "IEEE 802.1Q/ISL class of service/user priority values";
      tailf:cli-flat-list-syntax;
      type uint8 {
        range "0..7";
      }
    }
    // class-map * / match destination-address
    container destination-address {
      description
        "Destination address";
      leaf-list mac {
        description
          "MAC address";
        tailf:cli-list-syntax;
        type yang:mac-address;
      }
    }
    // class-map * / discard-class
    leaf-list discard-class {
      description
        "Discard behavior identifier";
      tailf:cli-list-syntax;
      type uint8 {
        range "0..7";
      }
    }
    // class-map * / dscp
    leaf-list dscp {
      description
        "Match DSCP in IP(v4) and IPv6 packets";
      tailf:cli-flat-list-syntax;
      tailf:cli-list-syntax;
      type dscp-type;
    }
    // class-map * / fr-de
    leaf fr-de {
      description
        "Match on Frame-relay DE bit";
      type empty;
    }
    // class-map * / fr-dlci
    leaf-list fr-dlci {
      description
        "Match on fr-dlci";
      tailf:cli-list-syntax;
      type uint16 {
        range "16..1007";
      }
    }
    // class-map * / input-interface
    leaf-list input-interface {
      description
        "Select an input interface to match";
      tailf:cli-list-syntax;
      type string;
    }
    // class-map * / ip
    container ip {
      description
        "IP specific values";
      leaf-list dscp {
        description
          "Match IP DSCP (DiffServ CodePoints)";
        tailf:cli-flat-list-syntax;
        tailf:cli-list-syntax;
        type dscp-type;
      }
      // class-map * / ip precedence
      leaf-list precedence {
        description
          "Match IP precedence";
        tailf:cli-flat-list-syntax;
        type precedence-type;
      }
      // class-map * / ip rtp
      list rtp {
        description
          "Match RTP port nos";
        key "port1 port2";
        leaf port1 {
          type uint16 {
            range "2000..65535";
          }
        }
        leaf port2 {
          type uint16 {
            range "0..16383";
          }
        }
      }
    }
    // class-map * / non-client-nrt
    leaf non-client-nrt {
      tailf:cli-full-command;
      type empty;
    }
    // class-map * / mpls
    container mpls {
      description
        "Multi Protocol Label Switching specific values";
      container experimental {
        description
          "Match MPLS experimental";
        leaf-list topmost {
          description
            "Match MPLS experimental value on topmost label";
          tailf:cli-flat-list-syntax;
          type uint8 {
            range "0..7";
          }
        }
      }
    }
    // class-map * / packet
    container packet {
      description
        "Layer 3 Packet length";
      container length {
        description
          "Layer 3 Packet length";
        leaf max {
          description
            "Maximum length of packet";
          type uint16 {
            range "1..2000";
          }
        }
        leaf min {
          description
            "Minimum length of packet";
          type uint16 {
            range "1..2000";
          }
        }
      }
    }
    // class-map * / precedence
    leaf-list precedence {
      description
        "Match Precedence in IP(v4) and IPv6 packets";
      tailf:cli-flat-list-syntax;
      type precedence-type;
    }
    // class-map * / protocol
    container protocol {
      description
        "Protocol";
      leaf protocols {
        tailf:cli-drop-node-name;
        type enumeration {
          enum "x802-11-iapp";
          enum "ace-svr";
          enum "aol";
          enum "appleqtc";
          enum "biff";
          enum "bittorrent";
          enum "bootpc";
          enum "bootps";
          enum "cddbp";
          enum "cifs";
          enum "cisco-fna";
          enum "cisco-net-mgmt";
          enum "cisco-svcs";
          enum "cisco-sys";
          enum "cisco-tdp";
          enum "cisco-tna";
          enum "citriximaclient";
          enum "clp";
          enum "creativepartnr";
          enum "creativeserver";
          enum "daytime";
          enum "dbase";
          enum "dbcontrol_agent";
          enum "ddns-v3";
          enum "dhcp-failover";
          enum "directconnect";
          enum "discard";
          enum "dnsix";
          enum "echo";
          enum "entrust-svc-hdlr";
          enum "entrust-svcs";
          enum "exec";
          enum "fcip-port";
          enum "ftps";
          enum "gdoi";
          enum "giop";
          enum "gtpv0";
          enum "gtpv1";
          enum "h225ras";
          enum "h323callsigalt";
          enum "hp-alarm-mgr";
          enum "hp-collector";
          enum "hp-managed-node";
          enum "hsrp";
          enum "https";
          enum "ica";
          enum "icabrowser";
          enum "ident";
          enum "igmpv3lite";
          enum "imap3";
          enum "imaps";
          enum "ipass";
          enum "ipsec-msft";
          enum "irc-serv";
          enum "ircs";
          enum "ircu";
          enum "isakmp";
          enum "iscsi";
          enum "iscsi-target";
          enum "kermit";
          enum "ldap-admin";
          enum "ldaps";
          enum "login";
          enum "lotusmtap";
          enum "lotusnote";
          // AppNav match protocol
          enum "mapi";
          enum "ms-ad-rep";
          enum "ms-exch-nspi";
          enum "ms-frs";
          enum "ms-frsapi";
          enum "ms-rfr";
          //ms-sql         MS-SQL
          enum "msn-messenger";
          enum "netlogon";
          enum "microsoft-ds";
          enum "ms-cluster-net";
          enum "ms-dotnetster";
          enum "ms-sna";
          enum "ms-sql";
          enum "ms-sql-m";
          enum "msexch-routing";
          enum "msnmsgr";
          enum "msrpc";
          enum "mysql";
          enum "n2h2server";
          enum "ncp";
          enum "net8-cman";
          enum "netbios-dgm";
          enum "netbios-ns";
          enum "netbios-ssn";
          enum "netstat";
          enum "oem-agent";
          enum "oracle";
          enum "oracle-em-vp";
          enum "oraclenames";
          enum "orasrv";
          enum "pcanywheredata";
          enum "pcanywherestat";
          enum "pop3s";
          enum "pwdgen";
          enum "qmtp";
          enum "r-winsock";
          enum "radius";
          enum "rdb-dbs-disp";
          enum "realmedia";
          enum "realsecure";
          enum "router";
          enum "rsvp-encap";
          enum "rsvp_tunnel";
          enum "rtc-pm-port";
          enum "rtelnet";
          enum "send";
          enum "shell";
          enum "sip-tls";
          enum "sms";
          enum "snmptrap";
          enum "sql-net";
          enum "sqlserv";
          enum "sqlsrv";
          enum "sshell";
          enum "ssp";
          enum "syslog-conn";
          enum "tacacs";
          enum "tacacs-ds";
          enum "tarantella";
          enum "tcp";
          enum "telnets";
          enum "time";
          enum "timed";
          enum "tr-rsrb";
          enum "ttc";
          enum "udp";
          enum "uucp";
          enum "vqp";
          enum "webster";
          enum "who";
          enum "wins";
          enum "x11";
          enum "xdmcp";
          enum "ymsgr";
          enum "aarp";
          enum "appletalk";
          enum "arp";
          enum "bgp";
          enum "bridge";
          enum "bstun";
          enum "cdp";
        }
      }
      container citrix {
        description
          "Citrix Systems ICA protocol";
        presence "enable citrix system protocol matching";
        leaf ica-tag {
          description
            "Citrix ICA tag 0-high 1-medium 2-low 3-background";
          type string;
        }
      }
      leaf clns {
        description
          "ISO CLNS";
        type empty;
      }
      leaf clns_es {
        description
          "ISO CLNS End System";
        type empty;
      }
      leaf clns_is {
        description
          "ISO CLNS Intermediate System";
        type empty;
      }
      leaf cmns {
        description
          "ISO CMNS";
        type empty;
      }
      leaf compressedtcp {
        description
          "Compressed TCP (VJ";
        type empty;
      }
      leaf cuseeme {
        description
          "CU-SeeMe desktop video conference";
        type empty;
      }
      leaf decnet {
        description
          "DECnet";
        type empty;
      }
      leaf decnet_node {
        description
          "DECnet Node";
        type empty;
      }
      leaf decnet_router-l1 {
        description
          "DECnet Router L1";
        type empty;
      }
      leaf decnet_router-l2 {
        description
          "DECnet Router L2";
        type empty;
      }
      leaf dhcp {
        description
          "Dynamic Host Configuration";
        type empty;
      }
      leaf dlsw {
        type empty;
      }
      leaf dns {
        type empty;
      }
      leaf edonkey {
        type empty;
      }
      leaf egp {
        type empty;
      }
      leaf eigrp {
        type empty;
      }
      leaf exchange {
        type empty;
      }
      container fasttrack {
        description
          "FastTrack Traffic - KaZaA, Morpheus, Grokster";
        presence "enable fasttrack matching";
        leaf file-transfer {
          description
            "File transfer stream";
          type string;
        }
      }
      leaf finger {
        type empty;
      }
      leaf ftp {
        type empty;
      }
      container gnutella {
        description
          "Gnutella Version2 Traffic - BearShare, Shareeza, Morpheus";
        presence "enable gnutella matching";
        leaf file-transfer {
          description
            "File transfer stream";
          type string;
        }
      }
      leaf gopher {
        type empty;
      }
      leaf gre {
        type empty;
      }
      leaf h323 {
        type empty;
      }
      container http {
        description
          "World Wide Web traffic";
        presence "enable http traffic matching";
        leaf c-header-field {
          description
            "Client general Header Field";
          type string;
        }
        leaf host {
          description
            "Server Host Name";
          type string;
        }
        leaf mime {
          description
            "Match MIME Type";
          type string;
        }
        leaf s-header-field {
          description
            "Server general Header Field";
          type string;
        }
        leaf url {
          description
            "Match URL String";
          type string;
        }
      }
      leaf icmp {
        description
          "Internet Control Message";
        type empty;
      }
      leaf imap {
        description
          "Internet Message Access Protocol";
        type empty;
      }
      leaf ip {
        description
          "IP";
        type empty;
      }
      leaf ipinip {
        description
          "IP in IP (encapsulation";
        type empty;
      }
      leaf ipsec {
        description
          "IP Security Protocol (ESP/AH";
        type empty;
      }
      leaf ipv6 {
        description
          "IPV6";
        type empty;
      }
      leaf ipx {
        description
          "Novell IPX";
        type empty;
      }
      leaf irc {
        type empty;
        description
          "Internet Relay Chat";
      }
      container kazaa2 {
        description
          "Kazaa Version 2";
        presence "enable kazaa version 2 matching";
        leaf file-transfer {
          description
            "File transfer stream";
          type string;
        }
      }
      leaf kerberos {
        description
          "Kerberos";
        type empty;
      }
      leaf l2tp {
        description
          "L2F/L2TP tunnel";
        type empty;
      }
      leaf ldap {
        description
          "Lightweight Directory Access Protocol";
        type empty;
      }
      leaf llc2 {
        description
          "llc2";
        type empty;
      }
      leaf mgcp {
        description
          "Media Gateway Control Protocol";
        type empty;
      }
      container napster {
        description
          "Napster Traffic";
        presence "enable napster matching";
        leaf non-std {
          description
            "Non-standard port advertizements";
          type empty;
        }
      }
      leaf netbios {
        description
          "NetBIOS";
        type empty;
      }
      leaf netshow {
        description
          "Microsoft Netshow";
        type empty;
      }
      leaf nfs {
        description
          "Network File System";
        type empty;
      }
      leaf nntp {
        description
          "Network News Transfer Protocol";
        type empty;
      }
      leaf notes {
        description
          "Lotus Notes(R";
        type empty;
      }
      leaf novadigm {
        description
          "Novadigm EDM";
        type empty;
      }
      leaf ntp {
        description
          "Network Time Protocol";
        type empty;
      }
      leaf ospf {
        description
          "Open Shortest Path First";
        type empty;
      }
      leaf pad {
        description
          "PAD links";
        type empty;
      }
      leaf pcanywhere {
        description
          "Symantec pcANYWHERE";
        type empty;
      }
      leaf pop3 {
        description
          "Post Office Protocol";
        type empty;
      }
      leaf pppoe {
        description
          "PPP over Ethernet";
        type empty;
      }
      leaf pptp {
        description
          "Point-to-Point Tunneling Protocol";
        type empty;
      }
      leaf printer {
        description
          "print spooler/lpd";
        type empty;
      }
      leaf qllc {
        description
          "qllc protocol";
        type empty;
      }
      leaf rcmd {
        description
          "BSD r-commands (rsh, rlogin, rexec";
        type empty;
      }
      leaf rip {
        description
          "Routing Information Protocol";
        type empty;
      }
      leaf rsrb {
        description
          "Remote Source-Route Bridging";
        type empty;
      }
      leaf rsvp {
        description
          "Resource Reservation Protocol";
        type empty;
      }
      leaf rtcp {
        description
          "Real Time Control Protocol";
        type empty;
      }
      container rtp {
        description
          "Real Time Protocol";
        presence "enable rtp matching";
        leaf audio {
          description
            "Match voice packets";
          type empty;
        }
        leaf payload-type {
          description
            "Match an explicit PT";
          type string;
        }
        leaf video {
          description
            "Match video packets";
          type empty;
        }
      }
      leaf rtsp {
        description
          "Real Time Streaming Protocol";
        type empty;
      }
      leaf secure-ftp {
        description
          "FTP over TLS/SSL";
        type empty;
      }
      leaf secure-http {
        description
          "Secured HTTP";
        type empty;
      }
      leaf secure-imap {
        description
          "Internet Message Access Protocol over TLS/SSL";
        type empty;
      }
      leaf secure-irc {
        description
          "Internet Relay Chat over TLS/SSL";
        type empty;
      }
      leaf secure-ldap {
        description
          "Lightweight Directory Access Protocol over TLS/SSL";
        type empty;
      }
      leaf secure-nntp {
        description
          "Network News Transfer Protocol over TLS/SSL";
        type empty;
      }
      leaf secure-pop3 {
        description
          "Post Office Protocol over TLS/SSL";
        type empty;
      }
      leaf secure-telnet {
        description
          "Telnet over TLS/SSL";
        type empty;
      }
      leaf sip {
        description
          "Session Initiation Protocol";
        type empty;
      }
      leaf skinny {
        description
          "Skinny Protocol";
        type empty;
      }
      container smtp {
        description
          "Simple Mail Transfer Protocol";
        leaf extended {
          type empty;
        }
      }
      leaf snapshot {
        description
          "Snapshot routing support";
        type empty;
      }
      leaf snmp {
        description
          "Simple Network Management Protocol";
        type empty;
      }
      leaf socks {
        description
          "SOCKS";
        type empty;
      }
      leaf sqlnet {
        description
          "SQL*NET for Oracle";
        type empty;
      }
      leaf sqlserver {
        description
          "MS SQL Server";
        type empty;
      }
      leaf ssh {
        description
          "Secured Shell";
        type empty;
      }
      leaf streamwork {
        description
          "Xing Technology StreamWorks player";
        type empty;
      }
      leaf stun {
        description
          "Serial Tunnel";
        type empty;
      }
      leaf sunrpc {
        description
          "Sun RPC";
        type empty;
      }
      leaf syslog {
        description
          "System Logging Utility";
        type empty;
      }
      leaf telnet {
        description
          "Telnet";
        type empty;
      }
      leaf tftp {
        description
          "Trivial File Transfer Protocol";
        type empty;
      }
      leaf vdolive {
        description
          "VDOLive streaming video";
        type empty;
      }
      leaf vofr {
        description
          "voice over Frame Relay packets";
        type empty;
      }
      leaf winmx {
        description
          "WinMx file-sharing application";
        type empty;
      }
      leaf xwindows {
        description
          "X-Windows remote access";
        type empty;
      }
    }
    // class-map * / qos-group
    leaf-list qos-group {
      description
        "Qos-group";
      tailf:cli-list-syntax;
      type uint16 {
        range "0..99";
      }
    }
    // class-map * / match security-group
    container security-group {
      description
        "Security group";
      container destination {
        description
          "Destination security group";
        leaf tag {
          description
            "Security group tag";
          type uint16;
        }
      }
      container source {
        description
          "Source security group";
        leaf tag {
          description
            "Security group tag";
          type uint16;
        }
      }
    }
    // class-map * / source-address
    container source-address {
      description
        "Source address";
      leaf-list mac {
        description
          "MAC address";
        tailf:cli-list-syntax;
        type yang:mac-address;
      }
    }
    // class-map * / match vlan
    leaf-list vlan {
      description
        "VLANs to match";
      tailf:cli-range-list-syntax;
      tailf:cli-list-syntax;
      type uint16 {
        range "1..4094";
      }
    }
  }//class-map-match-grouping

  grouping class-map-appnav-match-grouping {
    leaf peer {
      description
        "APPNAV Peer Filter";
      when "../../type = 'appnav'";
      type string;
    }
  }

  grouping class-map-appnav-not-match-grouping {
    leaf peer {
      description
        "APPNAV Peer Filter";
      when "../../../type = 'appnav'";
      type string;
    }
  }

  grouping ntp-access-group-kod-grouping {
    leaf acl {
      tailf:cli-drop-node-name;
      type std-acl-type;
    }
    leaf kod {
      description
        "Send a Kiss-o-Death packet for failing peers";
      tailf:cli-optional-in-sequence;
      type empty;
    }
  }

  grouping ntp-access-group-grouping {
    container peer {
      description
        "Provide full access";
      tailf:cli-compact-syntax;
      tailf:cli-sequence-commands;
      uses ntp-access-group-kod-grouping;
    }
    //  query-only  Allow only control queries
    container query-only {
      description
        "Provide server and query access";
      tailf:cli-compact-syntax;
      tailf:cli-sequence-commands;
      uses ntp-access-group-kod-grouping;
    }
    container serve {
      description
        "Provide server and query access";
      tailf:cli-compact-syntax;
      tailf:cli-sequence-commands;
      uses ntp-access-group-kod-grouping;
    }
    //  serve-only  Provide only server access
    container serve-only {
      description
        "Provide only server access";
      tailf:cli-compact-syntax;
      tailf:cli-sequence-commands;
      uses ntp-access-group-kod-grouping;
    }
  }

  grouping ntp-peer-server-attr-grouping {
    leaf burst {
      description
        "Send a burst when peer is reachable (Default)";
      type empty;
    }
    leaf iburst {
      description
        "Send a burst when peer is unreachable (Default)";
      type empty;
    }
    leaf key {
      description
        "Configure peer authentication key";
      type uint32;
    }
    leaf maxpoll {
      description
        "Maximum poll interval";
      type uint8 {
        range "4..17";
      }
    }
    leaf minpoll {
      description
        "Minimum poll interval";
      type uint8 {
        range "4..17";
      }
    }
    leaf prefer {
      description
        "Prefer this peer when possible";
      type empty;
    }
    leaf source {
      description
        "Interface for source address";
      tailf:display-when "../../../server or ../../../ip or ../../../ipv6";
      type string;
    }
    leaf version {
      description
        "    Configure NTP version";
      type uint8;
    }
  }

  grouping ntp-peer-server-grouping {
    list server-list {
      tailf:cli-drop-node-name;
      tailf:cli-suppress-mode;
      tailf:cli-delete-when-empty;
      tailf:cli-compact-syntax;
      tailf:cli-reset-container;
      key "ip-address";
      leaf ip-address {
        tailf:cli-disallow-value "vrf|ip|ipv6";
        type union {
          type inet:ipv4-address;
          type string;
          type inet:ipv6-address;
        }
      }
      uses ntp-peer-server-attr-grouping;
    }
    list ip {
      description
        "Use IP for DNS resolution";
      tailf:cli-suppress-mode;
      tailf:cli-delete-when-empty;
      tailf:cli-compact-syntax;
      tailf:cli-reset-container;
      key "host-name";
      leaf host-name {
        type string;
      }
      uses ntp-peer-server-attr-grouping;
    }
    list ipv6 {
      description
        "Use IPv6 for DNS resolution";
      tailf:cli-suppress-mode;
      tailf:cli-delete-when-empty;
      tailf:cli-compact-syntax;
      tailf:cli-reset-container;
      key "host-name";
      leaf host-name {
        type string;
      }
      uses ntp-peer-server-attr-grouping;
    }
  }

  grouping line-grouping {
    // line * / authorization
    container authorization {
      description
        "Authorization parameters";
      container command {
        description
          "For exec (shell) commands";
        tailf:cli-compact-syntax;
        tailf:cli-sequence-commands;
        leaf enable-level {
          tailf:cli-drop-node-name;
          type uint8 {
            range "0..15";
          }
        }
        leaf auth-name {
          tailf:cli-drop-node-name;
          type string;
        }
      }
    }
    // line * / access-class
    container access-class {
      description
        "Filter connections based on an IP access list";
      tailf:cli-compact-syntax;
      tailf:cli-sequence-commands;
      tailf:cli-reset-container;
      tailf:cli-flatten-container;
      list acccess-list {
        tailf:cli-drop-node-name;
        tailf:cli-compact-syntax;
        tailf:cli-reset-container;
        tailf:cli-suppress-mode;
        tailf:cli-delete-when-empty;
        key "direction";
        leaf direction {
          type enumeration {
            enum "in";
            enum "out";
          }
        }
        leaf access-list {
          tailf:cli-drop-node-name;
          tailf:cli-prefix-key;
          type exp-acl-type;
          mandatory true;
        }
        leaf vrf-also {
          description
            "Same access list is applied for all VRFs";
          type empty;
        }
      }
    }
    // line * / activation-character
    leaf no-activation-character {
      tailf:alt-name "activation-character";
      tailf:cli-boolean-no;
      tailf:cli-trim-default;
      type boolean;
    }
    leaf activation-character {
      description
        "Define the activation character";
      tailf:cli-no-value-on-delete;
      type union {
        type string;
        type uint8 {
          range "0..127";
        }
      }
    }
    // line * / autocommand
    container autocommand {
      description
        "Automatically execute an EXEC command";
      leaf line {
        description
          "Appropriate EXEC command";
        tailf:cli-drop-node-name;
        tailf:cli-multi-value;
        type string;
      }
      container no-suppress-linenumber {
        description
          "Display service linenumber message";
        presence "true";
        leaf line {
          description
            "Appropriate EXEC command";
          tailf:cli-drop-node-name;
          tailf:cli-multi-value;
          type string;
        }
      }
    }
    // line * / autocommand-options
    container autocommand-options {
      description
        "Autocommand options";
      presence "true";
      tailf:cli-compact-syntax;
      container abort-character {
        description
          "Autocommand abort character";
        presence "true";
        leaf character {
          tailf:cli-drop-node-name;
          type union {
            type uint8;
            type string;
          }
        }
      }
      container delay {
        description
          "Delay autocommand execution";
        presence "true";
        leaf time {
          description
            "Time in seconds";
          tailf:cli-drop-node-name;
          type uint8 {
            range "0..120";
          }
        }
      }
      container nohangup {
        description
          "No hangup after autocommand completion";
        presence "true";
        leaf abort-character {
          description
            "Autocommand abort character";
          type empty;
        }
        leaf delay {
          description
            "Delay autocommand execution";
          type empty;
        }
      }
    }
    // line * / data-character-bits
    leaf data-character-bits {
      description
        "Bits per character";
      type uint8 {
        range "7..8";
      }
    }
    // line * / databits
    container databits {
      description
        "Set number of data bits per character";
      leaf set-to-5 {
        tailf:alt-name "5";
        description
          "Number of data bits";
        type empty;
      }
      leaf set-to-6 {
        tailf:alt-name "6";
        description
          "Number of data bits";
        type empty;
      }
      leaf set-to-7 {
        tailf:alt-name "7";
        description
          "Number of data bits";
        type empty;
      }
      leaf set-to-8 {
        tailf:alt-name "8";
        description
          "Number of data bits";
        type empty;
      }
    }
    //line * / domain-lookup
    leaf domain-lookup {
      description
        "Enable domain lookups in show commands";
      type empty;
    }
    //line * /editing
    leaf editing {
      description
        "Enable command line editing";
      type empty;
    }
    // line * / escape-character
    container escape-character {
      description
        "Change the current line's escape character";
      tailf:cli-compact-syntax;
      leaf char {
        tailf:cli-drop-node-name;
        type union {
          type uint8;
          type enumeration {
            enum "BREAK";
            enum "DEFAULT";
            enum "NONE";
          }
          type string;
        }
      }
      leaf soft {
        type empty;
      }
    }
    // line * / exec
    choice exec-choice {
      container no-exec {
        tailf:cli-drop-node-name;
        leaf exec {
          description
            "Configure EXEC";
          tailf:cli-boolean-no;
          tailf:cli-trim-default;
          type boolean;
        }
      }
      container exec {
        tailf:cli-incomplete-command;
        tailf:cli-incomplete-no;
        container prompt {
          leaf timestamp {
            type empty;
          }
        }
      }
    }
    // line * / exec-banner
    leaf exec-banner {
      description
        "Enable the display of the EXEC banner";
      type empty;
    }
    // line * /exec-character-bits
    leaf exec-character-bits {
      description
        "Bits per character";
      type uint8 {
        range "7..8";
      }
    }
    // line * / exec-timeout
    container exec-timeout {
      description
        "Set the EXEC timeout";
      tailf:cli-sequence-commands;
      tailf:cli-compact-syntax;
      leaf minutes {
        description
          "<0-35791>;;Timeout in minutes";
        tailf:cli-drop-node-name;
        type uint32;
      }
      leaf seconds {
        description
          "<0-2147483>;;Timeout in seconds";
        tailf:cli-drop-node-name;
        type uint32;
      }
    }
    // line * / flowcontrol
    container flowcontrol {
      description
        "Set the flow control";
      leaf NONE {
        description
          "Set no flow control";
        type empty;
      }
      leaf hardware {
        description
          "Set hardware flow control";
        type empty;
      }
      leaf software {
        description
          "Set software flow control";
        type empty;
      }
    }
    // line * / full-help
    leaf full-help {
      description
        "Provide help to unprivileged user";
      type empty;
    }
    // line * / history
    container history {
      description
        "Enable and control the command history function";
      presence "true";
      leaf size {
        description
          "Set history buffer size";
        type uint8;
      }
    }
    // line * / international
    leaf international {
      description
        "Enable international 8-bit character support";
      type empty;
    }
    // line * / ip
    container ip {
      description
        "IP options";
      container netmask-format {
        description
          "Change display of netmasks";
        presence "true";
        leaf format {
          tailf:cli-drop-node-name;
          type enumeration {
            enum "bit-count";
            enum "decimal";
            enum "hexadecimal";
          }
        }
      }
      leaf tcp {
        type empty;
      }
    }
    // line * / ipv6
    container ipv6 {
      leaf access-class {
        type empty;
      }
    }
    // line * / length
    leaf length {
      description
        "Set number of lines on a screen";
      type uint16 {
        range "0..512";
      }
    }
    // line * / line
    leaf line {
      type uint8;
    }
    // line * / location
    leaf location {
      description
        "One text line describing the terminal's location";
      tailf:cli-multi-value;
      type string;
    }
    // line * / logging
    container logging {
      description
        "Modify message logging facilities";
      container synchronous {
        description
          "Synchronized message output";
        presence "true";
      }
    }
    // line * / login
    container login {
      description
        "Enable password checking";
      tailf:cli-delete-when-empty;
      presence "true";
      leaf local {
        type empty;
      }
      leaf authentication {
        type string;
      }
    }
    // line * / media-type
    container media-type {
      description
        "Console connection media type";
      leaf rj45 {
        description
          "Console connection set to RJ45";
        type empty;
      }
    }
    // line * / modem
    container modem {
      description
        "Configure the Modem Control Lines";
      leaf CTS-Alarm {
        description
          "Alarm device which only uses CTS for call control";
        type empty;
      }
      leaf DTR-active {
        description
          "Leave DTR low unless line has an active incoming connection or EXEC";
        type empty;
      }
      leaf Dialin {
        description
          "Configure line for a modern dial-in modem";
        type empty;
      }
      leaf Host {
        description
          "Devices that expect an incoming modem call";
        type empty;
      }
      leaf InOut {
        description
          "Configure line for incoming AND outgoing use of modem";
        type empty;
      }
      leaf Printer {
        description
          "Devices that require DSR/CD active";
        type empty;
      }
      leaf answer-timeout {
        description
          "Set interval between raising DTR and CTS response";
        type empty;
      }
      leaf dtr-delay {
        description
          "Set interval during which DTR is held low";
        type empty;
      }
    }
    // line * / monitor
    leaf monitor {
      description
        "Copy debug output to the current terminal line";
      type empty;
    }
    // line * / motd-banner
    leaf motd-banner {
      description
        "Enable the display of the MOTD banner";
      type empty;
    }
    // line * / notify
    leaf notify {
      description
        "Inform users of output from concurrent sessions";
      type empty;
    }
    // line * / padding
    container padding {
      description
        "Set padding for a specified output character";
      tailf:cli-compact-syntax;
      tailf:cli-sequence-commands;
      leaf character {
        tailf:cli-drop-node-name;
        description
          "Character to be padded";
        type union {
          type uint8 {
            range "0..127";
          }
          type string;
        }
      }
      leaf null {
        tailf:cli-drop-node-name;
        type uint8;
      }
    }
    // line * / parity
    container parity {
      description
        "Set terminal parity";
      leaf even {
        description
          "Even parity";
        type empty;
      }
      leaf mark {
        description
          "Mark parity";
        type empty;
      }
      leaf none {
        description
          "No parity";
        type empty;
      }
      leaf odd {
        description
          "Odd parity";
        type empty;
      }
      leaf space {
        description
          "Space parity";
        type empty;
      }
    }
    // line * / password
    container password {
      description
        "Set a password";
      tailf:cli-compact-syntax;
      tailf:cli-sequence-commands;
      uses password-07-grouping;
    }
    // line * / prc
    container prc {
      description
        "PRC commands";
      leaf expose {
        description
          "Expose PRC data";
        type empty;
      }
      leaf hide {
        description
          "Hide PRC data";
        type empty;
      }
    }
    // line * / privilege
    container privilege {
      description
        "Change privilege level for line";
      container level {
        description
          "Assign default privilege level for line";
        presence "true";
        leaf number {
          tailf:cli-drop-node-name;
          type uint8 {
            range "0..15";
          }
        }
      }
    }
    // line * / refuse-message
    leaf refuse-message {
      tailf:cli-multi-value;
      description
        "c refuse-text c, where 'c' is a delimiting character";
      type string;
    }
    // line * / rotary
    leaf rotary {
      description
        "Rotary group to add line to";
      type uint8 {
        range "1..99";
      }
    }
    // line * / rxspeed
    leaf rxspeed {
      description
        "Receive speed";
      type uint32 {
        range "0..4294967295";
      }
    }
    // line * / session-timeout
    container session-timeout {
      description
        "Set interval for closing connection when there is no input traffic";
      tailf:cli-sequence-commands;
      tailf:cli-compact-syntax;
      leaf session-timeout-value {
        tailf:cli-drop-node-name;
        type uint16 {
          range "0..35791";
        }
      }
      leaf output {
        description
          "Include output traffic as well as input traffic";
        type empty;
      }
    }
    // line * / special-character-bits
    leaf special-character-bits {
      description
        "Bits per character";
      type uint8 {
        range "7..8";
      }
    }
    // line * / speed
    leaf speed {
      description
        "Transmit and receive speeds";
      type uint32 {
        range "0..4294967295";
      }
    }
    // line * / start-character
    leaf start-character {
      description
        "Define the start character";
      type union {
        type uint8;
        type string;
      }
    }
    // line * / stop-character
    leaf stop-character {
      description
        "Define the stop character";
      type union {
        type uint8;
        type string;
      }
    }
    // line * / stopbits
    leaf stopbits {
      description
        "Set async line stop bits";
      type enumeration {
        enum "1";
        enum "1.5";
        enum "2";
      }
    }
    // line * / terminal-type
    leaf terminal-type {
      description
        "Terminal type";
      type string;
    }
    // line * / timeout
    container timeout {
      description
        "Timeouts for the line";
      leaf login {
        description
          "Timeouts related to the login sequence";
        type empty;
      }
    }
    // line * / telnet
    container telnet {
      description
        "Telnet protocol-specific configuration";
      leaf transparent {
        description
          "Send a CR as a CR followed by a NULL instead of a CR followed by a LF";
        type empty;
      }
    }
    // line * / transport
    container transport {
      description
        "Define transport protocols for line";
      tailf:cli-incomplete-no;
      // line * / transport input
      container input {
        leaf-list input {
          description
            "Define which protocols to use when connecting to the terminal server";
          ordered-by user;
          tailf:cli-drop-node-name;
          tailf:cli-flat-list-syntax;
          tailf:cli-no-value-on-delete;
          type enumeration {
            enum "acercon";
            enum "all";
            enum "lapb-ta";
            enum "lat";
            enum "mop";
            enum "nasi";
            enum "none";
            enum "pad";
            enum "rlogin";
            enum "ssh";
            enum "telnet";
            enum "udptn";
            enum "v120";
          }
        }
      }
      // line * / transport output
      container output {
        leaf-list output {
          description
            "Define which protocols to use for outgoing connections";
          ordered-by user;
          tailf:cli-drop-node-name;
          tailf:cli-flat-list-syntax;
          tailf:cli-no-value-on-delete;
          type enumeration {
            enum "acercon";
            enum "all";
            enum "lapb-ta";
            enum "lat";
            enum "mop";
            enum "nasi";
            enum "none";
            enum "pad";
            enum "rlogin";
            enum "ssh";
            enum "telnet";
            enum "udptn";
            enum "v120";
          }
        }
      }
      // line * / transport preferred
      container preferred {
        description
          "Specify the preferred protocol to use";
        presence "true";
        leaf protocol {
	  tailf:cli-no-value-on-delete;
          tailf:cli-drop-node-name;
          tailf:cli-delete-container-on-delete;
          type enumeration {
            enum "acercon";
            enum "lat";
            enum "mop";
            enum "nasi";
            enum "none";
            enum "pad";
            enum "rlogin";
            enum "ssh";
            enum "telnet";
            enum "udptn";
          }
        }
      }
    }
    // line * / txspeed
    leaf txspeed {
      description
        "Transmit speed";
      type uint32;
    }
    // line * / usb-inactivity-timeout
    container usb-inactivity-timeout {
      description
        "Inactivity timeout for USB media type";
      leaf switch {
        description
          "Switch Number";
        type empty;
      }
    }
    // line * / vacant-message
    container vacant-message {
      description
        "Define a vacant banner";
      presence "true";
      leaf banner {
        tailf:cli-multi-value;
        description
          "c vacant-text c, where 'c' is a delimiting character";
        tailf:cli-drop-node-name;
        type string;
      }
    }
    // line * / width
    leaf width {
      description
        "Number of characters on a screen line";
      type uint16 {
        range "0..512";
      }
    }
  }

  grouping queue-size-grouping {
    leaf queue-size-1 {
      tailf:cli-drop-node-name;
      type uint8 {
        range "1..100";
      }
    }
    leaf queue-size-2 {
      tailf:cli-drop-node-name;
      type uint8 {
        range "1..100";
      }
    }
    leaf queue-size-3 {
      tailf:cli-drop-node-name;
      type uint8 {
        range "1..100";
      }
    }
    leaf queue-size-4 {
      tailf:cli-drop-node-name;
      type uint8 {
        range "1..100";
      }
    }
    leaf queue-size-5 {
      tailf:cli-drop-node-name;
      type uint8 {
        range "1..100";
      }
    }
    leaf queue-size-6 {
      tailf:cli-drop-node-name;
      type uint8 {
        range "1..100";
      }
    }
    leaf queue-size-7 {
      tailf:cli-drop-node-name;
      type uint8 {
        range "1..100";
      }
    }
    leaf queue-size-8 {
      tailf:cli-drop-node-name;
      type uint8 {
        range "1..100";
      }
    }
  }

  grouping authentication-ipsec-grouping {
    container ipsec {
      description
        "Use IPsec authentication";
      leaf spi {
        description
          "Set the SPI (Security Parameters Index)";
        tailf:cli-incomplete-command;
        type uint64 {
          range "256..4294967295";
        }
      }
      container md5 {
        description
          "Use MD5 authentication";
        container key-string {
          tailf:cli-drop-node-name;
          tailf:cli-compact-syntax;
          leaf encrypt {
            tailf:cli-drop-node-name;
            type enumeration {
              enum "0";
              enum "7";
            }
          }
          leaf string {
            tailf:cli-drop-node-name;
            type string;
          }
        }
      }
      container sha1 {
        description
          "Use SHA-1 authentication";
        container key-string {
          tailf:cli-drop-node-name;
          tailf:cli-compact-syntax;
          leaf encrypt {
            tailf:cli-drop-node-name;
            type enumeration {
              enum "0";
              enum "7";
            }
          }
          leaf string {
            tailf:cli-drop-node-name;
            type string;
          }
        }
      }
    }
  }

  grouping interface-xconnect-grouping {
    choice xconnect-choice {
      // interface * / xconnect encapsulation
      container xconnect {
        tailf:cli-add-mode;
        tailf:cli-mode-name "config-if-xconn";
        tailf:cli-compact-syntax;
        tailf:cli-sequence-commands;
        tailf:cli-incomplete-command;
        leaf address {
          tailf:cli-drop-node-name;
          tailf:cli-incomplete-command;
          tailf:cli-hide-in-submode;
          type inet:ipv4-address;
        }
        leaf vcid {
          tailf:cli-drop-node-name;
          tailf:cli-incomplete-command;
          tailf:cli-hide-in-submode;
          type uint32 {
            range "1..4294967295";
          }
        }
        leaf encapsulation {
          description
            "Data encapsulation method";
          tailf:cli-hide-in-submode;
          type enumeration {
            enum "mpls";
            enum "l2tpv3";
          }
        }
        leaf manual {
          description
            "Manually configure L2TP session parameters";
          tailf:cli-optional-in-sequence;
          tailf:cli-hide-in-submode;
          type empty;
        }
        leaf pw-class {
          description
            "Optional pseudowire-class to use for advanced configuration";
          tailf:cli-optional-in-sequence;
          tailf:cli-hide-in-submode;
          type string;
        }
        leaf sequencing {
          description
            "Configure sequencing options for xconnect";
          tailf:cli-full-command;
          tailf:cli-hide-in-submode;
          when "../encapsulation = 'l2tpv3'";
          type enumeration {
            enum "both";
            enum "receive";
            enum "transmit";
          }
        }
        // interface * / xconnect encapsulation / backup peer
        container backup {
          tailf:cli-break-sequence-commands;
          description
            "Xconnect backup configuration commands";
          container peer {
            description
              "Backup pseudowire";
            tailf:cli-compact-syntax;
            tailf:cli-sequence-commands {
              tailf:cli-reset-siblings;
            }
            leaf peer-router-ip-addr {
              tailf:cli-drop-node-name;
              tailf:cli-incomplete-command;
              type inet:ipv4-address;
            }
            leaf vcid {
              tailf:cli-drop-node-name;
              type uint32 {
                range "1..4294967295";
              }
            }
            leaf pw-class {
              tailf:cli-optional-in-sequence;
              type string;
            }
            leaf priority {
              description
                "Optional priority to use for backup pseudowire.";
              type uint8 {
                range "1..10";
              }
            }
          }
          container delay {
            description
              "backup delay time";
            tailf:cli-compact-syntax;
            tailf:cli-sequence-commands {
              tailf:cli-reset-siblings;
            }
            leaf min {
              tailf:cli-drop-node-name;
              type uint32;
            }
            leaf max {
              tailf:cli-drop-node-name;
              type uint32;
            }
          }
        }
        leaf mtu {
          type uint32;
        }
      }
      //interface * / xconnect pw-class
      container xconnect-pw-class {
        tailf:cli-drop-node-name;
        container xconnect {
          description
            "Xconnect commands";
          tailf:cli-add-mode;
          tailf:cli-mode-name "config-if-xconn";
          tailf:cli-sequence-commands;
          tailf:cli-compact-syntax;
          leaf address {
            tailf:cli-drop-node-name;
            tailf:cli-incomplete-command;
            tailf:cli-hide-in-submode;
            type inet:ipv4-address;
          }
          leaf vcid {
            tailf:cli-drop-node-name;
            tailf:cli-incomplete-command;
            tailf:cli-hide-in-submode;
            type uint32 {
              range "1..4294967295";
            }
          }
          leaf pw-class {
            description
              "Pseudowire-class to use for encapsulation and protocol configuration";
            tailf:cli-full-command;
            tailf:cli-hide-in-submode;
            type string;
          }
          container udp {
            description
              "UDP";
            container port {
              description
                "UDP ports";
              tailf:cli-compact-syntax;
              leaf local {
                type uint32;
              }
              leaf remote {
                type uint32;
              }
            }
          }
        }
      }
    }
  }

  grouping interface-atm-grouping {
    container ip {
      description
        "IP address";
      leaf address {
        type inet:ipv4-address;
      }
    }
    container atm {
      description
        "ATM";
      leaf bandwidth {
        description
          "ATM bandwith";
        type enumeration {
          enum "dynamic";
        }
      }
      leaf enable-ilmi-trap {
        description
          "Enable-ilmi-trap";
        tailf:cli-boolean-no;
        tailf:cli-trim-default;
        type boolean;
      }
      list pvp {
        description
          "PVP";
        tailf:cli-mode-name "config-if-atm-pvp";
        key "pvp-number";
        leaf pvp-number {
          description
            "PVP number";
          type uint16;
        }
        leaf l2transport {
          tailf:cli-hide-in-submode;
          type empty;
        }
        uses interface-xconnect-grouping;
      }
    }
    leaf load-interval {
      description
        "Load interval";
      type uint32;
    }
    list cem {
      description
        "CEM";
      tailf:cli-mode-name "config-if-cem";
      key "number";
      leaf number {
        type uint32;
      }
      uses interface-xconnect-grouping;
    }
    list pvc {
      description
        "PVC";
      tailf:cli-mode-name "config-if-pvc";
      key "local-vpi-vci";
      leaf local-vpi-vci {
        description
          "Vpi and vci";
        type string;
      }
      leaf remote-vpi-vci {
        description
          "Vpi and vci";
        tailf:cli-hide-in-submode;
        tailf:cli-drop-node-name;
        type string;
      }
      leaf l2transport {
        tailf:cli-hide-in-submode;
        type empty;
      }
      leaf ubr {
        description
          "UBR";
        type uint32;
      }
      uses interface-xconnect-grouping;
    }
  }

  grouping sonet-grouping {
    leaf framing {
      description
        "SONET framing";
      type enumeration {
        enum "sonet";
        enum "sdh";
      }
    }
    leaf shutdown {
      type empty;
    }
    container clock {
      description
        "SONET clock";
      leaf source {
        description
          "SONET clock source";
        type enumeration {
          enum "internal";
          enum "line";
        }
      }
    }
    container aug {
      description
        "AUG";
      leaf mapping {
        type enumeration {
          enum "au-3";
          enum "au-4";
        }
      }
    }
    list au-3 {
      description
        "AU-3";
      tailf:cli-mode-name "config-au3Path";
      key "number";
      leaf number {
        description
          "AU-3 number";
        type int8 {
          range "1..3";
        }
      }
      container overhead {
        description
          "overhead";
        tailf:cli-no-keyword;
        tailf:cli-sequence-commands;
        tailf:cli-compact-syntax;
        leaf byte {
          tailf:cli-drop-node-name;
          type enumeration {
            enum "j1";
          }
        }
        leaf length {
          type uint8;
        }
      }
      container mode {
        description
          "mode";
        tailf:cli-no-keyword;
        tailf:cli-sequence-commands;
        tailf:cli-compact-syntax;
        leaf mapping {
          tailf:cli-drop-node-name;
          type enumeration {
            enum "c-11";
            enum "c-12";
            enum "c-2";
          }
        }
      }
    }
    container au-4-atm {
      tailf:cli-drop-node-name;
      container au-4 {
        description
          "AU-4";
        tailf:cli-compact-syntax;
        tailf:cli-sequence-commands;
        leaf number {
          description
            "AU-4 number";
          tailf:cli-drop-node-name;
          type int8 {
            range "1..3";
          }
        }
        leaf atm {
          type empty;
        }
      }
    }
    list au-4 {
      description
        "AU-4";
      tailf:cli-mode-name "config-au4Path";
      key "number tug-3";
      leaf number {
        description
          "AU-4 number";
        type int8 {
          range "1..3";
        }
      }
      leaf tug-3 {
        description
          "TUG-3";
        tailf:cli-expose-key-name;
        type int8 {
          range "1..3";
        }
      }
      leaf mode {
        description
          "mode";
        type enumeration {
          enum "c-11";
          enum "c-12";
          enum "c-2";
          enum "c-3";
          enum "c-4";
          enum "e3";
        }
      }
      leaf cem-group {
        description
          "CEM group";
        type int32;
      }
      choice framing-choice {
        case unframed-case {
          leaf unframed {
            description
              "Unframed";
            type empty;
          }
        }
        case framing-case {
          leaf framing {
            type enumeration {
              enum "unframed";
            }
          }
        }
      }
      container cem-group-timeslots {
        tailf:cli-drop-node-name;
        list tug-2 {
          description
            "TUG-2";
          tailf:cli-suppress-mode;
          tailf:cli-compact-syntax;
          tailf:cli-sequence-commands;
          key "number e1 cem-group";
          leaf number {
            description
              "TUG-2 number";
            type int8 {
              range "1..7";
            }
          }
          leaf e1 {
            description
              "E1";
            tailf:cli-expose-key-name;
            type int8 {
              range "1..3";
            }
          }
          leaf cem-group {
            description
              "CEM group";
            tailf:cli-expose-key-name;
            type int32;
          }
          leaf timeslots {
            description
              "Time slots";
            type string;
          }
        }
      }
      container channel-group-timeslots {
        tailf:cli-drop-node-name;
        list tug-2 {
          description
            "TUG-2";
          tailf:cli-suppress-mode;
          tailf:cli-compact-syntax;
          tailf:cli-sequence-commands;
          key "number e1 channel-group";
          leaf number {
            description
              "TUG-2 number";
            type int8 {
              range "1..7";
            }
          }
          leaf e1 {
            description
              "E1";
            tailf:cli-expose-key-name;
            type int8 {
              range "1..3";
            }
          }
          leaf channel-group {
            description
              "Channel group";
            tailf:cli-expose-key-name;
            type int32;
          }
          leaf timeslots {
            description
              "Time slots";
            type string;
          }
        }
      }
      container cem-group-unframed {
        tailf:cli-drop-node-name;
        list tug-2 {
          description
            "TUG-2";
          tailf:cli-suppress-mode;
          tailf:cli-compact-syntax;
          tailf:cli-sequence-commands;
          key "number e1 cem-group";
          leaf number {
            description
              "TUG-2 number";
            type int8 {
              range "1..7";
            }
          }
          leaf e1 {
            description
              "E1";
            tailf:cli-expose-key-name;
            type int8 {
              range "1..3";
            }
          }
          leaf cem-group {
            tailf:cli-expose-key-name;
            description
              "CEM group";
            type int32;
          }
          leaf unframed {
            description
              "Unframed";
            type empty;
          }
        }
      }
      container framing-unframed {
        tailf:cli-drop-node-name;
        list tug-2 {
          description
            "TUG-2";
          tailf:cli-suppress-mode;
          tailf:cli-compact-syntax;
          tailf:cli-sequence-commands;
          key "number e1";
          leaf number {
            description
              "TUG-2 number";
            type int8 {
              range "1..7";
            }
          }
          leaf e1 {
            description
              "E1";
            tailf:cli-expose-key-name;
            type int8 {
              range "1..3";
            }
          }
          leaf framing {
            type enumeration {
              enum "unframed";
            }
          }
        }
      }
      container cem-group-atm {
        tailf:cli-drop-node-name;
        list tug-2 {
          description
            "TUG-2";
          tailf:cli-suppress-mode;
          tailf:cli-compact-syntax;
          tailf:cli-sequence-commands;
          key "number e1";
          leaf number {
            description
              "TUG-2 number";
            type int8 {
              range "1..7";
            }
          }
          leaf e1 {
            description
              "E1";
            tailf:cli-expose-key-name;
            type int8 {
              range "1..3";
            }
          }
          leaf atm {
            type empty;
          }
        }
      }
      container ima-group {
        tailf:cli-drop-node-name;
        list tug-2 {
          description
            "TUG-2";
          tailf:cli-suppress-mode;
          tailf:cli-compact-syntax;
          tailf:cli-sequence-commands;
          key "number e1 ima-group";
          leaf number {
            description
              "TUG-2 number";
            type int8 {
              range "1..7";
            }
          }
          leaf e1 {
            description
              "E1";
            tailf:cli-expose-key-name;
            type int8 {
              range "1..3";
            }
          }
          leaf ima-group {
            tailf:cli-expose-key-name;
            description
              "IMA group";
            type int32;
          }
        }
      }
    }
    container aps {
      description
        "SONET APS";
      container group {
        description
          "SONET APS group";
        leaf group-number {
          tailf:cli-drop-node-name;
          type uint8;
        }
        leaf acr {
          description
            "ACR";
          type int8;
        }
      }
      leaf working {
        description
          "Working line";
        type int8;
      }
      container protect {
        description
          "Protect line";
        tailf:cli-compact-syntax;
        leaf number {
          tailf:cli-drop-node-name;
          type int8;
        }
        leaf ip-addr {
          tailf:cli-drop-node-name;
          type inet:ipv4-address;
        }
      }
      leaf hspw-icrm-grp {
        type uint8;
      }
      container interchassis {
        leaf group {
          type uint8;
        }
      }
    }
  }

  grouping interface-ospf-encryption-grouping {
    container encryption {
      description
        "Enable encryption";
      leaf null {
        description
          "No IPsec encryption on this interface";
        type empty;
      }
      container ipsec {
        description
          "Use IPsec encryption";
        tailf:cli-sequence-commands;
	tailf:cli-compact-syntax;
        leaf spi {
          description
            "Set the SPI (Security Parameters Index)";
          type uint64;
        }
        leaf esp {
          description
            "Use ESP encapsulation";
          type empty;
        }
        container ipsec_3des {
          tailf:alt-name "3des";
          description
            "Use 3DES encryption";
          tailf:cli-optional-in-sequence;
          container key-string {
            tailf:cli-drop-node-name;
            tailf:cli-compact-syntax;
            leaf encrypt {
              tailf:cli-drop-node-name;
              type enumeration {
                enum "0";
                enum "7";
              }
            }
            leaf string {
              tailf:cli-drop-node-name;
              type string;
            }
          }
        }
        container aes-cbc {
          description
            "Use AES-CBC encryption";
          tailf:cli-optional-in-sequence;
          container aes-cbc-128 {
            tailf:alt-name "128";
            description
              "Use 128 bit key";
            container key-string {
              tailf:cli-drop-node-name;
              tailf:cli-compact-syntax;
              leaf encrypt {
                tailf:cli-drop-node-name;
                type enumeration {
                  enum "0";
                  enum "7";
                }
              }
              leaf string {
                tailf:cli-drop-node-name;
                type string;
              }
            }
          }
          container aes-192 {
            tailf:alt-name "192";
            description
              "Use 192 bit key";
            container key-string {
              tailf:cli-drop-node-name;
              tailf:cli-compact-syntax;
              leaf encrypt {
                tailf:cli-drop-node-name;
                type enumeration {
                  enum "0";
                  enum "7";
                }
              }
              leaf string {
                tailf:cli-drop-node-name;
                type string;
              }
            }
          }
          container aes-256 {
            tailf:alt-name "256";
            description
              "Use 256 bit key";
            container key-string {
              tailf:cli-drop-node-name;
              tailf:cli-compact-syntax;
              leaf encrypt {
                tailf:cli-drop-node-name;
                type enumeration {
                  enum "0";
                  enum "7";
                }
              }
              leaf string {
                tailf:cli-drop-node-name;
                type string;
              }
            }
          }
        }
      }
    }
  }

  grouping interface-ospf-neighbor-grouping {
    list neighbor {
      description
        "OSPF neighbor";
      tailf:cli-suppress-mode;
      tailf:cli-delete-when-empty;
      tailf:cli-incomplete-command;
      ordered-by user;
      must "count(*) > 1" {
        tailf:dependency ".";
      }
      key "id";
      leaf id {
        type inet:ipv6-address;
      }
      leaf cost {
        description
          "OSPF cost for point-to-multipoint neighbor";
        type uint16 {
          range "1..65535";
        }
      }
      container database-filter {
        description
          "Filter OSPF LSA during synchronization and flooding for point-to-multipoint neighbor";
        choice database {
          leaf all {
            description
              "Filter all LSA";
            type enumeration {
              enum "out";
            }
          }
        }
      }
      leaf poll-interval {
        description
          "OSPF dead-router polling interval";
        type uint32 {
          range "0..65535";
        }
      }
      leaf priority {
        description
          "OSPF priority of non-broadcast neighbor";
        type uint8 {
          range "0..255";
        }
      }
    }
  }

  grouping interface-ospf-network-grouping {
    container network {
      description
        "Network type";
      leaf broadcast {
        description
          "Specify OSPF broadcast multi-access network";
        tailf:cli-full-command;
        type empty;
      }
      leaf manet {
        description
          "Specify MANET OSPF interface type";
        tailf:cli-full-command;
        type empty;
      }
      leaf non-broadcast {
        description
          "Specify OSPF NBMA network";
        tailf:cli-full-command;
        type empty;
      }
      container point-to-multipoint {
        description
          "Specify OSPF point-to-multipoint network";
        presence "true";
        leaf non-broadcast {
          description
            "Specify non-broadcast point-to-mpoint network";
          type empty;
        }
      }
      leaf point-to-point {
        description
          "Specify OSPF point-to-point network";
        tailf:cli-full-command;
        type empty;
      }
    }
  }

  grouping interface-ospf-prefix-suppression-grouping {
    container prefix-suppression {
      description
        "OSPF prefix suppression";
      presence "true";
      leaf disable {
        description
          "Disable prefix suppression";
        type empty;
      }
    }
  }

  grouping interface-ospf-priority-grouping {
    leaf priority {
      description
        "Router priority";
      type uint8 {
        range "0..255";
      }
    }
  }

  grouping interface-ospf-retransmit-interval-grouping {
    leaf retransmit-interval {
      description
        "Time between retransmitting lost link state advertisements";
      type uint32 {
        range "1..65535";
      }
    }
  }

  grouping interface-ospf-transmit-delay-grouping {
    leaf transmit-delay {
      description
        "Link state transmit delay";
      type uint32 {
        range "1..65535";
      }
    }
  }

  grouping interface-ospf-bfd-grouping {
    container bfd {
      description
        "Enable BFD on this interface";
      presence "true";
      leaf disable {
        description
          "Disable BFD on this interface";
        type empty;
      }
    }
  }

  grouping interface-ospfv3-cost-grouping {
    container cost {
      description
        "Route cost of this interface";
      leaf value {
        tailf:cli-full-command;
        tailf:cli-drop-node-name;
        type uint32 {
          range "1..65535";
        }
      }
      container dynamic {
        description
          "Specify dynamic cost options";
        presence "true";
        leaf default {
          description
            "Specify default link metric value";
          type uint32 {
            range "0..65535";
          }
        }
        container hysteresis {
          description
            "Specify hysteresis value for LSA dampening";
          presence "true";
          leaf percent {
            description
              "Specify hysteresis percent changed";
            tailf:cli-full-command;
            type uint8 {
              range "1..100";
            }
          }
          leaf threshold {
            description
              "Specify hysteresis threshold value";
            tailf:cli-full-command;
            type uint32 {
              range "0..65535";
            }
          }
        }
        container weight {
          description
            "Specify weight to be placed on individual metrics";
          container L2-factor {
            description
              "Specify weight to be given to L2-factor metric";
            presence "true";
            leaf value {
              tailf:cli-drop-node-name;
              type uint8 {
                range "0..100";
              }
            }
          }
          container latency {
            description
              "Specify weight to be given to latency metric";
            presence "true";
            leaf value {
              tailf:cli-drop-node-name;
              type uint8 {
                range "0..100";
              }
            }
          }
          container resources {
            description
              "Specify weight to be given to resources metric";
            presence "true";
            leaf value {
              tailf:cli-drop-node-name;
              type uint8 {
                range "0..100";
              }
            }
          }
          container throughput {
            description
              "Specify weight to be given to throughput metric";
            presence "true";
            leaf value {
              tailf:cli-drop-node-name;
              type uint8 {
                range "0..100";
              }
            }
          }
        }
      }
    }
  }

  grouping interface-ospf-dead-interval-grouping {
    leaf dead-interval {
      description
        "Interval after which a neighbor is declared dead";
      type uint16 {
        range "1..65535";
      }
    }
  }

  grouping interface-ospf-hello-interval-grouping {
    leaf hello-interval {
      description
        "Time between HELLO packets";
      type uint32 {
        range "1..65535";
      }
    }
  }

  grouping interface-ospfv3-manet-grouping {
    container manet {
      description
        "Mobile Adhoc Networking options";
      container peering {
        description
          "MANET Peering options";
        container cost {
          description
            "Redundant path cost improvement required to peer";
          leaf percent {
            description
              "Relative incremental path cost";
            tailf:cli-full-command;
            type uint8 {
              range "0..100";
            }
          }
          leaf threshold {
            description
              "Absolute incremental path cost";
            tailf:cli-full-command;
            type uint32 {
              range "0..65535";
            }
          }
        }
        leaf link-metrics {
          description
            "Require link metrics";
          type uint32 {
            range "0..65535";
          }
        }
      }
    }
  }

  grouping interface-ospfv3-process-id-grouping {
    // interface * / ospfv3 * authentication
    container authentication {
      description
        "Enable authentication";
      leaf key-chain {
        description
          "Use a key-chain for cryptographic authentication keys";
        tailf:cli-full-command;
        type string;
      }
      leaf null {
        tailf:cli-full-command;
        description
          "Use no authentication";
        type empty;
      }
    }
    // interface * / ospfv3 * bfd
    uses interface-ospf-bfd-grouping;
    // interface * / ospfv3 * cost
    uses interface-ospfv3-cost-grouping;
    // interface * / ospfv3 * database-filter
    container database-filter {
      description
        "Filter OSPF LSA during synchronization and flooding";
      choice database {
        leaf all {
          description
            "Filter all LSA";
          type enumeration {
            enum "out";
          }
        }
        leaf disable {
          description
            "Disable LSA Filter on this interface";
          type empty;
        }
      }
    }
    // interface * / ospfv3 * dead-interval
    uses interface-ospf-dead-interval-grouping;
    // interface * / ospfv3 * demand-circuit
    container demand-circuit {
      description
        "OSPF demand circuit";
      presence "true";
      leaf disable {
        tailf:cli-full-command;
        description
          "Disable demand circuit on this interface";
        type empty;
      }
      leaf ignore {
        tailf:cli-full-command;
        description
          "Ignore demand circuit auto-negotiation requests";
        type empty;
      }
    }
    // interface * / ospfv3 * flood-reduction
    container flood-reduction {
      description
        "OSPF Flood Reduction";
      presence "true";
      leaf disable {
        type empty;
      }
    }
    // interface * / ospfv3 * hello-interval
    uses interface-ospf-hello-interval-grouping;
    // interface * / ospfv3 * manet
    uses interface-ospfv3-manet-grouping;
    // interface * / ospfv3 * mtu-ignore
    container mtu-ignore {
      description
        "Ignores the MTU in DBD packets";
      presence "true";
      leaf disable {
        description
          "Disable Ingore MTU on this interface";
        type empty;
      }
    }
    // interface * /  ospfv3 * multi-area
    container multi-area {
      description
        "Set the OSPF multi-area ID";
      tailf:cli-sequence-commands;
      tailf:cli-compact-syntax;
      leaf id {
        tailf:cli-drop-node-name;
        type union {
          type uint32 {
            range "0..4294967295";
          }
          type inet:ipv4-address;
        }
      }
      leaf cost {
        description
          "Interface cost";
        tailf:cli-optional-in-sequence;
        tailf:cli-full-command;
        type uint32 {
          range "1..65535";
        }
      }
      leaf disable {
        description
          "disable OSPF multi-area";
        tailf:cli-optional-in-sequence;
        tailf:cli-full-command;
        type empty;
      }
    }
    // interface * /  ospfv3 * neighbor
    uses interface-ospf-neighbor-grouping;
    // interface * /  ospfv3 * network
    uses interface-ospf-network-grouping;
    // interface * / ospfv3 * prefix-suppression
    uses interface-ospf-prefix-suppression-grouping;
    // interface * /  ospfv3 * priority
    uses interface-ospf-priority-grouping;
    // interface * /  ospfv3 * retransmit-interval
    uses interface-ospf-retransmit-interval-grouping;
    // interface * / ospfv3 * shutdown
    container shutdown {
      description
        "Shut down the interface in OSPFv3";
      presence "true";
      leaf disable {
        description
          "Disable inherited shutdown";
        type empty;
      }
    }
    // interface * / ospfv3 * transmit-delay
    uses interface-ospf-transmit-delay-grouping;
  }

  grouping interface-ip-monitor-grouping {
    list monitor {
      description
        "Apply a Flow Monitor";
      tailf:cli-suppress-mode;
      key "name";
      leaf name {
        description
          "User defined";
        tailf:cli-disallow-value "input|multicast|output|sampler|unicast";
        type string;
      }
      list sampler {
        description
          "Optional Sampler to apply to this Flow Monitor";
        tailf:cli-suppress-mode;
        key direction;
        leaf direction {
          description
            "Apply Flow Monitor on input/output traffic";
          type enumeration {
            enum input;
            enum output;
          }
        }
        leaf name {
          description
            "User defined";
          tailf:cli-drop-node-name;
          tailf:cli-prefix-key;
          tailf:cli-disallow-value "input|output";
          type string;
        }
      }
      leaf input {
        description
          "Apply Flow Monitor on input traffic";
        type empty;
      }      
      leaf output {
        description
          "Apply Flow Monitor on input traffic";
        type empty;
      }
      leaf multicast {
        type empty;
      }
      leaf unicast {
        type empty;
      }      
    }
  }

  grouping interface-ip-wccp-group-listen-grouping {
    leaf group-listen {
      description
        "Listen for multicasted WCCP protocol packets";
      tailf:cli-full-command;
      type empty;
    }
    container redirect {
      description
        "Set packet redirection options for the service";
      leaf in {
        description
          "Redirect to a Cache Engine appropriate inbound packets";
        tailf:cli-full-command;
        type empty;
      }
      leaf out {
        description
          "Redirect to a Cache Engine appropriate outbound packets";
        tailf:cli-full-command;
        type empty;
      }
    }
  }

  grouping interface-ip-wccp-grouping {
    list wccp-list {
      tailf:cli-drop-node-name;
      tailf:cli-suppress-mode;
      key "id";
      leaf id {
        type uint8 {
          range "0..254";
        }
      }
      uses interface-ip-wccp-group-listen-grouping;
    }
    container web-cache {
      description
        "Standard web caching service";
      uses interface-ip-wccp-group-listen-grouping;
    }
  }

  grouping interface-common-grouping {

    // interface cemoudp * /  
    container cemoudp {
      description
        "cemoudp";
      container reserve {
        leaf acr {
          type uint8;
        }
      }
    }
    
    // interface * / cts 
    container cts {
      description 
        "Configure Cisco Trusted Security";
      container manual {
        description 
	      "Supply local configuration for CTS parameters";
        presence true;  
        tailf:cli-add-mode;
        container policy {
          description 
	        "CTS policy for manual mode";
          container static {
            description 
	          "Configure policy to be applied on the link";
            tailf:cli-compact-syntax;
            tailf:cli-sequence-commands;  
            leaf sgt {
              description 
	            "Source Security Group Tag to apply to untagged or non-trusted incoming traffic";
              type uint16 {
                range "2..65519";
              }
            }
            leaf trusted {
              description 
                "Trust the Source Group Tags (SGT) that the peer uses for sending";
              type empty;
            }
          }
        }
        container sap {
          description 
	    "CTS SAP configuration for manual mode";
          list pmk {
            tailf:cli-suppress-mode;
            description 
	      "Pre-Master Key (PMK) to use for CTS SAP";
            key "word";
            leaf word {
              type string;
            }
	    container mode-list {
	      description
	        "List of advertised modes (prioritized from highest to lowest)";
              container gcm-encrypt {
	        description 
		  "GCM authentication, GCM encryption";
                presence true;
	        container gmac {
	          description 
		    "GCM authentication, no encryption";
                  presence true;
	          leaf null {
		    description 
		      "Encapsulation present, no authentication, no encryption";
	 	    type empty;
	          }
	        }
	      }  
	      container no-encap {
 	        description "No encapsulation";
                presence true;
		container gmac {
	 	  description
		    "GCM authentication, no encryption";
                  presence true;
		  leaf gcm-encrypt {
		    description
		      "GCM authentication, GCM encryption";
		    type empty;
		  }
		}
	      }  
            } 
          }  
        } 
        container propagate {
          description 
            "CTS SGT Propagation configuration for manual mode";
          leaf sgt {
            description 
              "CTS SGT Propagation configuration";
            tailf:cli-boolean-no;
            tailf:cli-full-command;
            type boolean;
          }
        }
      }
    }

    // interface * / crypto
    container crypto {
      description
        "Encryption/Decryption commands";
      container map {
        description
          "Assign a Crypto Map";
        tailf:cli-sequence-commands;
        tailf:cli-compact-syntax;
        leaf tag {
          tailf:cli-drop-node-name;
          type string;
        }
        leaf redundancy {
          description
            "enable redundancy";
          tailf:cli-optional-in-sequence;
          type string;
        }
        leaf stateful {
          description
            "enable stateful failover";
          tailf:cli-optional-in-sequence;
          type empty;
        }
      }
      container ipsec {
        description
          "Set IPSec parameters";
        leaf df-bit {
          description
            "Handling of encapsulated DF bit.";
          type enumeration {
            enum "clear";
            enum "copy";
            enum "set";
          }
        }
        leaf fragmentation {
          description
            "Handling of fragmentation of near-MTU sized packets";
          type enumeration {
            enum "after-encryption";
            enum "before-encryption";
          }
        }
      }
    }
    // interface * / crypto
    leaf description {
      description
        "Interface specific description";
      tailf:cli-multi-value;
      tailf:cli-full-command;
      type string {
        length "0..240";
      }
    }
    // interface * / mab
    container mab {
      presence "true";
      leaf eap {
        type empty;
      }
    }
    // interface * / l2protocol-tunnel
    container l2protocol-tunnel {
      description
        "Tunnel Layer2 protocols";
      tailf:cli-delete-when-empty;
      presence "true";
      leaf cdp {
        description
          "Cisco Discovery Protocol";
        type empty;
      }
      container drop-threshold {
        description
          "Set drop threshold for protocol packets";
        leaf packet-rate {
          tailf:cli-drop-node-name;
          type uint16 {
            range "1..4096";
          }
        }
        leaf cdp {
          description
            "Cisco Discovery Protocol";
          type uint16 {
            range "1..4096";
          }
        }
        leaf stp {
          description
            "Spanning Tree Protocol";
          type uint16 {
            range "1..4096";
          }
        }
        leaf vtp {
          description
            "Vlan Trunking Protocol";
          type uint16 {
            range "1..4096";
          }
        }
      }
      container shutdown-threshold {
        description
          "Set shutdown threshold for protocol packets";
        leaf packet-rate {
          tailf:cli-drop-node-name;
          type uint16 {
            range "1..4096";
          }
        }
        leaf cdp {
          description
            "Cisco Discovery Protocol";
          type uint16 {
            range "1..4096";
          }
        }
        leaf stp {
          description
            "Spanning Tree Protocol";
          type uint16 {
            range "1..4096";
          }
        }
        leaf vtp {
          description
            "Vlan Trunking Protocol";
          type uint16 {
            range "1..4096";
          }
        }
      }
      leaf stp {
        description
          "Spanning Tree Protocol";
        type empty;
      }
      leaf vtp {
        description
          "Vlan Trunking Protocol";
        type empty;
      }
    }
    // interface * / encapsulation
    container encapsulation {
      description
        "Set encapsulation type for an interface";
      container dot1Q {
        description
          "IEEE 802.1Q Virtual LAN";
        tailf:cli-sequence-commands;
        tailf:cli-compact-syntax;
        leaf vlan-id {
          tailf:cli-drop-node-name;
          type uint16 {
            range "1..4094";
          }
        }
        leaf native {
          description
            "Make this as native vlan";
          type empty;
        }
      }
      // interface * / encapsulation isl
      container isl {
        description
          "Inter Switch Link - Virtual LAN encapsulation";
        tailf:cli-sequence-commands;
        tailf:cli-compact-syntax;
        leaf vlan-id {
          tailf:cli-drop-node-name;
          type uint16 {
            range "1..4095";
          }
        }
      }
      // interface * / encapsulation ppp
      container ppp {
        description
          "Point-to-Point protocol";
        presence "true";
      }
      // interface * / encapsulation slip
      container slip {
        description
          "Serial Line IP";
        presence "true";
      }
      // interface * / encapsulation frame-relay
      container frame-relay {
        description
          "Frame Relay networks";
        tailf:cli-delete-when-empty;
        presence "true";
        leaf ietf {
          description
            "Use RFC1490/RFC2427 encapsulation";
          type empty;
        }
      }
    }

    // interface * / no fair-queue
    container fair-queue-conf {
      tailf:cli-no-keyword;
      tailf:cli-drop-node-name;
      when "not(../name[contains(.,'.')])" {
        tailf:dependency "../name";
      }
      leaf fair-queue {
        tailf:cli-boolean-no;
        tailf:cli-trim-default;
        type boolean;
      }
    }
    // interface * / fair-queue
    container fair-queue {
      description
        "Enable Fair Queuing on an Interface";
      tailf:cli-incomplete-no;
      leaf incomplete {
        type empty;
      }
    }
 
    // interface * / flowcontrol
    container flowcontrol {
      description
        "Configure flow operation.";
      leaf receive {
        description
          "Configure receiving flow operation";
        type enumeration {
          enum "desired";
          enum "off";
          enum "on";
        }
      }
      leaf send {
        description
          "Configure sending flow operation";
        type enumeration {
          enum "desired";
          enum "off";
          enum "on";
        }
      }
    }
    // interface * / isis
    container isis {
      description
        "IS-IS commands";
      container adjacency-filter {
        description
          "Filter IS-IS adjacencies";
        tailf:cli-sequence-commands;
        tailf:cli-compact-syntax;
        leaf name {
          tailf:cli-drop-node-name;
          type string;
        }
        leaf match-all {
          description
            "Match all area addresses";
          tailf:cli-optional-in-sequence;
          type empty;
        }
      }
      container advertise {
        description
          "Control addresses advertisements in LSPs";
        leaf prefix {
          description
            "Interface IP address";
          type empty;
        }
      }
      container authentication {
        description
          "ISIS authentication for interface related PDUs";
        uses isis-authentication-grouping;
      }
      container circuit-type {
        description
          "Configure circuit type for interface";
        presence "true";
        leaf levels {
          tailf:cli-drop-node-name;
          type enumeration {
            enum "level-1";
            enum "level-1-2";
            enum "level-2-only";
          }
        }
      }
      container csnp-interval {
        description
          "Set CSNP interval in seconds";
        choice csnp-interval-choice {
          case csnp-interval-level-case {
            list csnp-interval-list {
              tailf:cli-drop-node-name;
              tailf:cli-suppress-mode;
              key "levels";
              leaf levels {
                type enumeration {
                  enum "level-1";
                  enum "level-2";
                }
              }
              leaf value {
                tailf:cli-drop-node-name;
                tailf:cli-prefix-key;
                type uint16;
              }
            }
          }
          case csnp-interval-only-case {
            leaf value {
              tailf:cli-drop-node-name;
              type uint16;
            }
          }
        }
      }
      container hello {
        description
          "Add padding to IS-IS hello packets";
        container padding {
          description
            "Pad hello packets";
          presence "true";
          leaf always {
            description
              "Never pad hello packets if no prefix present";
            type empty;
          }
        }
      }
      container hello-interval {
        description
          "Set Hello interval in seconds";
        choice hello-interval-choice {
          case hello-interval-level-case {
            list hello-interval-list {
              tailf:cli-drop-node-name;
              tailf:cli-suppress-mode;
              key "levels";
              leaf levels {
                type enumeration {
                  enum "level-1";
                  enum "level-2";
                }
              }
              leaf value {
                tailf:cli-drop-node-name;
                tailf:cli-prefix-key;
                type union {
                  type uint16 {
                    range "1..65535";
                  }
                  type enumeration {
                    enum "minimal";
                  }
                }
              }
            }
          }
          case hello-interval-only-case {
            leaf value {
              tailf:cli-drop-node-name;
              type union {
                type uint16 {
                  range "1..65535";
                }
                type enumeration {
                  enum "minimal";
                }
              }
            }
          }
        }
      }
      container hello-multiplier {
        description
          "Set multiplier for Hello holding time";
        choice hello-multiplier-choice {
          case hello-multiplier-level-case {
            list hello-multiplier-list {
              tailf:cli-drop-node-name;
              tailf:cli-suppress-mode;
              key "levels";
              leaf levels {
                type enumeration {
                  enum "level-1";
                  enum "level-2";
                }
              }
              leaf value {
                tailf:cli-drop-node-name;
                tailf:cli-prefix-key;
                type uint16 {
                  range "3..1000";
                }
              }
            }
          }
          case hello-multiplier-only-case {
            leaf value {
              tailf:cli-drop-node-name;
              type uint16 {
                range "3..1000";
              }
            }
          }
        }
      }
      container ipv6 {
        description
          "IPv6 interface configuration";
        uses isis-metric-grouping;
        leaf tag {
          description
            "Assign an admin tag to an ISIS interface IPv6 route";
          type uint32 {
            range "1..4294967295";
          }
        }
      }
      leaf lsp-interval {
        description
          "Set LSP transmission interval";
        tailf:cli-full-command;
        type uint32 {
          range "1..4294967295";
        }
      }
      leaf mesh-group {
        description
          "Set ISIS mesh group";
        tailf:cli-full-command;
        type union {
          type uint32 {
            range "1..4294967295";
          }
          type enumeration {
            enum "blocked";
          }
        }
      }
      uses isis-metric-grouping;
      leaf network {
        description
          "Network type";
        type enumeration {
          enum "point-to-point";
        }
      }
      container password {
        description
          "Configure the authentication password for interface";
        choice password-choice {
          case password-level-case {
            list password-list {
              tailf:cli-drop-node-name;
              tailf:cli-suppress-mode;
              key "levels";
              leaf levels {
                type enumeration {
                  enum "level-1";
                  enum "level-2";
                }
              }
              leaf password {
                tailf:cli-drop-node-name;
                tailf:cli-prefix-key;
                type string;
              }
            }
          }
          case password-only-case {
            leaf password {
              tailf:cli-drop-node-name;
              type string;
            }
          }
        }
      }
      container priority {
        description
          "Set priority for Designated Router election";
        choice priority-choice {
          case priority-level-case {
            list priority-list {
              tailf:cli-drop-node-name;
              tailf:cli-suppress-mode;
              key "levels";
              leaf levels {
                type enumeration {
                  enum "level-1";
                  enum "level-2";
                }
              }
              leaf value {
                tailf:cli-drop-node-name;
                tailf:cli-prefix-key;
                type uint8 {
                  range "0..127";
                }
              }
            }
          }
          case priority-only-case {
            leaf value {
              tailf:cli-drop-node-name;
              type uint8 {
                range "0..127";
              }
            }
          }
        }
      }
      leaf protocol {
        description
          "Set ISIS protocol's state under current interface";
        type enumeration {
          enum "shutdown";
        }
      }
      leaf retransmit-interval {
        description
          "Set per-LSP retransmission interval";
        type uint16;
      }
      leaf retransmit-throttle-interval {
        description
          "Set interface LSP retransmission interval";
        type uint16;
      }
      leaf tag {
        description
          "Assign an admin tag to an ISIS interface IP route";
        type uint32 {
          range "1..4294967295";
        }
      }
      container three-way-handshake {
        description
          "Select Cisco or IETF three-way handshake";
        presence "true";
        leaf implementor {
          tailf:cli-drop-node-name;
          type enumeration {
            enum "cisco";
            enum "ietf";
          }
        }
      }
    }
    // interface * / full-duplex
    // results in "duplex full"

    // interface * / keepalive
    choice keepalive-choice {
      leaf keepalive {
        description
          "Enable keepalive";
        tailf:cli-boolean-no;
        type boolean;
      }
      container keepalive-settings {
        tailf:cli-drop-node-name;
        container keepalive {
          description
            "Enable keepalive";
          tailf:cli-sequence-commands;
          tailf:cli-compact-syntax;
          presence "true";
          leaf period {
            tailf:cli-drop-node-name;
            type uint16 {
              range "0..32767";
            }
          }
          leaf retries {
            tailf:cli-drop-node-name;
            tailf:cli-optional-in-sequence;
            type uint8;
          }
        }
      }
    }
    // interface * / snmp
    container snmp {
      description
        "Modify SNMP interface parameters";
      container ifindex {
        description
          "Persist ifindex for the interface";
        choice ifindex-choice {
          leaf persist {
            description
              "Enable/Disable ifIndex persistence ";
            type empty;
          }
          leaf clear {
            description
              "Clear Enable/Disable ifIndex persistence";
            tailf:cli-trim-default;
            tailf:cli-boolean-no;
            type boolean;
          }
        }
      }
      // interface * / snmp trap
      container trap {
        description
          "Allow a specific SNMP trap";
          //  ip           internet protocol
        leaf link-status {
          description
            "Allow SNMP LINKUP and LINKDOWN traps";
          tailf:cli-boolean-no;
          tailf:cli-trim-default;
          tailf:cli-full-command;
          type boolean;
        }
        container link-status-capas {
          tailf:cli-drop-node-name;
          container link-status {
            description
              "Allow SNMP LINKUP and LINKDOWN traps";
            container permit {
              description
                "Permit the following capability";
              leaf duplicates {
                description
                  "Permit duplicate SNMP LINKUP and LINKDOWN traps";
                type empty;
              }
            }
          }
        }
      }
    }
    // interface * / bfd
    container bfd {
      description
        "BFD interface configuration commands";
      leaf template {
        description
          "BFD template";
        type string;
      }
      container interval {
        description
          "Transmit interval between BFD packets";
        tailf:cli-reset-container;
        tailf:cli-compact-syntax;
        tailf:cli-sequence-commands;
        leaf msecs {
          tailf:cli-drop-node-name;
          tailf:cli-incomplete-command;
          type uint16 {
            range "100..999";
          }
        }
        leaf min_rx {
          description
            "Minimum receive interval capability";
          tailf:cli-incomplete-command;
          type uint16 {
            range "100..999";
          }
        }
        leaf multiplier {
          description
            "Multiplier value used to compute holddown";
          type uint8 {
            range "3..50";
          }
        }
      }
      leaf echo {
        description
          "Use echo adjunct as bfd detection mechanism";
        tailf:cli-boolean-no;
        tailf:cli-trim-default;
        tailf:cli-full-command;
        type boolean;
      }
      container neighbor {
        description
	  "BFD neighbor configuration commands (simulate client)";
	container ipv4 {
	  description
	    "Neighbor IPv4 address";
	  leaf address {
	    tailf:cli-drop-node-name;
	    description
	      "Neighbor IPv4 address A.B.C.D";
	      type inet:ipv4-address;
	  }
	}
      }
    }
    // interface * / bandwidth
    container bandwidth {
      description
        "Set bandwidth informational parameter";
      container receive {
        description
          "Specify receive-side bandwidth";
        tailf:cli-compact-syntax;
        leaf inherit {
          description
            "Specify how bandwidth is inherited";
          type empty;
        }
        leaf kilobits {
          tailf:cli-drop-node-name;
          type uint32 {
            range "1..10000000";
          }
        }
      }
      container inherit {
        description
          "Specify how bandwidth is inherited";
        presence "true";
        leaf kilobits {
          tailf:cli-drop-node-name;
          type uint32 {
            range "1..10000000";
          }
        }
      }
      leaf qos-reference {
        description
          "Reference bandwidth for QOS";
        type uint32 {
          range "1..10000000";
        }
      }
      leaf kilobits {
        tailf:cli-drop-node-name;
        type uint32 {
          range "1..10000000";
        }
      }
    }
    // interface * / cdp
    container cdp {
      description
        "CDP interface subcommands";
      leaf enable {
        description
          "Enable CDP on interface";
        tailf:cli-boolean-no;
        tailf:cli-trim-default;
        tailf:cli-full-command;
        type boolean;
      }
      // interface * / cdp tlv
      container tlv {
        description
          "Enable exchange of specific tlv information";
        container app {
          description
            "Enable/Configure Application TLV";
          tailf:cli-display-separated;
          tailf:cli-compact-syntax;
          tailf:cli-reset-container;
          tailf:cli-sequence-commands;
          presence "true";
          leaf tlvtype {
            description
              "Configure APP TLV";
            tailf:cli-incomplete-command;
            type uint16 {
              range "1001..65535";
            }
          }
          leaf value {
            description
              "Configure App TLV Value information";
            type string;
          }
        }
        leaf server-location {
          description
            "Enable CDP location server on interface";
          tailf:cli-full-command;
          type empty;
        }
        leaf location {
          description
            "Exchange location information";
          tailf:cli-full-command;
          type empty;
        }
      }
    }
    // interface * / dampening
    container dampening {
      description
        "Enable event dampening";
      presence "true";
      tailf:cli-sequence-commands;
      tailf:cli-compact-syntax;
      leaf dampening-time {
        tailf:cli-drop-node-name;
        tailf:cli-delete-container-on-delete;
        description
          "<1-30>;;Half-life time for penalty";
        type uint16 {
          range "1..30";
        }
      }
      leaf start-reusing-time {
        tailf:cli-drop-node-name;
        description
          "<1-20000>;;Value to start reusing an interface";
        type uint16 {
          range "1..20000";
        }
      }
      leaf start-supressing-time {
        tailf:cli-drop-node-name;
        tailf:cli-incomplete-command;
        description
          "<1-20000>;;Value to start supressing an interface";
        type uint16 {
          range "1..20000";
        }
      }
      leaf maximum-supressing-time {
        tailf:cli-drop-node-name;
        tailf:cli-full-command;
        description
          "<1-255>;;Maximum duration to suppress an interface";
        type uint16 {
          range "1..255";
        }
      }
      container restart {
        description
          "Enable restart penalty";
        tailf:cli-sequence-commands;
        tailf:cli-compact-syntax;
        presence "true";
        leaf restart-penalty {
          description
            "<1-20000>;;Penalty applied at restart";
          tailf:cli-optional-in-sequence;
          tailf:cli-drop-node-name;
          type uint16 {
            range "1..20000";
          }
        }
      }
    }
    // interface * / if-state
    leaf if-state {
      type enumeration {
        enum "nhrp";
      }
    }

    // interface * / delay
    leaf delay {
      description
        "Specify interface throughput delay";
      type uint32 {
        range "1..16777215";
      }
    }
    // interface * / domain
    container domain {
      description
        "Specify a domain";
      tailf:cli-compact-syntax;
      leaf name {
        tailf:cli-drop-node-name;
        type string;
      }
      leaf path {
        description
          "Specify a service provider for this interface";
        type string;
      }
      leaf internet-bound {
        tailf:display-when "../path";
        description
          "Specify Internet-bound interface";
        type empty;
      }
      leaf path-id {
        tailf:display-when "../path";
        description
          "Specify service provider path-id for this interface";
        type uint8;
      }
      leaf path-last-resort {
        tailf:display-when "../path";
        description
          "Specify if you want this interface to be a path of last resort";
        type empty;
      }
      leaf zero-sla {
        tailf:display-when "../path";
        description
          "Specify if you want this interface to be a 0-sla interface";
        type empty;
      }
    }
    // interface * / hold-queue
    container hold-queue {
      description
        "Set hold queue depth";
      tailf:cli-compact-syntax;
      tailf:cli-reset-container;
      tailf:cli-sequence-commands;
      leaf queue-length {
        tailf:cli-drop-node-name;
        type uint16 {
          range "0..4096";
        }
      }
      leaf direction {
        tailf:cli-drop-node-name;
        type enumeration {
          enum "in";
          enum "out";
        }
      }
    }
    // interface * / mpls
    container mpls {
      description
        "Configure MPLS interface parameters";
      container accounting {
        description
          "Enable MPLS accounting on this interface";
        container experimental {
          description
            "Count packets by MPLS experimental value on this interface";
          leaf input {
            description
              "received packets";
            type empty;
          }
          leaf output {
            description
              "transmitted packets";
            type empty;
          }
        }
      }
      container bgp {
        description
          "MPLS BGP";
        leaf forwarding {
          description
            "Configure MPLS forwarding for directly connected BGP peers";
          type empty;
        }
      }
      leaf ip {
        description
          "Configure dynamic MPLS forwarding for IP";
        tailf:cli-full-command;
        type empty;
      }
      container label {
        description
          "Label properties";
        leaf protocol {
          description
            "Configure label/tag distribution protocol (LDP/TDP)";
          type enumeration {
            enum "both";
            enum "ldp" {
              tailf:code-name "lab_ldp";
            }
            enum "tdp" {
              tailf:code-name "lab_tdp";
            }
          }
        }
      }
      container ldp {
        description
          "Configure Label Distribution Protocol (LDP) parameters";
        container discovery {
          description
            "Configure interface LDP Discovery parameters";
          leaf transport-address {
            description
              "Specify interface LDP transport address";
            type ldp-discovery-address-type;
          }
        }
      }
      leaf mtu {
        description
          "Set MPLS Maximum Transmission Unit";
        tailf:cli-full-command;
        type union {
          type uint16 {
            range "1501..1524";
          }
          type uint16 {
            range "64..1500";
          }
          type uint16 {
            range "64..9216";
          }
        }
      }
      container traffic-eng {
        description
          "Configure Traffic Engineering parameters";
        leaf administrative-weight {
          description
            "Set the administrative weight for the interface";
          tailf:cli-full-command;
          type uint32 {
            range "0..4294967295";
          }
        }
        leaf attribute-flags {
          description
            "Set user-defined interface attibute flags";
          tailf:cli-full-command;
          type string;
        }
        // interface * / mpls traffic-eng backup-path
        leaf backup-path {
          description
            "Configure an MPLS TE backup for this interface";
          type string;
        }
        container flooding {
          description
            "Set flooding parameters";
          container thresholds {
            description
              "Set flooding thresholds";
            leaf-list down {
              description
                "Set the thresholds for decreased resource availability";
              tailf:cli-flat-list-syntax;
              type uint8 {
                range "0..100";
              }
            }
            leaf-list up {
              description
                "Set the thresholds for increased resource availability";
              tailf:cli-flat-list-syntax;
              type uint8 {
                range "0..100";
              }
            }
          }
        }
        leaf tunnels {
          description
            "enable MPLS Traffic Engineering tunnels";
          tailf:cli-full-command;
          type empty;
        }
      }
    }


    // interface * / vrf forwarding
    // interface * / ip vrf forwarding
    choice vrf-choice {
      container ip-vrf {
        tailf:cli-no-keyword;
        tailf:cli-drop-node-name;
        container ip {
          container vrf {
            leaf forwarding {
              description
                "Configure forwarding table";
              type string;
              tailf:non-strict-leafref {
                path "/ios:native/ip/vrf/name";
              }
            }
          }
        }
      }
      container vrf {
        description
          "VPN Routing/Forwarding parameters on the interface";
          // interface * / vrf forwarding
        leaf forwarding {
          description
            "Configure forwarding table";
          type string;
          tailf:non-strict-leafref {
            path "/ios:native/vrf/definition/name";
          }
        }
      }
    }
    // interface * / ip
    container ip {
      description
        "Interface Internet Protocol config commands";
      // interface * / ip admission
      leaf admission {
        description 
	      "Apply Network Admission Control";
        type string;
      }
        // interface * / ip access-group
      container access-group {
        description
          "Specify access control for packets";
        container in {
          tailf:cli-drop-node-name;
          tailf:cli-incomplete-command;
          tailf:cli-sequence-commands;
          tailf:cli-compact-syntax;
          choice apply-type {
            case apply-common {
              container common-acl {
                tailf:cli-drop-node-name;
                tailf:cli-incomplete-command;
                tailf:cli-sequence-commands;
                tailf:cli-compact-syntax;
                tailf:cli-flatten-container;
                leaf common {
                  description
                    "specify ipv4 common ACL for packet filtering";
                  tailf:cli-incomplete-command;
                  type exp-acl-type;
                  mandatory true;
                }
                leaf in {
                  tailf:cli-full-command;
                  description
                    "inbound packets";
                  type empty;
                }
              }
            }
            case apply-intf {
              container acl {
                tailf:cli-drop-node-name;
                tailf:cli-incomplete-command;
                tailf:cli-sequence-commands;
                tailf:cli-compact-syntax;
                tailf:cli-flatten-container;
                leaf acl-name {
                  tailf:cli-drop-node-name;
                  tailf:cli-incomplete-command;
                  type exp-acl-type;
                  mandatory true;
                }
                leaf in {
                  tailf:cli-full-command;
                  description
                    "inbound packets";
                  type empty;
                }
              }
            }
          }
        }
        container out {
          tailf:cli-drop-node-name;
          tailf:cli-incomplete-command;
          tailf:cli-sequence-commands;
          tailf:cli-compact-syntax;
          choice apply-type {
            case apply-common {
              container common-acl {
                tailf:cli-drop-node-name;
                tailf:cli-incomplete-command;
                tailf:cli-sequence-commands;
                tailf:cli-compact-syntax;
                tailf:cli-flatten-container;
                leaf common {
                  description
                    "specify ipv4 common ACL for packet filtering";
                  tailf:cli-incomplete-command;
                  type exp-acl-type;
                  mandatory true;
                }
                leaf out {
                  tailf:cli-full-command;
                  description
                    "outbound packets";
                  type empty;
                }
              }
            }
            case apply-intf {
              container acl {
                tailf:cli-drop-node-name;
                tailf:cli-incomplete-command;
                tailf:cli-sequence-commands;
                tailf:cli-compact-syntax;
                tailf:cli-flatten-container;
                leaf acl-name {
                  tailf:cli-drop-node-name;
                  tailf:cli-incomplete-command;
                  type exp-acl-type;
                  mandatory true;
                }
                leaf out {
                  tailf:cli-full-command;
                  description
                    "outbound packets";
                  type empty;
                }
              }
            }
          }
        }
      }
      // interface * / ip arp
      container arp {
        description
          "Configure ARP features";
        container inspection {
          description
            "Arp Inspection configuration";
          container limit {
            description
              "Configure Rate limit of incoming ARP packets";
            leaf none {
              description
                "No limit";
              tailf:cli-full-command;
              type empty;
            }
            leaf rate {
              description
                "Rate Limit";
              type uint32;
            }
          }
          leaf trust {
            description
              "Configure Trust state";
            tailf:cli-full-command;
            type empty;
          }
        }
      }
      // interface * / ip vrf
      container vrf {
        description
          "VPN Routing/Forwarding parameters on the interface";
        leaf receive {
          description
            "Add Interface Address into VRF Table";
          tailf:cli-full-command;
          type string;
        }
        leaf sitemap {
          description
            "Configure route-map for routesreceived from this site";
          tailf:cli-full-command;
          type string;
          // Note: no dependency to /ios:route-map
        }
      }
      // interface * / ip address
      choice address-choice {
        // interface * / ip unnumbered
        leaf unnumbered {
          description
            "Enable IP processing without an explicit address";
          type string;
        }
        // interface * / no ip address
        container no-address {
          tailf:cli-drop-node-name;
          leaf address {
            tailf:cli-boolean-no;
            tailf:cli-trim-default;
            type boolean;
          }
        }
        // interface * / ip address XXX
        container address {
          description
            "Set the IP address of an interface";
          tailf:cli-incomplete-command;
          tailf:cli-incomplete-no;
          choice address-choice {
            case fixed-case {
              container primary {
                tailf:cli-drop-node-name;
                tailf:cli-sequence-commands;
                tailf:cli-compact-syntax;
                tailf:cli-incomplete-command;
                tailf:cli-incomplete-no;
                leaf address {
                  tailf:cli-incomplete-command;
                  tailf:cli-drop-node-name;
                  tailf:cli-incomplete-no;
                  tailf:cli-diff-dependency "/ios:native/vrf/definition/address-family/ipv4";
                  tailf:cli-diff-dependency "../../../../vrf/forwarding";
                  type inet:ipv4-address;
                }
                leaf mask {
                  tailf:cli-drop-node-name;
                  type inet:ipv4-address;
                }
              }
              list secondary {
                key "address";
                tailf:cli-incomplete-command;
                tailf:cli-sequence-commands;
                tailf:cli-compact-syntax;
                tailf:cli-drop-node-name;
                tailf:cli-suppress-mode;
                tailf:cli-incomplete-no;
                leaf address {
                  tailf:cli-incomplete-no;
                  type inet:ipv4-address;
                }
                leaf mask {
                  tailf:cli-drop-node-name;
                  tailf:cli-incomplete-command;
                  mandatory true;
                  type inet:ipv4-address;
                }
                leaf secondary {
                  description
                    "Make this IP address a secondary address";
                  mandatory true;
                  type empty;
                }
              }
            }
            case dhcp-case {
              container dhcp {
                description
                  "IP Address negotiated via DHCP";
                presence "IP Address negotiated via DHCP";
                tailf:cli-sequence-commands;
		tailf:cli-compact-syntax;
                container client-id {
                  description
                    "Specify client-id to use";
                  tailf:cli-flatten-container;
                  tailf:cli-optional-in-sequence;
                  tailf:cli-diff-dependency "/ios:native/interface";
                  uses ethernet-grouping;
                }
                leaf hostname {
                  description
                    "Specify value for hostname option";
                  type string;
                }
              }
            }
          }
        }
      }

      // interface * / ip directed-broadcast
      leaf directed-broadcast {
        description
          "Enable forwarding of directed broadcasts";
        type exp-acl-type;
      }


      // interface * / ip flow
      container flow {
        description
          "NetFlow related commands";
        leaf ingress {
          description
            "Enable inbound NetFlow";
          type empty;
        }
        leaf egress {
          description
            "Enable outbound NetFlow";
          type empty;
        }
        uses interface-ip-monitor-grouping;
      }

      // interface * / ip hello-interval
      container hello-interval {
        description
          "Configures EIGRP-IPv4 hello interval";
        tailf:cli-sequence-commands;
        tailf:cli-compact-syntax;
        leaf eigrp {
          description
            "Enhanced Interior Gateway Routing Protocol (EIGRP)";
          type uint16;
        }
        leaf seconds {
          tailf:cli-drop-node-name;
          description
            "Seconds between hello transmissions";
          type uint16;
        }
      }


      // interface * / ip authentication
      container authentication {
        description
          "authentication subcommands";
        container key-chain {
          description
            "key-chain";
          tailf:cli-sequence-commands;
          tailf:cli-compact-syntax;
          leaf eigrp {
            description
              "Enhanced Interior Gateway Routing Protocol (EIGRP)";
            type uint16;
          }
          leaf name {
            tailf:cli-drop-node-name;
            description
              "name of key-chain";
            type string;
          }
        }
        container mode {
          description
            "mode";
          tailf:cli-sequence-commands;
          tailf:cli-compact-syntax;
          leaf eigrp {
            description
              "Enhanced Interior Gateway Routing Protocol (EIGRP)";
            type uint16;
          }
          leaf md5 {
            description
              "Keyed message digest";
            type empty;
          }
        }
      }

      // interface * / ip hold-time 
      container hold-time {
        description
          "Configures EIGRP-IPv4 hold time";
        tailf:cli-sequence-commands;
        tailf:cli-compact-syntax;
        leaf eigrp {
          description
            "Enhanced Interior Gateway Routing Protocol (EIGRP)";
          type uint16;
        }
        leaf seconds {
          tailf:cli-drop-node-name;
          description
            "Seconds before neighbor is considered down";
          type uint16;
        }
      }


      // interface * / ip helper-address
      list helper-address {
        description
          "Specify a destination address for UDP broadcasts";
        tailf:cli-suppress-mode;
        key "address";
        leaf address {
          type inet:ipv4-address;
        }
        choice helper-choice {
          leaf global {
            description
              "Helper-address is global";
            tailf:cli-prefix-key;
            type empty;
          }
          leaf vrf {
            description
              "VRF name for helper-address (if different from interface VRF)";
            tailf:cli-prefix-key;
            tailf:cli-diff-dependency "/ios:native/ip/vrf";
            tailf:cli-diff-dependency "/ios:native/vrf/definition";
            type string;
          }
        }
      }

      // interface * / ip lisp
      container lisp {
        description
          "Locator/ID Separation Protocol";
        leaf source-locator {
          description
            "Choose IP source address for LISP packets egressing this interface";
          type string;
        }
      }


      // interface * / ip nbar
      container nbar {
        description
          "Network-Based Application Recognition";
        container protocol-discovery {
          description
            "Enable protocol discovery for both ipv4 and ipv6";
          presence "true";
          leaf ipv4-ipv6 {
            tailf:cli-drop-node-name;
            type enumeration {
              enum "ipv4";
              enum "ipv6";
            }
          }
        }
      }

      // interface * / ip nhrp
      container nhrp {
        description
          "NHRP interface subcommands";
        container attribute {
          description
            "NHRP attribute set";
          container set {
            description
              "attribute set";
            list attr-type {
              tailf:cli-drop-node-name;
              tailf:cli-suppress-mode;
              key "attr-type";
              leaf attr-type {
                description
                  "attribute type";
                type string;
              }
              leaf attr-val {
                description
                  "attribute value";
                tailf:cli-drop-node-name;
                type string;
              }
            }
          }
        }
        leaf authentication {
          description
            "authentication string";
          type string;
        }
        container cache {
          description
            "NHRP Cache related commands.";
          leaf non-authoritative {
            description
              "Mark cache entries non-authoritative";
            type empty;
          }
        }
        leaf connect {
          description
            "NHRP event request id";
          type uint16 {
            range "1..65535";
          }
        }
        leaf group {
          type string;
        }
        leaf holdtime {
          description
            "Number of seconds";
          type uint16 {
            range "1..65535";
          }
        }
        container interest {
          description
            "Specify an access list";
          leaf acl-range {
            description
              "IP access list";
            tailf:cli-drop-node-name;
            type uint8 {
              range "1..199";
            }
          }
          leaf none {
            description
              "No traffic is interesting.";
            type empty;
          }
        }
        container map {
          description
            "Map dest IP addresses to NBMA addresses";
          list dest-ipv4 {
            tailf:cli-drop-node-name;
            tailf:cli-suppress-mode;
            key "dest-ipv4";
            leaf dest-ipv4 {
              description
                "IP address of destination";
              type inet:ipv4-address;
            }
            list nbma-ipv4 {
              tailf:cli-drop-node-name;
              tailf:cli-suppress-mode;
              key "nbma-ipv4";
              leaf nbma-ipv4 {
                description
                  "IP NBMA address";
                type inet:ipv4-address;
              }
              leaf ipv4 {
                tailf:cli-drop-node-name;
                type inet:ipv4-address;
              }
              leaf ipv6 {
                tailf:cli-drop-node-name;
                type inet:ipv6-address;
              }
            }
            list dest-mask {
              tailf:cli-drop-node-name;
              tailf:cli-suppress-mode;
              key "dest-mask";
              leaf dest-mask {
                description
                  "IP mask of destination";
                type inet:ipv4-address;
              }
              leaf ipv4 {
                tailf:cli-drop-node-name;
                type inet:ipv4-address;
              }
              leaf ipv6 {
                tailf:cli-drop-node-name;
                type inet:ipv6-address;
              }
            }
            leaf nbma-ipv6 {
              tailf:cli-drop-node-name;
              type inet:ipv6-address;
            }
          }
          container multicast {
            description
              "Use this NBMA mapping for broadcasts/multicasts";
            leaf ipv4 {
              tailf:cli-drop-node-name;
              type inet:ipv4-address;
            }
            leaf ipv6 {
              tailf:cli-drop-node-name;
              type inet:ipv6-address;
            }
            leaf dynamic {
              description
                "Dynamically learn destinations from client registrations on hub";
              type empty;
            }
          }
          list group {
            tailf:cli-suppress-mode;
            key "name";
            leaf name {
              type string;
            }
            container service-policy {
              leaf output {
                description
                  "Policy";
                type string;
              }
            }
          }
        }
        container max-send {
          description
            "Rate limit NHRP traffic";
          list pkt-count {
            tailf:cli-drop-node-name;
            tailf:cli-suppress-mode;
            key "pkt-count";
            leaf pkt-count {
              description
                "Packet count";
              type uint16 {
                range "1..65535";
              }
            }
            leaf every {
              description
                "Interval in seconds";
              type uint16 {
                range "10..65535";
              }
            }
          }
        }
        leaf network-id {
          description
            "Network identifier";
          type uint32 {
            range "1..4294967295";
          }
        }
        container nhs {
          description
            "Specify a next hop server";
          list ipv4 {
            tailf:cli-drop-node-name;
            tailf:cli-suppress-mode;
            key "ipv4";
            leaf ipv4 {
              description
                "Protocol IP address of NHS";
              type inet:ipv4-address;
            }
            leaf cluster {
              description
                "NHS cluster number";
              type uint8 {
                range "0..10";
              }
            }
            container nbma {
              description
                "NBMA of NHS";
              list ipv4 {
                tailf:cli-drop-node-name;
                tailf:cli-suppress-mode;
                key "ipv4";
                leaf ipv4 {
                  description
                    "IPv4 address";
                  type inet:ipv4-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list prior {
                      tailf:cli-drop-node-name;
                      tailf:cli-suppress-mode;
                      key "prior";
                      leaf prior {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list pri {
                    tailf:cli-drop-node-name;
                    tailf:cli-suppress-mode;
                    key "pri";
                    leaf pri {
                      description
                        "NHS priority, range = 0 to 255, 0 is the highest";
                      type uint8 {
                        range "0..255";
                      }
                    }
                    leaf cluster {
                      description
                        "NHS cluster number";
                      type uint8 {
                        range "0..10";
                      }
                    }
                  }
                }
              }
              list nhs-fqdn {
                tailf:cli-drop-node-name;
                tailf:cli-suppress-mode;
                key "nhs-fqdn";
                leaf nhs-fqdn {
                  description
                    "NHS FQDN string";
                  type string;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list mc-pri {
                      tailf:cli-drop-node-name;
                      tailf:cli-suppress-mode;
                      key "mc-pri";
                      leaf mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list nhs-pri {
                    tailf:cli-drop-node-name;
                    tailf:cli-suppress-mode;
                    key "nhs-pri";
                    leaf nhs-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              list ipv6 {
                tailf:cli-drop-node-name;
                tailf:cli-suppress-mode;
                key "ipv6";
                leaf ipv6 {
                  description
                    "IPv6 address";
                  type inet:ipv6-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list mc-pri {
                      tailf:cli-drop-node-name;
                      tailf:cli-suppress-mode;
                      key "mc-pri";
                      leaf mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list mc-prior {
                    tailf:cli-drop-node-name;
                    tailf:cli-suppress-mode;
                    key "mc-prior";
                    leaf mc-prior {
                      description
                        "NHS priority, range = 0 to 255, 0 is the highest";
                      type uint8 {
                        range "0..255";
                      }
                    }
                    leaf cluster {
                      description
                        "NHS cluster number";
                      type uint8 {
                        range "0..10";
                      }
                    }
                  }
                }
              }
            }
            container priority {
              description
                "NHS priority, don't specify for default priority";
              list pri-range {
                tailf:cli-drop-node-name;
                tailf:cli-suppress-mode;
                key "pri-range";
                leaf pri-range {
                  description
                    "NHS priority, range = 0 to 255, 0 is the highest";
                  type uint8 {
                    range "0..255";
                  }
                }
                leaf cluster {
                  description
                    "NHS cluster number";
                  type uint8 {
                    range "0..10";
                  }
                }
              }
            }
          }
          container cluster {
            description
              "NHS Redundancy cluster configurations";
            list clus-num {
              tailf:cli-drop-node-name;
              tailf:cli-suppress-mode;
              key "clus-num";
              leaf clus-num {
                description
                  "NHS cluster number";
                type uint8 {
                  range "0..10";
                }
              }
              leaf max-connections {
                description
                  "Max-connections value";
                type uint8 {
                  range "0..255";
                }
              }
            }
          }
          container dynamic {
            description
              "NHS protocol address dynamically learnt";
            container nbma {
              description
                "NBMA of NHS";
              list ipv4 {
                description
                  "NBMA of NHS";
                tailf:cli-drop-node-name;
                tailf:cli-suppress-mode;
                key "ipv4";
                leaf ipv4 {
                  description
                    "IPv4 address";
                  type inet:ipv4-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list dyn-pri {
                      tailf:cli-drop-node-name;
                      tailf:cli-suppress-mode;
                      key "dyn-pri";
                      leaf dyn-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list n-prior {
                    tailf:cli-drop-node-name;
                    tailf:cli-suppress-mode;
                    key "n-prior";
                    leaf n-prior {
                      description
                        "NHS priority, range = 0 to 255, 0 is the highest";
                      type uint8 {
                        range "0..255";
                      }
                    }
                    leaf cluster {
                      description
                        "NHS cluster number";
                      type uint8 {
                        range "0..10";
                      }
                    }
                  }
                }
              }
              list dyn-fqdn {
                tailf:cli-drop-node-name;
                tailf:cli-suppress-mode;
                key "dyn-fqdn";
                leaf dyn-fqdn {
                  description
                    "NHS FQDN string";
                  type string;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list dyn-mc-pri {
                      tailf:cli-drop-node-name;
                      tailf:cli-suppress-mode;
                      key "dyn-mc-pri";
                      leaf dyn-mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list dp {
                    tailf:cli-drop-node-name;
                    tailf:cli-suppress-mode;
                    key "dp";
                    leaf dp {
                      description
                        "NHS priority, range = 0 to 255, 0 is the highest";
                      type uint8 {
                        range "0..255";
                      }
                    }
                    leaf cluster {
                      description
                        "NHS cluster number";
                      type uint8 {
                        range "0..10";
                      }
                    }
                  }
                }
              }
              list ipv6 {
                tailf:cli-drop-node-name;
                tailf:cli-suppress-mode;
                key "ipv6";
                leaf ipv6 {
                  description
                    "IPv6 address";
                  type inet:ipv6-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list v6-pri {
                      tailf:cli-drop-node-name;
                      tailf:cli-suppress-mode;
                      key "v6-pri";
                      leaf v6-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list v6-pri2 {
                    tailf:cli-drop-node-name;
                    tailf:cli-suppress-mode;
                    key "v6-pri2";
                    leaf v6-pri2 {
                      description
                        "NHS priority, range = 0 to 255, 0 is the highest";
                      type uint8 {
                        range "0..255";
                      }
                    }
                    leaf cluster {
                      description
                        "NHS cluster number";
                      type uint8 {
                        range "0..10";
                      }
                    }
                  }
                }
              }
            }
          }
          leaf fallback {
            description
              "NHS Redundancy Fallback time, 0 -60 seconds";
            type uint8 {
              range "0..60";
            }
          }
        }
        leaf record {
          description
            "Allow NHRP record option";
          type empty;
        }
        container redirect {
          description
            "Enable NHRP redirect traffic indication";
          presence "true";
          leaf timeout {
            description
              "Interval in seconds";
            type uint8 {
              range "2..30";
            }
          }
        }
        container registration {
          description
            "Settings for registration packets.";
          leaf no-unique {
            description
              "Do not set the 'Unique' flag in registration requests.";
            type empty;
          }
          leaf timeout {
            description
              "Number of seconds";
            type uint16 {
              range "1..65535";
            }
          }
        }
        container reject {
          description
            "NHRP resolution reject request";
          list reqid {
            tailf:cli-drop-node-name;
            tailf:cli-suppress-mode;
            key "reqid";
            leaf reqid {
              description
                "reqid value";
              type uint16 {
                range "1..65535";
              }
            }
            leaf rej-secs {
              description
                "Number of seconds";
              tailf:cli-drop-node-name;
              type uint16 {
                range "0..65535";
              }
            }
          }
        }
        container responder {
          description
            "Responder interface";
          leaf res-int {
            description
              "Virtual ACR interface";
            tailf:cli-drop-node-name;
            type string;
          }
          leaf Analysis-Module {
            description
              "Analysis-Module interface number";
            type uint8;
          }
          leaf Fcpa {
            description
              "Fcpa interface number";
            type uint8;
          }
          leaf SBC {
            description
              "SBC interface number";
            type uint32 {
              range "0..2147483647";
            }
          }
          leaf SONET_ACR {
            description
              "SONET_ACR interface number";
            type uint8;
          }
          leaf TB-controller {
            description
              "Telecom-Bus Clock Controller";
            tailf:cli-drop-node-name;
            type string;
          }
          leaf Service-Engine {
            description
              "Service-Engine interface number";
            type uint8;
          }
          leaf Tunnel {
            description
              "Tunnel interface number";
            type uint32 {
              range "0..2147483647";
            }
          }
          leaf Tunnel-tp {
            description
              "Tunnel-tp interface number";
            type uint16 {
              range "0..65535";
            }
          }
          leaf VPN {
            description
              "VPN interface number";
            type uint32 {
              range "0..2147483647";
            }
          }
          leaf Virtual-TokenRing {
            description
              "Virtual-TokenRing interface number";
            type uint32 {
              range "0..2147483647";
            }
          }
          leaf VirtualPortGroup {
            description
              "VirtualPortGroup interface number";
            type uint8 {
              range "0..31";
            }
          }
          leaf Vlan {
            description
              "Vlan interface number";
            type uint16 {
              range "1..4095";
            }
          }
          leaf ucse {
            description
              "ucse interface number";
            type uint8;
          }
          leaf vasileft {
            description
              "vasileft interface number";
            type uint16 {
              range "1..2000";
            }
          }
          leaf vasiright {
            description
              "vasiright interface number";
            type uint16 {
              range "1..2000";
            }
          }
        }
        container server-only {
          description
            "Disable NHRP requests";
          presence "true";
          leaf non-caching {
            description
              "Do not create NHRP cache entries";
            type empty;
          }
        }
        container shortcut {
          description
            "Enable shortcut switching";
          presence "true";
          leaf virtual-template {
            description
              "Virtual template number";
            type uint16 {
              range "1..4095";
            }
          }
        }
        container trigger-svc {
          description
            "Create NHRP cut-through based on traffic load";
          list kbps {
            tailf:cli-drop-node-name;
            tailf:cli-suppress-mode;
            key "kbps";
            leaf kbps {
              description
                "Trigger rate in kbps";
              type uint32 {
                range "1..4294967295";
              }
            }
            leaf tear-kbps {
              description
                "Teardown rate in kbps";
              tailf:cli-drop-node-name;
              type uint32 {
                range "0..4294967295";
              }
            }
          }
        }
        leaf use {
          description
            "Number of packets to cause NHRP request";
          type uint16 {
            range "1..65535";
          }
        }
      }
      // interface * / ip ospf
      container ospf {
        description
          "OSPF interface commands";
          // interface * / ip ospf *
        list process-id {
          tailf:cli-drop-node-name;
          tailf:cli-suppress-mode;
          tailf:cli-delete-when-empty;
          tailf:cli-compact-syntax;
          tailf:cli-incomplete-command;
          tailf:cli-reset-container;
          tailf:cli-sequence-commands;
          key "id";
          leaf id {
            type uint16;
          }
          leaf area {
            type ospf-area-type;
          }
          leaf secondaries {
            description
              "Include or exclude secondary IP addresses";
            type empty;
          }
          leaf none {
            description
              "Do not include secondary IP addresses";
            type empty;
          }
        }
        // interface * / ip ospf authentication
        container authentication {
          description
            "Enable authentication";
          presence "Enable authentication";
          container key-chain {
            description
              "Use a key-chain for cryptographic authentication keys";
            tailf:cli-compact-syntax;
            leaf name {
              tailf:cli-drop-node-name;
              type string;
            }
          }
          leaf message-digest {
            description
              "Use message-digest authentication";
            type empty;
          }
          leaf null {
            description
              "Use no authentication";
            type empty;
          }
        }
        // interface * / ip ospf authentication-key
        uses ospf-authentication-key-grouping;
        // interface * / ip ospf network
        leaf network {
          description
            "Network type";
          type enumeration {
            enum "broadcast";
            enum "non-broadcast";
            enum "point-to-multipoint";
            enum "point-to-point";
          }
        }
        // interface * / ip ospf bfd
        uses interface-ospf-bfd-grouping;
        // interface * / ip ospf cost
        leaf cost {
          description
            "Interface cost";
          type uint16 {
            range "1..65535";
          }
        }
        // interface * / ip ospf database-filter
        container database-filter {
          description
            "Filter OSPF LSA during synchronization and flooding";
          tailf:cli-compact-syntax;
          tailf:cli-sequence-commands;
          leaf all {
            description
              "Filter all LSA";
            type empty;
          }
          leaf out {
            description
              "Outgoing LSA";
            type empty;
          }
        }
        // interface * / ip ospf dead-interval
        container dead-interval {
          description
            "Interval after which a neighbor is declared dead";
          leaf value {
            tailf:cli-drop-node-name;
            type uint32 {
              range "1..65535";
            }
          }
          container minimal {
            description
              "Set to 1 second";
            leaf hello-multiplier {
              description
                "Set multiplier for Hellos";
              type uint8;
            }
          }
        }
        // interface * / ip ospf demand-circuit
        container demand-circuit {
          description
            "OSPF Demand Circuit";
          presence "true";
          leaf ignore {
            description
              "Ignore demand circuit auto-negotiation requests";
            type empty;
          }
        }
        // interface * / ip ospf fast-reroute
        container fast-reroute {
          description
            "LFA FastReroute parameters";
          container per-prefix {
            description
              "Per-prefix LFA FRR parameters";
            container candidate {
              description
                "If interface can be protecting";
              presence "true";
              leaf disable {
                description
                  "Disable LFA FRR interface protection";
                type empty;
              }
            }
            container protection {
              description
                "If interface can be protected";
              presence "true";
              leaf disable {
                description
                  "Disable LFA FRR interface protection";
                type empty;
              }
            }
          }
        }
        // interface * / ip ospf flood-reduction
        leaf flood-reduction {
          description
            "OSPF Flood Reduction";
          type empty;
        }
        // interface * / ip ospf hello-interval
        uses interface-ospf-hello-interval-grouping;
        // interface * / ip ospf lls
        container lls {
          description
            "Link-local Signaling (LLS) support";
          presence "true";
          leaf disable {
            description
              "disable LLS";
            type empty;
          }
        }
        // interface * / ip ospf message-digest-key
        list message-digest-key {
          description
            "Set message digest key";
          tailf:cli-suppress-mode;
          tailf:cli-delete-when-empty;
          tailf:cli-incomplete-command;
          key "id";
          leaf id {
            tailf:cli-suppress-range;
            type uint8 {
              range "1 .. 255";
            }
          }
          container md5 {
            description
              "Use MD5 algorithm";
            tailf:cli-sequence-commands;
            tailf:cli-compact-syntax;
            leaf auth-type {
              tailf:cli-drop-node-name;
              tailf:cli-optional-in-sequence;
              type uint8 {
                range "0 .. 7";
              }
            }
            leaf auth-key {
              tailf:cli-drop-node-name;
              tailf:cli-full-command;
              tailf:cli-multi-value;
              type string;
            }
          }
        }
        // interface * / ip ospf mtu-ignore
        leaf mtu-ignore {
          description
            "Ignores the MTU in DBD packets";
          type empty;
        }
        // interface * / ip ospf multi-area
        container multi-area {
          description
            "Set the OSPF multi-area ID";
          tailf:cli-sequence-commands;
          tailf:cli-compact-syntax;
          leaf id {
            tailf:cli-drop-node-name;
            type union {
              type uint32 {
                range "0..4294967295";
              }
              type inet:ipv4-address;
            }
          }
          leaf cost {
            description
              "Interface cost";
            tailf:cli-optional-in-sequence;
            type uint32 {
              range "1..65535";
            }
          }
        }
        // interface * / ip ospf prefix-suppression
        uses interface-ospf-prefix-suppression-grouping;
        // interface * / ip ospf priority
        uses interface-ospf-priority-grouping;
        // interface * / ip ospf resync-timeout
        leaf resync-timeout {
          description
            "Interval after which adjacency is reset if oob-resync is not started";
          type uint32 {
            range "1..65535";
          }
        }
        // interface * / ip ospf retransmit-interval
        uses interface-ospf-retransmit-interval-grouping;
        // interface * / ip ospf shutdown
        leaf shutdown {
          description
            "Set OSPF protocol's state to disable under current interface";
          type empty;
        }
        // interface * / ip ospf transmit-delay
        uses interface-ospf-transmit-delay-grouping;
        // interface * / ip ospf ttl-security
        container ttl-security {
          description
            "TTL security check";
          presence "true";
          leaf diable {
            description
              "disable TTL security check";
            type empty;
          }
          leaf hops {
            description
              "IP hops";
            type uint8 {
              range "1..254";
            }
          }
        }
      }

      // interface * / ip pim
      container pim {
        description
          "PIM interface commands";
        container accept-register {
          leaf list {
            type string;
          }
        }
        // interface * / ip pim sparse-mode/sparse-dense-mode
        leaf sparse-mode {
          tailf:cli-drop-node-name;
          type enumeration{
            enum sparse-dense-mode;
            enum sparse-mode;
          }
        }
        // interface * / ip pim nbma-mode
        leaf nbma-mode {
          description
            "Enable PIM nbma-mode operation";
          type empty;
        }
        // interface * / ip pim dr-priority
        leaf dr-priority {
          description
            "PIM router DR priority";
          type uint32;
        }
        // interface * / ip pim query-interval
        container query-interval {
          description
            "PIM router query interval";
          tailf:cli-sequence-commands;
          tailf:cli-compact-syntax;
          choice seconds-milliseconds {
            case seconds {
              leaf seconds-interval {
                tailf:cli-drop-node-name;
                type uint16 {
                  range "1..18725";
                }
              }
            }
            case milliseconds {
              leaf milliseconds-interval {
                tailf:cli-drop-node-name;
                type uint16 {
                  range "100..65535";
                }
              }
              leaf msec {
                description
                  "Query interval in milliseconds";
                mandatory true;
                type empty;
              }
            }
          }
        }
        // interface * / ip pim spt-threshold
        leaf spt-threshold {
          type enumeration {
            enum "infinity";
          }
        }
      }
      // interface * / ip policy
      container policy {
        description
          "Enable policy routing";
        leaf route-map {
          description
            "Policy route-map";
          type string;
        }
      }
      // interface * / ip local-proxy-arp
      leaf local-proxy-arp {
        description
          "Enable local-proxy ARP";
        type empty;
      }
      // interface * / ip proxy-arp
      leaf proxy-arp {
        description
          "Enable proxy ARP";
        tailf:cli-boolean-no;
        tailf:cli-trim-default;
        type boolean;
      }
      // interface * / no ip route-cache
      container route-cache-conf {
        tailf:cli-no-keyword;
        tailf:cli-drop-node-name;
        leaf route-cache {
          tailf:cli-boolean-no;
          tailf:cli-trim-default;
          type boolean;
        }
      }
      // interface * / ip route-cache
      container route-cache {
        description
          "Enable fast-switching cache for outgoing packets";
        tailf:cli-incomplete-no;
        // interface * / ip route-cache cef
        leaf cef {
          description
            "Enable Cisco Express Forwarding";
          tailf:cli-boolean-no;
          tailf:cli-trim-default;
          type boolean;
        }
        // interface * / ip route-cache flow
        leaf flow {
          description
            "Enable Flow fast-switching cache";
          tailf:cli-boolean-no;
          tailf:cli-trim-default;
          type boolean;
        }
        // interface * / ip route-cache policy
        leaf policy {
          description
            "Enable fast-switching policy cache for outgoing packets";
          tailf:cli-boolean-no;
          tailf:cli-trim-default;
          type boolean;
        }
        // interface * / ip route-cache same-interface
        leaf same-interface {
          description
            "Enable fast-switching on the same interface";
          tailf:cli-boolean-no;
          tailf:cli-trim-default;
          type boolean;
        }
      }
      // interface * / ip router
      container router {
        description
          "IP router interface commands";
        container isis {
          description
            "IS-IS Routing for IP";
          presence "true";
          leaf tag {
            tailf:cli-drop-node-name;
            type string;
          }
        }
      }
      // interface * / ip igmp
      container igmp {
        description
          "IGMP interface commands";
        container static-group {
          description
            "IGMP static multicast group";
          list groups {
            tailf:cli-suppress-mode;
            tailf:cli-delete-when-empty;
            tailf:cli-drop-node-name;
            key "name";
            leaf name {
              tailf:cli-suppress-range;
              type union {
                type inet:ipv4-address;
                type enumeration {
                  enum "*";
                }
              }
            }
          }
          list class-map {
            description
              "Class map of type multicast-flows";
            key "id";
            leaf id {
              type leafref {
                path "/ios:native/class-map/name";
              }
            }
          }
        }
        list join-group {
          description
            "IGMP join multicast group";
          tailf:cli-suppress-mode;
          key "ip-group-address";
          leaf ip-group-address {
            description
              "IP group address";
            type inet:ipv4-address;
          }
          leaf source {
            description
              "IP source address";
            type inet:ipv4-address;              
          }
        }
        leaf version {
          description
            "IGMP version";
          type uint8 {
            range "1..3";
          }
        }
      }
      // interface * / ip redirects
      leaf redirects {
        description
          "Enable sending ICMP Redirect messages";
        tailf:cli-boolean-no;
        tailf:cli-trim-default;
        type boolean;
      }
      // interface * / ip unreachables
      leaf unreachables {
        description
          "Enable sending ICMP Unreachable messages";
        tailf:cli-boolean-no;
        tailf:cli-trim-default;
        type boolean;
      }
      // interface * / ip tcp
      container tcp {
        description
          "TCP header compression and other parameters";
        leaf adjust-mss {
          description
            "Adjust the mss of transit packets";
          type uint16 {
            range "500..1460";
          }
        }
      }

      // interface * / ip virtual-reassembly
      container virtual-reassembly {
        tailf:cli-compact-syntax;
        leaf max-reassemblies {
          type uint32;
        }
        leaf max-fragments {
          type uint32;
        }
        leaf timeout {
          type uint32;
        }
        leaf drop-fragments {
          type empty;
        }
        leaf in {
          type empty;
        }
      }


      // interface * / ip dhcp
      container dhcp {
        description
          "Configure DHCP parameters for this interface";
        container client {
          description
            "DHCP client configuration";
            leaf hostname {
              description 
                "Specify hostname to use";
              type string;
            }  
        }   
        container relay {
          description
            "DHCP relay configuration parameters";
          container information {
            description
              "DHCP relay information option";
            container check-reply {
              description
                "Validate relay information in BOOTREPLY";
              presence "true";
              leaf none {
                description
                  "Set to none";
                type empty;
              }
            }
            container option {
              description
                "DHCP relay information option";
              leaf subscriber-id {
                description
                  "Subscriber identifier sub option";
                type string;
              }
            }
            container option-insert {
              description
                "Insert relay information in BOOTREQUEST";
              presence "true";
              leaf none {
                description
                  "Set to none";
                type empty;
              }
            }
            leaf policy-action {
              description
                "Define reforwarding policy";
              type enumeration {
                enum "drop";
                enum "encapsulate";
                enum "keep";
                enum "replace";
              }
            }
            leaf trusted {
              description
                "Received DHCP packet may contain relay info option with zero giaddr";
              type empty;
            }
          }
          leaf source-interface {
            description
              "Set source interface for relayed messages";
            type string;
          }
        }
        container snooping {
          description
            "DHCP Snooping";
          container limit {
            description
              "DHCP Snooping limit";
            leaf rate {
              description
                "DHCP Snooping limit";
              type uint16 {
                range "1..2048";
              }
            }
          }
          leaf trust {
            description
              "DHCP Snooping trust config";
            type empty;
          }
          list vlan {
            description
              "DHCP Snooping vlan";
            key "id";
            max-elements "1";
            leaf id {
              type uint16 {
                range "1..4094";
              }
            }
            container information {
              description
                "DHCP Snooping information";
              container option {
                description
                  "DHCP Snooping information option";
                container format-type {
                  description
                    "Option 82 information format";
                  container circuit-id {
                    description
                      "Circuit id option 82 format";
                    leaf string {
                      description
                        "User defined string for circuit id";
                      type string {
                        length "3..63";
                      }
                    }
                  }
                }
              }
            }
          }
        }
      }
      // interface * / ip mtu
      leaf mtu {
        description
          "Set IP Maximum Transmission Unit";
        type uint16 {
          range "68..9198";
        }
      }
       // interface * / no ip mroute-cache
      leaf mroute-cache {
        description
          "Enable switching cache for incoming multicast packets";
        tailf:cli-boolean-no;
        tailf:cli-trim-default;
        type boolean;
      }

      // interface * / ip nat
      container nat {
        description
          "NAT interface commands";
        leaf allow-static-host {
          description
            "Allow static-ip clients";
          type empty;
        }
        leaf enable {
          description
            "Enable Address Translation (NVI)";
          type empty;
        }
        choice nat-choice {
          leaf inside {
            description
              "Inside interface for address translation";
            type empty;
          }
          leaf outside {
            description
              "Outside interface for address translation";
            type empty;
          }
        }
      }
      // interface * / ip rsvp
      container rsvp {
        description
          "RSVP Interface Commands";
        container bandwidth {
          description
            "RSVP Reservable Bandwidth (kbps)";
          tailf:cli-reset-container;
          presence "true";
        }
        container signalling {
          description
            "IP RSVP signalling";
          leaf hello {
            description
              "Enable neighbor-down detection";
            type empty;
          }
          leaf blockade {
            description
              "(Re)sets time duration of blockade state";
            type empty;
          }
          leaf dscp {
            description
              "DSCP for RSVP signalling messages";
            type empty;
          }
          leaf fast-local-repair {
            description
              "Fast Local Repair parameters";
            type empty;
          }
        }
        container resource-provider {
          description
            "RSVP resource provider";
          choice resource-provider-choice {
            leaf none {
              description
                "Associates NO resources with reservations";
              type empty;
            }
            leaf wfq {
              description
                "Associates WFQ resources with reservations";
              type enumeration {
                enum "interface";
                enum "pvc";
              }
            }
          }
        }
      }

      // interface * / ip summary-address
      container summary-address {
        list eigrp {
          tailf:cli-suppress-mode;
          tailf:cli-compact-syntax;
          key id;
          leaf id {
            type string;
          }
          leaf ip {
            tailf:cli-drop-node-name;
            type inet:ipv4-address;
          }
          leaf mask {
            tailf:cli-drop-node-name;
            type inet:ipv4-address;
          }
          leaf metric {
            tailf:cli-drop-node-name;
            type uint32;
          }
        }
      }

      // interface * / ip verify
      container verify {
        description
          "Enable per packet validation";
        container source {
          description
            "Validation of source address";
          presence true;
          container vlan {
            description
              "vlan specification";
            container dhcp-snooping {
              description
                "snooping enable vlan";
              presence true;
              leaf port-security {
                description
                  "port security";
                type empty;
              }
            }
          }
        }
        container unicast {
          description
            "Enable per packet validation for unicast";
          container reverse-path {
            description
              "Reverse path validation of source address (old command format)";
            presence "true";
          }
          container source {
            description
              "Validation of source address";
            tailf:cli-compact-syntax;
            tailf:cli-sequence-commands {
              tailf:cli-reset-all-siblings;
            }
            leaf reachable-via {
              description
                "Specify reachability check to apply to the source address";
              type enumeration {
                enum "any";
                enum "rx";
              }
            }
            leaf allow-self-ping {
              tailf:cli-break-sequence-commands;
              description
                "Allow router to ping itself (opens vulnerability in verification)";
              type empty;
            }
            leaf allow-default {
              description
                "Allow default route to match when checking source address";
              type empty;
            }
          }
        }
      }
      // interface * / ip wccp
      container wccp {
        description
          "WCCP IPv4 interface commands";
        uses interface-ip-wccp-grouping;
        container redirect {
          description
            "Set packet redirection options";
          container exclude {
            description
              "Exclude packets from redirection";
            leaf in {
              description
                "Exclude inbound packets from outbound redirection";
              type empty;
            }
          }
        }
        list vrf {
          description
            "Configure WCCP for a VRF";
          tailf:cli-suppress-mode;
          key "name";
          leaf name {
            type string;
          }
          uses interface-ip-wccp-grouping;
        }
      }
    }
    // interface * / ipv6
    container ipv6 {
      description
        "IPv6 interface subcommands";
      // interface * / ipv6 dhcp
      container dhcp {
        description 
          "IPv6 DHCP interface subcommands";
        container guard {
          description "Configure IPv6 DHCP guard on the interface";
          presence true;
          leaf attach-policy {
            description "Apply a policy for feature DHCP Guard";
            type string;            
          }
        }
        list server {
          description 
            "Act as an IPv6 DHCP server";
          tailf:cli-suppress-mode;
          key "word";
          leaf word {
            type string;
          }
          leaf preference {
            description 
              "Preference";
            type uint8 {
              range "0..255";
            }
          }
        }
      }
      container destination-guard {
        description "Configure ipv6 destination guard on the interface";
        presence true;
        leaf attach-policy {
          description "Apply a policy for feature ipv6 destguard";
          type string;
        }
      }
      // interface * / ipv6 address
      container address {
        description
          "Configure IPv6 address on interface";
        choice address-choice {
          case dhcp-case {
            leaf dhcp {
              description "Obtain a ipv6 address using dhcp";
              type empty;
            }
          }
          case autoconfig-case {
            container autoconfig {
              description
                "Obtain address using autoconfiguration";
              presence "true";
              leaf default {
                description
                  "Insert default route";
                type empty;
              }
            }
          }
          case manual-case {
            list prefix-list {
              tailf:cli-drop-node-name;
              tailf:cli-suppress-mode;
              tailf:cli-delete-when-empty;
              key "prefix";
              leaf prefix {
                type ios:ipv6-prefix;
              }
              leaf anycast {
                description
                  "Configure as an anycast";
                tailf:cli-full-command;
                type empty;
              }
              leaf eui-64 {
                description
                  "Use eui-64 interface identifier";
                tailf:cli-full-command;
                type empty;
              }
            }
          }
          case link-local-case {
            list link-local-address {
              tailf:cli-drop-node-name;
              tailf:cli-suppress-mode;
              tailf:cli-delete-when-empty;
              key "address";
              leaf address {
                type inet:ipv6-address;
              }
              leaf link-local {
                description
                  "Use link-local address";
                tailf:cli-full-command;
                type empty;
              }
            }
          }
        }
      }
      // interface * / ipv6 enable
      leaf enable {
        description
          "Enable IPv6 on interface";
        type empty;
      }
      // interface * / ipv6 flow
      container flow {
        description
          "NetFlow related commands";
        leaf ingress {
          description
            "Enable inbound NetFlow";
          type empty;
        }
        leaf egress {
          description
            "Enable outbound NetFlow";
          type empty;
        }
        uses interface-ip-monitor-grouping;
      }

      // interface * / ipv6 ospf
      container ospf {
        description
          "OSPF interface commands";
        list process {
          tailf:cli-suppress-mode;
          tailf:cli-delete-when-empty;
          tailf:cli-drop-node-name;
          tailf:cli-compact-syntax;
          tailf:cli-sequence-commands {
            tailf:cli-reset-siblings;
          }
          key "id";
          leaf id {
            type uint16 {
              range "1..65535";
            }
          }
          leaf area {
            description
              "Set the OSPF area ID";
            type union {
              type uint32 {
                range "0..4294967295";
              }
              type inet:ipv4-address;
            }
          }
          leaf instance {
            description
              "Set the OSPF instance";
            type union {
              type uint8 {
                range "0..31";
              }
              type uint8 {
                range "32..255";
              }
            }
          }
        }
        // interface * / ipv6 ospf authentication
        container authentication {
          description
            "Enable authentication";
          leaf null {
            description
              "Use no authentication";
            type empty;
          }
          uses authentication-ipsec-grouping;
        }
        // interface * / ipv6 ospf bfd
        uses interface-ospf-bfd-grouping;
        // interface * / ipv6 ospf cost
        leaf cost {
          description
            "Route cost of this interface";
          type uint16 {
            range "1..65535";
          }
        }
        // interface * / ipv6 ospf database-filter
        container database-filter {
          description
            "Filter OSPF LSA during synchronization and flooding";
          choice database {
            leaf all {
              description
                "Filter all LSA";
              type enumeration {
                enum "out";
              }
            }
            leaf disable {
              description
                "Disable LSA Filter on this interface";
              type empty;
            }
          }
        }
        // interface * / ipv6 ospf dead-interval
        uses interface-ospf-dead-interval-grouping;
        // interface * / ipv6 ospf demand-circuit
        container demand-circuit {
          description
            "OSPF demand circuit";
          presence "true";
          leaf disable {
            description
              "Disable demand circuit on this interface";
            tailf:cli-full-command;
            type empty;
          }
          leaf ignore {
            description
              "Ignore demand circuit auto-negotiation requests";
            tailf:cli-full-command;
            type empty;
          }
        }
        // interface * / ipv6 ospf encryption
        uses interface-ospf-encryption-grouping;
        // interface * / ipv6 ospf flood-reduction
        container flood-reduction {
          description
            "OSPF Flood Reduction";
          presence "true";
          leaf disable {
            description
              "Disable Flood Reduction on this interface";
            type empty;
          }
        }
        // interface * / ipv6 ospf hello-interval
        uses interface-ospf-hello-interval-grouping;
        // interface * / ipv6 ospf mtu-ignore
        container mtu-ignore {
          description
            "Ignores the MTU in DBD packets";
          presence "true";
          leaf disable {
            description
              "Disable Ingore MTU on this interface";
            type empty;
          }
        }
        // interface * / ipv6 ospf neighbor
        uses interface-ospf-neighbor-grouping;
        //  interface * / ipv6 ospf network
        uses interface-ospf-network-grouping;
        // interface * / ipv6 ospf priority
        uses interface-ospf-priority-grouping;
        // interface * / ipv6 ospf retransmit-interval
        uses interface-ospf-retransmit-interval-grouping;
        // interface * / ipv6 ospf shutdown
        container shutdown {
          description
            "Shut down the interface in OSPFv3";
          presence "true";
          leaf disable {
            description
              "Disable inherited shutdown";
            type empty;
          }
        }
        // interface * / ipv6 ospf transmit-delay
        uses interface-ospf-transmit-delay-grouping;
      }


      // interface * / ipv6 mtu
      leaf mtu {
        description
          "Set IPv6 Maximum Transmission Unit";
        type uint16 {
          range "1280..9198";
        }
      }
      //interface * / ipv6 nd
      container nd {
        description
          "IPv6 interface Neighbor Discovery subcommands";
        container raguard {
          description
            "Configure RA guard on the interface";
          leaf attach-policy {
            description
              "Apply a policy for feature RA guard";
            type string;
          }
        }
      }
      // interface * / ipv6 redirects
      leaf redirects {
        description
          "Enable sending ICMP Redirect messages";
        tailf:cli-boolean-no;
        tailf:cli-trim-default;
        type boolean;
      }

      // interface * / ipv6 rip
      list rip {
        description
          "Configure RIP routing protocol";
        tailf:cli-suppress-mode;
        key "id";
        leaf id {
          type string;
        }
        leaf enable {
          description
            "Enable/disable RIP routing";
          tailf:cli-full-command;
          type empty;
        }
        container default-information {
          description
            "Configure handling of default route";
          tailf:cli-compact-syntax;
          tailf:cli-sequence-commands;
          leaf route {
            tailf:cli-drop-node-name;
            type enumeration {
              enum "only";
              enum "originate";
            }
          }
          leaf metric {
            description
              "Default route metric";
            tailf:cli-optional-in-sequence;
            type uint8 {
              range "1..15";
            }
          }
        }
      }


      // interface * / ipv6 pim
      choice ipv6-pim-choice {
        container no-pim {
          tailf:cli-drop-node-name;
          leaf pim {
            description
              "PIM interface commands";
            tailf:cli-boolean-no;
            tailf:cli-trim-default;
            type boolean;
          }
        }
        // interface * / ipv6 pim
        container pim {
          description
            "PIM interface commands";
          leaf bfd {
            description
              "Configure BFD";
            tailf:cli-full-command;
            type empty;
          }
          container bsr {
            description
              "Configure BSR";
            leaf border {
              description
                "Border of PIM BSR domain";
              type empty;
            }
          }
          leaf dr-priority {
            description
              "PIM Hello DR priority";
            tailf:cli-full-command;
            type uint32;
          }
        }
      }
      // interface * / ipv6 traffic-filter
      list traffic-filter {
        description
          "Access control list for packets";
        tailf:cli-compact-syntax;
        tailf:cli-suppress-mode;
        tailf:cli-delete-when-empty;
        key "direction";
        leaf direction {
          type enumeration {
            enum "in";
            enum "out";
          }
        }
        leaf access-list {
          tailf:cli-drop-node-name;
          tailf:cli-prefix-key;
          type string;
        }        
      }
    }
    // interface * / lisp
    container lisp {
      description
        "Locator/ID Separation Protocol";
      leaf extended-subnet-mode {
        description
          "Configures to enable extended subnet mode on the interface";
        tailf:cli-full-command;
        type empty;
      }
      container mobility {
        description
          "Configures to allow EID mobility on interface";
        container dynamic-eid {
          tailf:cli-drop-node-name;
          tailf:cli-sequence-commands;
          tailf:cli-compact-syntax;
          leaf dynamic-eid-name {
            tailf:cli-drop-node-name;
            type string;
          }
          leaf nbr-proxy-reply {
            description
              "Neighbor proxy reply behavior for dynamic EID group";
            tailf:cli-optional-in-sequence;
            tailf:cli-incomplete-command;
            type empty;
          }
          leaf requests {
            description
              "Send neighbor proxy reply after reaching request threshold";
            tailf:cli-optional-in-sequence;
            type uint8 {
              range "0..5";
            }
          }
        }
        container discover {
          description
            "Configure mobility dynamic EID discover settings";
          leaf arp {
            description
              "Dynamic EID discover through ARP events on this interface";
            tailf:cli-trim-default;
            tailf:cli-boolean-no;
            type boolean;
          }
        }
        container liveness {
          description
            "Configure mobility liveness settings";
          leaf test {
            description
              "Perform liveness test on dynamic-EID discovered on this interface";
            tailf:cli-trim-default;
            tailf:cli-boolean-no;
            type boolean;
          }
          leaf ttl {
            description
              "Configures the TTL in the liveness test packet";
            type uint8 {
              range "2..255";
            }
          }
        }
      }
    }
    // interface * / load-interval
    leaf load-interval {
      description
        "Specify interval for load calculation for an interface";
      type uint16 {
        range "0..600";
      }
    }
    // interface * / logging
    container logging {
      description
        "Configure logging for interface";
      container event {
        description
          "Interface events";
        leaf bundle-status {
          description
            "BUNDLE/UNBUNDLE messages";
          tailf:cli-full-command;
          type empty;
        }
        leaf link-status {
          description
            "UPDOWN and CHANGE messages";
          tailf:cli-full-command;
          type empty;
        }
        leaf trunk-status {
          description
            "TRUNK status messages";
          tailf:cli-full-command;
          type empty;
        }
        leaf nfas-status {
          description
            "NFAS D-channel status messages";
          tailf:cli-full-command;
          type empty;
        }
        leaf power-inline-status {
             description
                "Inline power messages";
             type empty;
        }
        leaf status {
          description
            "Spanning-tree state change messages";
          type empty;
        }
        container spanning-tree {
          description
            "Spanning-tree Interface events";
          presence "true";
          leaf status {
            description
              "Spanning-tree state change messages";
            tailf:cli-full-command;
            type empty;
          }
        }
        container subif-link-status {
          description
            "Sub-interface UPDOWN and CHANGE messages";
          presence "true";
          leaf ignore-bulk {
            description
              "Do not log messages when the main interface is transitioning";
            tailf:cli-full-command;
            type empty;
          }
        }
      }
    }    
    // interface * / mdix
    container mdix {
      description
        "Set Media Dependent Interface with Crossover";
      leaf auto {
        tailf:cli-full-command;
        tailf:cli-boolean-no;
        tailf:cli-trim-default;
        type boolean;
      }
    }

    // interface * / mop
    container mop {
      leaf enabled {
        tailf:cli-full-command;
        tailf:cli-boolean-no;
        tailf:cli-trim-default;
        type boolean;
      }
    }
    // interface * / max-reserved-bandwidth
    leaf max-reserved-bandwidth {
      description
        "Maximum Reservable Bandwidth on an Interface";
      tailf:cli-full-command;
      type uint8 {
        range "1..100";
      }
    }


    // interface * / mls
    container mls {
      description
        "mls sub/interface commands";
      container qos-channel-consistency {
        tailf:cli-drop-node-name;
        container qos {
          description
            "qos command keyword";
          leaf channel-consistency {
            description
              "enable or disable qos consistency checks";
            tailf:cli-full-command;
            tailf:cli-boolean-no;
            tailf:cli-trim-default;
            type boolean;
          }
        }
      }
      container qos {
        description
          "qos command keyword";
        container trust {
          description
            "trust keyword";
          leaf cos {
            type empty;
          }
          leaf "dscp" {
            type empty;
          }
          leaf "ip-precedence" {
            type empty;
          }
          leaf device {
            type enumeration {
              enum "cisco-phone";
              enum "cts";
              enum "ip-camera";
              enum "media-player";
            }
          }
        }
        leaf vlan-based {
          description
            "vlan-based keyword";
          tailf:cli-full-command;
          type empty;
        }
      }
    }
    // interface * / mtu
    leaf mtu {
      description
        "Set the interface Maximum Transmission Unit (MTU)";
      tailf:cli-full-command;
      type uint16 {
        range "64..18000";
      }
    }

    // interface * / ospfv3
    container ospfv3 {
      description
        "OSPFv3 interface commands";
      list process-id {
        tailf:cli-drop-node-name;
        tailf:cli-suppress-mode;
        tailf:cli-delete-when-empty;
        tailf:cli-reset-container;
        key "id";
        leaf id {
          type uint16;
        }
        uses interface-ospfv3-process-id-grouping;
        //interface * / ospfv3 * ipv4
        container ipv4 {
          description
            "Specify parameters for IPv4";
          list area {
            tailf:cli-suppress-mode;
            description
              "Set the OSPF area ID";
            key "id";
            leaf id {
              type ospf-area-type;
            }
            leaf instance {
              description
                "Set the OSPF instance";
              type uint8 {
                range "64..95";
              }
            }
          }
          uses interface-ospfv3-process-id-grouping;
        }
        //interface * / ospfv3 * ipv6
        container ipv6 {
          description
            "Specify parameters for IPv6";
          list area {
            tailf:cli-suppress-mode;
            description
              "Set the OSPF area ID";
            key "id";
            leaf id {
              type ospf-area-type;
            }
            leaf instance {
              description
                "Set the OSPF instance";
              type uint8 {
                range "0..31";
              }
            }
          }
          uses interface-ospfv3-process-id-grouping;
        }
      }
      // interface * / ospfv3 authentication
      container authentication {
        description
          "Enable authentication";
        leaf key-chain {
          description
            "Use a key-chain for cryptographic authentication keys";
          tailf:cli-full-command;
          type string;
        }
        leaf null {
          tailf:cli-full-command;
          description
            "Use no authentication";
          type empty;
        }
        uses authentication-ipsec-grouping;
      }
      // interface * / ospfv3 bfd
      uses interface-ospf-bfd-grouping;
      // interface * / ospfv3 cost
      uses interface-ospfv3-cost-grouping;
      // interface * / ospfv3 database-filter
      container database-filter {
        description
          "Filter OSPF LSA during synchronization and flooding";
        leaf all {
          description
            "Filter all LSA";
          type enumeration {
            enum "out";
          }
        }
      }
      // interface * / ospfv3 dead-interval
      uses interface-ospf-dead-interval-grouping;
      // interface * / ospfv3 demand-circuit
      container demand-circuit {
        description
          "OSPF Demand Circuit";
        presence "true";
        leaf ignore {
          description
            "Ignore demand circuit auto-negotiation requests";
          type empty;
        }
      }
      // interface * / ospfv3 encryption
      uses interface-ospf-encryption-grouping;
      // interface * / ospfv3 flood-reduction
      leaf flood-reduction {
        description
          "OSPF Flood Reduction";
        type empty;
      }
      // interface * / ospfv3 hello-interval
      uses interface-ospf-hello-interval-grouping;
      // interface * / ospfv3 manet
      uses interface-ospfv3-manet-grouping;
      // interface * / ospfv3 mtu-ignore
      leaf mtu-ignore {
        description
          "Ignores the MTU in DBD packets";
        type empty;
      }
      // interface * /  ospfv3 multi-area
      container multi-area {
        description
          "Set the OSPF multi-area ID";
        tailf:cli-sequence-commands;
	tailf:cli-compact-syntax;
        leaf id {
          tailf:cli-drop-node-name;
          type ospf-area-type;
        }
        leaf cost {
          description
            "Interface cost";
          tailf:cli-optional-in-sequence;
          type uint32 {
            range "1..65535";
          }
        }
      }
      // interface * /  ospfv3 neighbor
      uses interface-ospf-neighbor-grouping;
      // interface * /  ospfv3 network
      uses interface-ospf-network-grouping;
      // interface * / ospfv3 prefix-suppression
      uses interface-ospf-prefix-suppression-grouping;
      // interface * /  ospfv3 priority
      uses interface-ospf-priority-grouping;
      // interface * /  ospfv3 retransmit-interval
      uses interface-ospf-retransmit-interval-grouping;
      // interface * / ospfv3 shutdown
      leaf shutdown {
        description
          "Shut down the interface in OSPFv3";
        type empty;
      }
      // interface * / ospfv3 transmit-delay
      uses interface-ospf-transmit-delay-grouping;
    }

    // interface * / power
    container power {
      container inline {
        leaf consumption {
          tailf:cli-full-command;
          type uint16 {
            range "4000..15400";
          }
        }
        leaf never {
          type empty;
        }
        container auto{
          description
            "Automatically detect and power inline devices";
          presence true;
          leaf max {
            description
              "Maximum power allowed on this interface";
            type int16 {
               range "4000..30000";
            }
          }
        }
        container police {
          description
            "Police the power drawn on the port";
          presence true;
          container action {
            description
              "Action to be taken when power is overdrawn on the port";
            leaf errdisable{
              description
                "Error-disable the port when power is overdrawn on the port";
              type empty;
            }
            leaf log {
              description
                "Log a message when power is overdrawn on the port";
              type empty;
            }
          }
        }
        container static {
          description
            "High priority inline power interface";
          presence true;
          leaf max {
            description
              "Maximum power allowed on this interface";
            type int16 {
               range "4000..30000";
            }
          }
        }
      }
    }
    // interface * / qos
    container interface_qos {
      tailf:alt-name "qos";
      container trust {
        leaf device {
          type enumeration {
            enum "cisco-phone";
          }
        }
      }
    }
    // interface * / service-policy
    container service-policy {
      description
        "Configure QoS Service Policy";
      leaf history {
        tailf:cli-full-command;
        description
          "Keep history of QoS metrics";
        type empty;
      }
      leaf input {
        tailf:cli-full-command;
        description
          "Assign policy-map to the input of an interface";
        type string;
        tailf:non-strict-leafref {
          path "/ios:native/policy-map/name";
        }
      }
      leaf output {
        tailf:cli-full-command;
        description
          "Assign policy-map to the output of an interface";
        type string;
        tailf:non-strict-leafref {
          path "/ios:native/policy-map/name";
        }
      }
      container type {
        description
          "Configure CPL Service Policy";
        container control {
          tailf:info "Apply a control policy to the interface";
          leaf subscriber {
            tailf:info "Apply a subscriber control policy to the interface";
            tailf:cli-diff-dependency "/ios:native/policy-map";
            type string;
          }
        }
        container performance-monitor {
          description
            "Configure media monitor service-policy type";
          tailf:cli-sequence-commands;
          tailf:cli-compact-syntax;
          leaf direction {
            tailf:cli-drop-node-name;
            type enumeration {
              enum "input";
              enum "output";
            }
          }
          leaf name {
            tailf:cli-drop-node-name;
            type string;
            tailf:non-strict-leafref {
              path "/ios:native/policy-map/name";
            }
          }
        }
        // interface * / service-policy type * / service-chain
        container service-chain {
          description
            "Configure Service-chain Service Policy";
          tailf:cli-compact-syntax;
           container input {
               description "Assign policy-map to the input of an interface";
               leaf name {
                  tailf:cli-drop-node-name;
                  type string;
                  tailf:non-strict-leafref {
                     path "/ios:native/policy-map/name";
                  }
               }
            }
           container output {
               description "Assign policy-map to the output of an interface";
               leaf name {
                  tailf:cli-drop-node-name;
                  type string;
                  tailf:non-strict-leafref {
                    path "/ios:native/policy-map/name";
                  }
               }
           }
        }
      }
    }
    // interface * / service-insertion
    leaf service-insertion {
      description
        "Service-insertion AppNav Controller";
      type enumeration {
        enum "waas";
      }
    }
    // interface * / shutdown
    leaf shutdown {
      description
        "Shutdown the selected interface";
      tailf:cli-full-command;
      type empty;
    }
    // interface * / standby
    container standby {
      description
        "HSRP interface configuration commands";
      leaf version {
        description
          "HSRP version";
        tailf:cli-full-command;
        type enumeration {
          enum "1";
          enum "2";
        }
      }
      // interface * / standby bfd
      leaf bfd {
        description
          "Enable HSRP BFD";
        type empty;
      }
      // interface * / standby delay
      container delay {
        description
          "HSRP initialisation delay";
        tailf:cli-compact-syntax;
        leaf minimum {
          description
            "Minimum delay";
          type uint16 {
            range "0..10000";
          }
        }
        leaf reload {
          description
            "Delay after reload";
          type uint16 {
            range "0..10000";
          }
        }
      }
      // interface * / standby mac-refresh
      leaf mac-refresh {
        description
          "Refresh MAC cache on switch by periodically sending packet from virtual mac address";
        type uint8 {
          range "0..255";
        }
      }
      // interface * / standby use-bia
      container use-bia {
        description
          "HSRP uses interface's burned in address";
        presence "true";
        container scope {
          description
            "Specify the scope of use-bia";
          leaf interface {
            description
              "Use-bia applies to all groups on this interface or sub-interface";
            type empty;
          }
        }
      }
      // interface * / standby *
      list standby-list {
        tailf:cli-drop-node-name;
        tailf:cli-suppress-mode;
        tailf:cli-delete-when-empty;
        tailf:cli-incomplete-command;
        key "group-number";
        leaf group-number {
          tailf:cli-suppress-range;
          type uint16;
        }
        container authentication {
          description
            "Authentication";
          choice auth {
            leaf word {
              tailf:cli-drop-node-name;
              tailf:cli-disallow-value "md5|text";
              type string;
            }
            container md5 {
              description
                "Use MD5 authentication";
              leaf key-chain {
                description
                  "Set key chain";
                type string;
              }
              container key-string {
                description
                  "Set key string";
                tailf:cli-compact-syntax;
                leaf encrypt {
                  tailf:cli-drop-node-name;
                  type enumeration {
                    enum "0";
                    enum "7";
                  }
                }
                leaf string {
                  tailf:cli-drop-node-name;
                  type string;
                }
                leaf timeout {
                  description
                    "Set timeout";
                  type uint16 {
                    range "0..32767";
                  }
                }
              }
            }
            leaf text {
              description
                "Plain text authentication";
              type string;
            }
          }
        }
        leaf follow {
          description
            "Name of HSRP group to follow";
          type string;
        }
        container ip {
          description
            "Enable HSRP and set the virtual IP address";
          tailf:cli-sequence-commands;
          tailf:cli-compact-syntax;
          presence "true";
          leaf address {
            tailf:cli-drop-node-name;
            type inet:ipv4-address;
          }
          leaf secondary {
            description
              "Make this IP address a secondary virtual IP address";
            type empty;
          }
        }
        leaf ipv6 {
          description
            "Enable HSRP IPv6";
          type union {
            type inet:ipv6-address;
            type ios:ipv6-prefix;
            type enumeration {
              enum "autoconfig";
            }
          }
        }
        leaf mac-address {
          description
            "Virtual MAC address";
          type string;
        }
        leaf name {
          description
            "Redundancy name string";
          tailf:cli-full-command;
          type string;
        }
        container preempt {
          description
            "Overthrow lower priority Active routers";
          presence "true";
          container delay {
            description
              "Wait before preempting";
            tailf:cli-compact-syntax;
            leaf minimum {
              description
                "Delay at least this long";
              type uint16 {
                range "0..3600";
              }
            }
            leaf reload {
              description
                "Delay after reload";
              type uint16 {
                range "0..3600";
              }
            }
            leaf sync {
              description
                "Wait for IP redundancy client";
              type uint16 {
                range "0..3600";
              }
            }
          }
        }
        leaf priority {
          description
            "Priority level";
          tailf:cli-full-command;
          type uint8;
        }
        container redirect {
          description
            "Configure sending of ICMP Redirect messages with an HSRP virtual IP address as the gateway IP address";
          container advertisement {
            description
              "Redirect advertisement messages";
            container authentication {
              description
                "Authentication";
              container md5 {
                description
                  "Use MD5 authentication";
                leaf key-chain {
                  description
                    "Set key chain";
                  type string;
                }
                container key-string {
                  description
                    "Set key string";
                  tailf:cli-compact-syntax;
                  tailf:cli-sequence-commands {
                    tailf:cli-reset-siblings;
                  }
                  leaf encrypt {
                    tailf:cli-drop-node-name;
                    type enumeration {
                      enum "0";
                      enum "7";
                    }
                  }
                  leaf string {
                    tailf:cli-drop-node-name;
                    type string;
                  }
                  leaf timeout {
                    description
                      "Set timeout";
                    type uint16 {
                      range "0..32767";
                    }
                  }
                }
              }
            }
          }
          container timers {
            description
              "Adjust redirect timers";
            tailf:cli-compact-syntax;
            tailf:cli-sequence-commands {
              tailf:cli-reset-siblings;
            }
            leaf advertisement {
              tailf:cli-drop-node-name;
              type uint16 {
                range "10..180";
              }
            }
            leaf holddown {
              tailf:cli-drop-node-name;
              type uint16 {
                range "30..3600";
              }
            }
          }
          leaf unknown {
            description
              "Redirect to non-HSRP routers";
            type empty;
          }
        }
        container timers {
          description
            "Hello and hold timers";
          tailf:cli-compact-syntax;
          tailf:cli-sequence-commands {
            tailf:cli-reset-siblings;
          }
          container hello-interval {
            tailf:cli-drop-node-name;
            tailf:cli-flatten-container;
            tailf:cli-compact-syntax;
            choice hello-interval-choice {
              leaf seconds {
                tailf:cli-drop-node-name;
                tailf:cli-incomplete-command;
                type uint8 {
                  range "1..254";
                }
              }
              leaf msec {
                description
                  "Specify hello interval in milliseconds";
                tailf:cli-incomplete-command;
                type uint16 {
                  range "15..999";
                }
              }
            }
          }
          container hold-time {
            tailf:cli-drop-node-name;
            tailf:cli-flatten-container;
            tailf:cli-compact-syntax;
            choice hold-time-choice {
              leaf seconds {
                tailf:cli-drop-node-name;
                type uint8 {
                  range "1..255";
                }
              }
              leaf msec {
                description
                  "Specify hold time in milliseconds";
                type uint16 {
                  range "50..3000";
                }
              }
            }
          }
        }
        list track {
          description
            "Priority tracking";
          tailf:cli-suppress-mode;
          key "number";
          leaf number {
            type uint16 {
              range "1..1000";
            }
          }
          leaf decrement {
            description
              "Priority decrement";
            tailf:cli-full-command;
            type uint8;
          }
          leaf shutdown {
            description
              "Shutdown group";
            tailf:cli-full-command;
            type empty;
          }
        }
      }
    }
    // interface * / access-session
    container access-session {
      description "Access Session specific Interface Configuration Commands";
      leaf closed {
        description
          "Enable closed access on port (disabled by default, i.e. open access)";
        type empty;  
      }
      container port-control {
        description "Set the port-control value";
        leaf auto {
          description "PortState set to automatic";
          type empty;
        }
      }
      leaf host-mode {
        description
          "Set the Host mode for authentication on this interface";
        type enumeration {
          enum "multi-auth";
          enum "multi-domain";
          enum "multi-host";
          enum "single-host";
        }
      }
    }
    // interface * / storm-control
    container storm-control {
      description
        "storm configuration";
      container action {
        description
          "Action to take for storm..control;";
        leaf level {
          description
            "Set storm suppression level on this interface";
          type decimal64 {
            fraction-digits 2;
            range "0..100";
          }
        }        
        leaf shutdown {
          description
            "Shutdown this interface if a storm occurs";
          type empty;
        }
        leaf trap {
          description
            "Send SNMP trap if a storm occurs";
          type empty;
        }
      }
      container broadcast {
        description
          "Broadcast address storm control";
        container include {  // not in 3850
          leaf multicast {
            type empty;
          }
        }
        container level {  
          description
            "Set storm suppression level on this interface";
          leaf threshold{
            tailf:cli-drop-node-name;
            description
              "Broadcast address storm control";
            type decimal64 {
              fraction-digits 2;
              range "0..100";
            }
          }
          container bps {
            description
              "Enter suppression level in bits per second";
	    tailf:cli-sequence-commands;
	    tailf:cli-compact-syntax;
            leaf rising-threshold {
              tailf:cli-drop-node-name;
              tailf:cli-full-command;
              description
	        "Enter rising threshold - <0.0 - 10000000000.0>[k|m|g]>";
              type storm-control-threshold-type;
            }
	    leaf falling-threshold  {
              tailf:cli-drop-node-name; 
              description
               "Enter falling threshold - <0.0 - 10000000000.0>[k|m|g]> ";
	      type storm-control-threshold-type;
            }
          }
          container pps {
            description
              "Enter suppression level in packets per second";
	    tailf:cli-sequence-commands;
	    tailf:cli-compact-syntax;
	    leaf rising-threshold {
              tailf:cli-drop-node-name;
              tailf:cli-full-command;
              description
		"Enter rising threshold - <0.0 - 10000000000.0>[k|m|g]";
              type storm-control-threshold-type;
            }
            leaf falling-threshold  {
              tailf:cli-drop-node-name; 
              description
                "Enter falling threshold - <0.0 - 10000000000.0>[k|m|g] ";
              type storm-control-threshold-type;
            }
          }
        }
      }
      container multicast {
        description
          "Multicast address storm control";
        container level {
          description
            "Set storm suppression level on this interface";
          leaf threshold{
            tailf:cli-drop-node-name;
            description
              "Broadcast address storm control";
            type decimal64 {
              fraction-digits 2;
              range "0..100";
            }
          }
	  container bps {
            description
              "Enter suppression level in bits per second";
	    tailf:cli-sequence-commands;
	    tailf:cli-compact-syntax;
            leaf rising-threshold {
              tailf:cli-drop-node-name;
              tailf:cli-full-command;
              description
	        "Enter rising threshold - <0.0 - 10000000000.0>[k|m|g]";
              type storm-control-threshold-type;
            }
            leaf falling-threshold  {
              tailf:cli-drop-node-name; 
              description
                "Enter falling threshold - <0.0 - 10000000000.0>[k|m|g] ";
              type storm-control-threshold-type;
            }
          }
	  container pps {
            description
              "Enter suppression level in packets per second";
	    tailf:cli-sequence-commands;
	    tailf:cli-compact-syntax;
	    leaf rising-threshold {
              tailf:cli-drop-node-name;
              tailf:cli-full-command;
              description
		"Enter rising threshold - <0.0 - 10000000000.0>[k|m|g]";
              type storm-control-threshold-type;
            }
            leaf falling-threshold {
              tailf:cli-drop-node-name; 
              description
                "Enter falling threshold - <0.0 - 10000000000.0>[k|m|g]";
              type storm-control-threshold-type;
            }
          }
        } 
      }
      container unicast {
        description
          "Unicast address storm control";
        container level {
          description
            "Set storm suppression level on this interface";
          container threshold {
	    tailf:cli-drop-node-name;
	    tailf:cli-sequence-commands;
	    tailf:cli-compact-syntax;
	    leaf rising-threshold {
              tailf:cli-drop-node-name;
              description
                "Broadcast address storm control";
              type decimal64 {
                fraction-digits 2;
                range "0..100";
              } 
            }
	    leaf falling-threshold {
              tailf:cli-drop-node-name;
              description
                "Broadcast address storm control";
              type decimal64 {
                fraction-digits 2;
                range "0..100";
              }
            }
	  }
          container bps {
            description
              "Enter suppression level in bits per second";
	    tailf:cli-sequence-commands;
	    tailf:cli-compact-syntax;
            leaf rising-threshold {
              tailf:cli-drop-node-name;
              tailf:cli-full-command;
              description
		"Enter rising threshold - <0.0 - 10000000000.0>[k|m|g]";
              type storm-control-threshold-type;
            }
	    leaf falling-threshold  {
              tailf:cli-drop-node-name; 
              description
                "Enter falling threshold - <0.0 - 10000000000.0>[k|m|g]";
              type storm-control-threshold-type;              
            }
          }
	  container pps {
            description
              "Enter suppression level in packets per second";
	    tailf:cli-sequence-commands;
	    tailf:cli-compact-syntax;
	    leaf rising-threshold {
              tailf:cli-drop-node-name;
              tailf:cli-full-command;
              description
	        "Enter rising threshold - <0.0 - 10000000000.0>[k|m|g]";
              type storm-control-threshold-type;
            }
            leaf falling-threshold  {
              tailf:cli-drop-node-name; 
              description
                "Enter falling threshold - <0.0 - 10000000000.0>[k|m|g]";
              type storm-control-threshold-type;
            }
          }
        }  
      }
    }
    // interface * / trust
    container trust {
      description
        "Set trust value for the interface";
      leaf device {
        description
          "trusted device class";
        type enumeration {
          enum cisco-phone;
          enum cts;
          enum ip-camera;
          enum media-player;
        }
      }
    }

    // interface * / utd
    container utd {
      description
        "UTD support on this interface";
      leaf enable {
        description
          "Enable threat defense on this interface";
        type empty;
      }
    }


    // interface * / wrr-queue
    container wrr-queue {
      description
        "Configure weighted round-robin xmt queues";
      container bandwidth {
        description
          "Configure WRR minimum bandwidth with weights or percentages";
        tailf:cli-compact-syntax;
        tailf:cli-sequence-commands {
          tailf:cli-reset-siblings;
        }
        choice bandwidth-choice {
          case a {
            leaf weight-1 {
              tailf:cli-drop-node-name;
              type uint8 {
                range "0..255";
              }
            }
            leaf weight-2 {
              tailf:cli-drop-node-name;
              type uint8 {
                range "0..255";
              }
            }
            leaf weight-3 {
              tailf:cli-drop-node-name;
              type uint8 {
                range "0..255";
              }
            }
            leaf weight-4 {
              tailf:cli-drop-node-name;
              type uint8 {
                range "0..255";
              }
            }
            leaf weight-5 {
              tailf:cli-drop-node-name;
              type uint8 {
                range "0..255";
              }
            }
            leaf weight-6 {
              tailf:cli-drop-node-name;
              type uint8 {
                range "0..255";
              }
            }
            leaf weight-7 {
              tailf:cli-drop-node-name;
              type uint8 {
                range "0..255";
              }
            }
          }
          case b {
            container percent {
              tailf:cli-compact-syntax;
              tailf:cli-sequence-commands {
                tailf:cli-reset-siblings;
              }
              leaf percent-1 {
                tailf:cli-drop-node-name;
                type uint8 {
                  range "0..100";
                }
              }
              leaf percent-2 {
                tailf:cli-drop-node-name;
                type uint8 {
                  range "0..100";
                }
              }
              leaf percent-3 {
                tailf:cli-drop-node-name;
                type uint8 {
                  range "0..100";
                }
              }
              leaf percent-4 {
                tailf:cli-drop-node-name;
                type uint8 {
                  range "0..100";
                }
              }
              leaf percent-5 {
                tailf:cli-drop-node-name;
                type uint8 {
                  range "0..100";
                }
              }
              leaf percent-6 {
                tailf:cli-drop-node-name;
                type uint8 {
                  range "0..100";
                }
              }
              leaf percent-7 {
                tailf:cli-drop-node-name;
                type uint8 {
                  range "0..100";
                }
              }
            }
          }
        }
      }
      list cos-map {
        description
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            range "1..3";
          }
        }
        leaf threshold-id {
          type uint8 {
            range "1..8";
          }
        }
        leaf-list cos-values {
          tailf:cli-drop-node-name;
          tailf:cli-flat-list-syntax;
          max-elements "8";
          type uint8 {
            range "0..7";
          }
        }
      }
      container queue-limit {
        description
          "Configure queue-limit";
        tailf:cli-compact-syntax;
        tailf:cli-sequence-commands {
          tailf:cli-reset-siblings;
        }
        leaf weight-a {
          tailf:cli-drop-node-name;
          type uint8 {
            range "0..100";
          }
        }
        leaf weight-b {
          tailf:cli-drop-node-name;
          type uint8 {
            range "0..100";
          }
        }
        leaf weight-c {
          tailf:cli-drop-node-name;
          type uint8 {
            range "0..100";
          }
        }
      }
      container random-detect {
        description
          "Configure random-detect";
        list max-threshold {
          description
            "Max threshold for WRED";
          tailf:cli-suppress-mode;
          tailf:cli-delete-when-empty;
          tailf:cli-compact-syntax;
          tailf:cli-sequence-commands {
            tailf:cli-reset-siblings;
          }
          key "id";
          leaf id {
            type uint8 {
              range "1..3";
            }
          }
          uses queue-size-grouping;
        }
        list min-threshold {
          description
            "Min threshold for WRED";
          tailf:cli-suppress-mode;
          tailf:cli-delete-when-empty;
          tailf:cli-compact-syntax;
          tailf:cli-sequence-commands {
            tailf:cli-reset-siblings;
          }
          key "id";
          leaf id {
            type uint8 {
              range "1..3";
            }
          }
          uses queue-size-grouping;
        }
      }
      list threshold {
        description
          "Configure queue tail-drop thresholds";
        tailf:cli-suppress-mode;
        tailf:cli-delete-when-empty;
        tailf:cli-compact-syntax;
        tailf:cli-sequence-commands {
          tailf:cli-reset-siblings;
        }
        key "id";
        leaf id {
          type uint8 {
            range "1..3";
          }
        }
        uses queue-size-grouping;
      }
    }
    // interface * / priority-queue
    container priority-queue {
      description
        "Configure priority scheduling";
      container cos-map {
        description
          "Configure cos-map for a queue";
        tailf:cli-compact-syntax;
        tailf:cli-sequence-commands {
          tailf:cli-reset-siblings;
        }
        leaf id {
          tailf:cli-drop-node-name;
          type uint8;
        }
        leaf-list cos-values {
          tailf:cli-drop-node-name;
          tailf:cli-flat-list-syntax;
          max-elements "8";
          type uint8 {
            range "0..7";
          }
        }
      }
      leaf out {
        description
          "egress priority queue";
        tailf:cli-full-command;
        type empty;
      }
      //  queue-limit  Configure priority queue limit
    }
    // interface * / rep
    container rep {
      description
        "Resilient Ethernet Protocol characteristics";
      container block {
        description
          "Block port & VLANs for VLAN Load-balancing";
        container port {
          description
            "Specify port for VLAN Load-balancing";
          tailf:cli-sequence-commands {
            tailf:cli-reset-siblings;
          }
          tailf:cli-compact-syntax;
          choice port-choice {
            leaf neighbor-offset {
              tailf:cli-drop-node-name;
              type int16 {
                range "-256..256";
              }
            }
            leaf id {
              description
                "REP port ID";
              type string;
            }
            leaf preferred {
              description
                "Preferred flag";
              type empty;
            }
          }
          leaf vlan {
            description
              "VLANs to block";
            type union {
              type string;
              type enumeration {
                enum "all";
              }
            }
          }
        }
      }
      container preempt {
        description
          "Preemption options";
        leaf delay {
          description
            "Delay timer in seconds";
          type uint16 {
            range "15..300";
          }
        }
      }
      container segment {
        description
          "REP segment ID";
        tailf:cli-compact-syntax;
        tailf:cli-sequence-commands {
          tailf:cli-reset-siblings;
        }
        leaf id {
          tailf:cli-drop-node-name;
          type uint16 {
            range "1..1024";
          }
        }
        leaf edge {
          description
            "Edge Port";
          tailf:cli-optional-in-sequence;
          type empty;
        }
        leaf primary {
          description
            "Primary Edge Port";
          tailf:cli-optional-in-sequence;
          when "../edge" {
            tailf:dependency "../edge";
          }
          type empty;
        }
        leaf preferred {
          description
            "Preferred Alternate Port";
          type empty;
        }
      }
      container stcn {
        description
          "Segment Topology Change Notification";
        leaf segment {
          description
            "for REP segment";
          type string;
        }
        leaf stp {
          description
            "for STP network";
          type empty;
        }
      }
    }

    // interface * / rcv-queue
    container rcv-queue {
      description
        "Configure receive queue(s)";
      list cos-map {
        description
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            range "1..3";
          }
        }
        leaf threshold-id {
          type uint8 {
            range "1..8";
          }
        }
        leaf-list cos-values {
          tailf:cli-drop-node-name;
          tailf:cli-flat-list-syntax;
          max-elements "8";
          type uint8 {
            range "0..7";
          }
        }
      }
    }


    // interface * / udld
    container udld {
      description
        "Configure UDLD enabled or disabled and ignore global UDLD setting";
      container port {
        description
          "Enable UDLD protocol on this interface despite global UDLD setting";
        tailf:cli-delete-when-empty;
        presence "true";
        choice port-choice {
          leaf aggressive {
            description
              "Enable UDLD protocol in aggressive mode on this interface despite global UDLD setting";
            type empty;
          }
          leaf disable {
            description
              "Disable UDLD protocol on this interface despite global UDLD setting";
            type empty;
          }
        }
      }
    }
    // interface * / peer
    container peer {
      description
        "Peer parameters for point to point interfaces";
      container default {
        description
          "Specify default parameters";
        container ip {
          description
            "Specify default IP parameters";
          container address {
            description
              "Specify default IP address";
            choice address-choice {
              leaf dhcp {
                description
                  "Use DHCP proxy client mechanism to allocate a peer IP address";
                type empty;
              }
              container dhcp-pool {
                description
                  "Use local DHCP pools to allocate a peer IP address";
                presence "true";
                leaf pools {
                  tailf:cli-drop-node-name;
                  tailf:cli-multi-value;
                  type string;
                }
              }
              container pool {
                description
                  "Use IP pool mechanism to allocate a peer IP address";
                presence "true";
                leaf pools {
                  tailf:cli-drop-node-name;
                  tailf:cli-multi-value;
                  type string;
                }
              }
            }
          }
        }
      }
    }
    // interface * / performance monitor
    container performance {
      description
        "Global performance monitor configuration";
      container monitor {
        description
          "monitor";
        leaf-list context {
          description
            "Select ezPM context";
          tailf:cli-list-syntax;
          type string;
        }
      }
    }
  }
// grouping interface-common-grouping
   grouping interface-tunnel-grouping {
    container nhrp {
      description
        "NHRP Interface commands";
      container event-publisher {
        description
          "Enable NHRP smart spoke feature";
        leaf max-event-timeout {
          description
            "Number of seconds";
          type uint8 {
            range "1..22";
          }
        }
      }
      leaf group {
        description
          "group name string";
        type string;
      }
      container map {
        description
          "Map group name to QoS service policy";
        container group {
          description
            "NHRP group mapping";
          list nhrp-name {
            tailf:cli-drop-node-name;
            tailf:cli-suppress-mode;
            key "nhrp-name";
            leaf nhrp-name {
              description
                "NHRP group name";
              type string;
            }
            container service-policy {
              description
                "QoS service-policy";
              leaf output {
                description
                  "QoS policy-map name";
                type string;
              }
            }
          }
        }
      }
      leaf route-watch {
        description
          "Enable NHRP route watch";
        tailf:cli-boolean-no;
        tailf:cli-trim-default;
        tailf:cli-full-command;
        type boolean;
      }
    }
    container tunnel {
      description
        "protocol-over-protocol tunneling";
        // interface * / tunnel 6rd
      container tun-6rd {
        tailf:alt-name "6rd";
        description
          "set tunnel 6rd parameters";
        leaf br {
          description
            "Border Relay parameters";
          type inet:ipv4-address;
        }
        container ipv4 {
          description
            "Common IPv4 transport source parameters";
          leaf prefix-len {
            description
              "Common IPv4 transport source prefix length";
            type uint8;
          }
          leaf suffix-len {
            description
              "Common IPv4 transport source suffix length";
            type uint8;
          }
        }
        leaf prefix {
          description
            "Provider selected common IPv6 prefix";
          type inet:ipv6-prefix;
        }
        leaf reverse-map-check {
          description
            "Enable source IP address and port verification";
          type empty;
        }
      }
      // interface * / tunnel bandwidth
      container bandwidth {
        description
          "Set tunnel bandwidth informational parameter";
        leaf receive {
          description
            "Receive bandwidth";
          type uint32;
        }
        leaf transmit {
          description
            "Transmit bandwidth";
          type uint32;
        }
      }
      // interface * / tunnel checksum
      leaf checksum {
        description
          "enable end to end checksumming of packets";
        type empty;
      }
      // interface * / tunnel source
      leaf source {
        description
          "source of tunnel packets";
        type string;
      }
      // interface * / tunnel destination
      leaf destination {
        description
          "destination of tunnel";
        type host-v4v6-type;
      }
      // interface * / tunnel dst-port
      container dst-port {
        description
          "tunnel destination port";
        choice dst-port-choice {
          case port-num-case {
            leaf port-num {
              tailf:cli-drop-node-name;
              type uint16;
            }
          }
          case dynamic-case {
            leaf dynamic {
              description
                "Set Destination Port Dynamically";
              type empty;
            }
          }
        }
      }
      // interface * / tunnel endpoint
      container endpoint {
        description
          "Set endpoint parameter";
        container service-policy {
          description
            "Set service-policy";
          leaf output {
            description
              "apply QoS service policy in the output direction";
            type string;
          }
        }
      }
      // interface * / tunnel entropy
      leaf entropy {
        description
          "Compute hash (entropy) on payload and propagate to tunnel header";
        type empty;
      }
      // interface * / tunnel fixup
      container fixup {
        description
          "fixup on tunnel interface";
        leaf nat {
          description
            "enable post nat fixup ";
          type empty;
        }
      }
      // interface * / tunnel flow
      container flow {
        description
          "flow options";
        leaf egress-records {
          description
            "enable egress flow records ";
          type empty;
        }
      }
      // interface * / tunnel key
      leaf key {
        description
          "security or selector key";
        type uint64 {
          range "0..4294967295";
        }
      }
      // interface * / tunnel mode
      container mode {
        description
          "tunnel encapsulation method";
        choice mode-choice {
          // interface * / tunnel mode ipsec
          container ipsec {
            description
              "IPSec tunnel encapsulation";
            container ipv4 {
              description
                "over IPv4";
              tailf:cli-delete-when-empty;
              presence "true";
            }
            container ipv6 {
              description
                "over IPv6";
              tailf:cli-delete-when-empty;
              presence "true";
            }
          }
          // interface * / tunnel mode mpls
          container mpls {
            description
              "MPLS encapsulations";
            container traffic-eng {
              description
                "Traffic engineering tunnels";
              tailf:cli-delete-when-empty;
              presence "true";
              leaf gre-ip {
                type empty;
              }
            }
          }
          // interface * / tunnel mode ethernet
          container ethernet {
            description
              "Ethernet over gre";
            leaf gre {
              description
                "Ethernet over gre";
              type enumeration {
                enum "ipv4";
                enum "ipv6";
              }
            }
          }
          // interface * / tunnel mode gre
          container gre {
            description
              "generic route encapsulation protocol";
            leaf ip {
              description
                "over IP";
              tailf:cli-full-command;
              type empty;
            }
            leaf ipv6 {
              description
                "over IPv6";
              tailf:cli-full-command;
              type empty;
            }
            container multipoint {
              description
                "over IPv4 (multipoint)";
              presence "true";
              leaf ipv6 {
                description
                  "over IPv6";
                tailf:cli-full-command;
                type empty;
              }
            }
          }
          // interface * / tunnel mode ipip
          container ipip {
            description
              "IP over IP encapsulation";
            presence "true";
            leaf decapsulate-any {
              description
                "Incoming traffic only";
              tailf:cli-full-command;
              type empty;
            }
          }
          // interface * / tunnel mode ipv6
          leaf ipv6 {
            description
              "Generic packet tunneling in IPv6";
            tailf:cli-full-command;
            type empty;
          }
          // interface * / tunnel mode ipv6ip
          container ipv6ip {
            description
              "IPv6 over IP encapsulation";
            presence "true";
            leaf auto-6rd {
              tailf:alt-name "6rd";
              description
                "IPv6 automatic tunnelling using 6rd";
              tailf:cli-full-command;
              type empty;
            }
            leaf auto-6to4 {
              tailf:alt-name "6to4";
              description
                "IPv6 automatic tunnelling using 6to4";
              tailf:cli-full-command;
              type empty;
            }
            leaf isatap {
              description
                "IPv6 automatic tunnelling using ISATAP";
              tailf:cli-full-command;
              type empty;
            }
          }
          // interface * / tunnel mode udp
          leaf udp {
            description
              "UDP encapsulation protocol";
            type enumeration {
              enum "ip";
              enum "multipoint";
            }
          }
        }
      }
      // interface * / tunnel network-id
      container network-id {
        description
          "Set network-id";
        tailf:cli-sequence-commands;
        tailf:cli-compact-syntax;
        leaf id {
          tailf:cli-drop-node-name;
          type uint16;
        }
        leaf nexthop {
          description
            "nexthop";
          type inet:ipv4-address;
        }
        leaf qos {
          description
            "QoS profile";
          tailf:cli-break-sequence-commands;
          type string;
        }
        leaf weight {
          description
            "weight";
          type uint16;
        }
      }
      // interface * / tunnel path-mtu-discovery
      container path-mtu-discovery {
        description
          "Enable Path MTU Discovery on tunnel";
        presence "true";
      }
      // interface * / tunnel protection
      container protection {
        description
          "Enable tunnel protection";
        container ipsec {
          description
            "Use ipsec to protect this tunnel interface";
          leaf profile {
            description
              "Determine the ipsec policy profile to use.";
            type string;
          }
        }
      }
      // interface * / tunnel mpls
      container mpls {
        container traffic-eng {
          container affinity {
            tailf:cli-sequence-commands {
              tailf:cli-reset-siblings;
            }
            tailf:cli-compact-syntax;
            leaf attributes {
              tailf:cli-drop-node-name;
              type string;
            }
            leaf mask {
              type string;
            }
          }
          container auto-bw {
            description
              "Specify mpls tunnel should automatically change bw";
            leaf max-bw {
              description
                "Set the Maximum Bandwidth for auto-bw on this tunnel";
              type uint32 {
                range "0..4294967295";
              }
            }
          }
          container autoroute {
            leaf announce {
              tailf:cli-full-command;
              type empty;
            }
          }
          container priority {
            tailf:cli-sequence-commands {
              tailf:cli-reset-siblings;
            }
            tailf:cli-compact-syntax;
            leaf setup-priority {
              tailf:cli-drop-node-name;
              type uint8 {
                range "0..7";
              }
            }
            leaf hold-priority {
              tailf:cli-drop-node-name;
              type uint8 {
                range "0..7";
              }
            }
          }
          leaf bandwidth {
            tailf:cli-full-command;
            type uint32;
          }
          container path-option {
            tailf:cli-compact-syntax;
            list working {
              tailf:cli-drop-node-name;
              tailf:cli-suppress-mode;
              tailf:cli-delete-when-empty;
              tailf:cli-sequence-commands {
                tailf:cli-reset-siblings;
              }
              tailf:cli-compact-syntax;
              key "id";
              leaf id {
                type uint32;
              }
              choice path-option-choice {
                container dynamic {
                  presence "true";
                }
                container explicit {
                  tailf:cli-compact-syntax;
                  choice explicit-choice {
                    container name {
                      tailf:cli-compact-syntax;
                      tailf:cli-sequence-commands {
                        tailf:cli-reset-siblings;
                      }
                      leaf exp-name {
                        tailf:cli-drop-node-name;
                        type string;
                      }
                      leaf segment-routing {
                        type empty;
                      }
                    }
                    leaf identifier {
                      type uint32;
                    }
                  }
                }
              }
              container lockdown {
                presence "true";
              }
            }
            list protect {
              tailf:cli-suppress-mode;
              tailf:cli-delete-when-empty;
              tailf:cli-sequence-commands {
                tailf:cli-reset-siblings;
              }
              tailf:cli-compact-syntax;
              key "id";
              leaf id {
                type leafref {
                  path "/ios:native/interface/Tunnel/tunnel/mpls/traffic-eng/path-option/working/id";
                }
              }
              container explicit {
                tailf:cli-compact-syntax;
                choice explicit-choice {
                  leaf name {
                    type string;
                  }
                  leaf identifier {
                    type uint32;
                  }
                }
              }
              container lockdown {
                presence "true";
              }
            }
          }
          container fast-reroute {
            presence "true";
          }
          container path-selection {
            description
              "Path Selection Configuration";
            uses mpls-te-path-selection-common;
            container segment-routing {
              description
                "Segment-routing path-selection options";
              container adjacency {
                description
                  "Segment-routing adjacency path-selection type";
                choice protection {
                  leaf protected {
                    description
                      "Use only protected adjacencies";
                    type empty;
                  }
                  leaf unprotected {
                    description
                      "Use only unprotected adjacencies";
                    type empty;
                  }
                }
              }
            }
          }
        }
      }
      // interface * / tunnel raw-packet-interface
      leaf raw-packet-interface {
        description
          "physical interface for all packets entering itto be tunneled and for all packets entering the tunnel to exit";
        type string;
      }
      // interface * / tunnel rbscp
      container rbscp {
        description
          "Set tunnel RBSCP parameters";
        leaf ack-split {
          description
            "ACK splitting";
          type uint8 {
            range "1..32";
          }
        }
        leaf delay {
          description
            "enable delay";
          type empty;
        }
        leaf input-drop {
          description
            "max tunnel queue size (number of bw*delay)";
          type uint8 {
            range "1..10";
          }
        }
        leaf long-drop {
          description
            "Drop non-transmitted packets w/excessive delay";
          type empty;
        }
        leaf report {
          description
            "enable SCTP report chunk";
          type empty;
        }
        leaf window-stuff {
          description
            "Window stuffing";
          type uint8 {
            range "1..20";
          }
        }
      }
      // interface * / tunnel snooping
      leaf snooping {
        description
          "Snooping on tunnel";
        type enumeration {
          enum "enable";
        }
      }
      // interface * / tunnel src-port
      container src-port {
        description
          "tunnel source port";
        choice src-port-choice {
          case port-num-case {
            leaf port-num {
              tailf:cli-drop-node-name;
              type uint16;
            }
          }
          case dynamic-case {
            leaf dynamic {
              description
                "Set Source Port Dynamically";
              type empty;
            }
          }
        }
      }
      // interface * / tunnel tos
      leaf tos {
        description
          "set type of sevice byte";
        type uint8;
      }
      // interface * / tunnel ttl
      leaf ttl {
        description
          "set time to live";
        type uint8;
      }
      // interface * / tunnel udlr
      container udlr {
        description
          "associate tunnel with unidirectional interface";
        leaf address-resolution {
          description
            "Enable ARP and NHRP over a UDLR Tunnel";
          type empty;
        }
        leaf receive-only {
          description
            "Tunnel is receive-only capable";
          type string;
        }
        leaf send-only {
          description
            "Tunnel is send-only capable";
          type string;
        }
      }
      // interface * / tunnel vlan
      container vlan {
        description
          "Set vlan-id for ethernet over gre mode";
        tailf:cli-sequence-commands;
        tailf:cli-compact-syntax;
        leaf id1 {
          tailf:cli-drop-node-name;
          type uint16;
        }
        leaf hyphen {
          tailf:alt-name "-";
          tailf:cli-break-sequence-commands;
          type empty;
        }
        leaf id2 {
          tailf:cli-drop-node-name;
          type uint16;
        }
      }
      // interface * / tunnel vrf
      leaf vrf {
        description
          "set tunnel vrf membership";
        type string;
      }
    }
  }

  grouping interface-ethernet-carrier-delay-grouping {
    choice delay-choice {
      leaf seconds {
        tailf:cli-drop-node-name;
        type uint8 {
          range "0..60";
        }
      }
      leaf msec {
        description
          "delay specified in milliseconds";
        type uint16 {
          range "0..1000";
        }
      }
    }
  }

  grouping interface-ethernet-service-instance-l2protocol-grouping {
    leaf-list protocol {
      tailf:cli-drop-node-name;
      tailf:cli-flat-list-syntax;
      type enumeration {
        enum "R4";
        enum "R5";
        enum "R6";
        enum "R8";
        enum "R9";
        enum "RA";
        enum "RB";
        enum "RC";
        enum "RD";
        enum "RF";
        enum "cdp";
        enum "dtp";
        enum "elmi";
        enum "esmc";
        enum "lacp";
        enum "lldp";
        enum "loam";
        enum "pagp";
        enum "ptppd";
        enum "stp";
        enum "udld";
        enum "vtp";
      }
    }
  }

  grouping interface-ethernet-grouping {
    // interface * / carrier-delay
    container carrier-delay {
      description
        "Specify delay for interface transitions";
      uses interface-ethernet-carrier-delay-grouping;
      container down {
        description
          "Carrier Down Transitions";
        uses interface-ethernet-carrier-delay-grouping;
      }
      container up {
        description
          "Carrier Up Transitions";
        uses interface-ethernet-carrier-delay-grouping;
      }
    }
    // interface * / channel-group
    container channel-group {
      description
        "Add this interface to an Etherchannel group";
      tailf:cli-sequence-commands {
        tailf:cli-reset-siblings;
      }
      tailf:cli-compact-syntax;
      tailf:cli-diff-dependency "/ios:native/interface/Port-channel";
      tailf:cli-diff-dependency "/ios:native/interface/Port-channel-subinterface/Port-channel";
      tailf:cli-diff-dependency "../cts";
      leaf number {
        tailf:cli-drop-node-name;
        type uint16 {
          range "1..512";
        }
      }
      leaf mode {
        description
          "Etherchannel Mode of the interface";
        type enumeration {
          enum "active";
          enum "auto";
          enum "desirable";
          enum "on";
          enum "passive";
        }
      }
      leaf non-silent {
        description
          "Start negotiation only after data packets received";
        tailf:cli-break-sequence-commands;
        type empty;
      }
      leaf link {
        description
          "Assign a link identifier used for load-balancing";
        type uint8 {
          range "1..4";
        }
      }
      leaf auto {
        description
          "LACP auto";
        type empty;
      }
    }
    // interface * / channel-protocol
    leaf channel-protocol {
      description
        "Select the channel protocol (LACP, PAgP)";
      type enumeration {
        enum "lacp";
        enum "pagp";
      }
    }

    // interface * / ethernet
    container ethernet {
      description
        "Ethernet interface parameters";
      container oam {
        description
          "To enable Ethernet Link OAM";
        presence "true";
        container link-monitor {
          description
            "Ethernet OAM Link Monitor";
          container frame {
            description
              "Errored frames in a period measured by time";
            container threshold {
              description
                "Errored frame threshold";
              container high {
                description
                  "High Threshold";
                leaf thresh {
                  description
                    "Set the high errored frame threshold in number of frames";
                  tailf:cli-drop-node-name;
                  type uint16 {
                    range "1..65535";
                  }
                }
                leaf none {
                  description
                    "Disable high threshold";
                  type empty;
                }
              }
              leaf low {
                description
                  "Set the low errored frame threshold in number of frames";
                type uint16 {
                  range "0..65535";
                }
              }
            }
            leaf window {
              description
                "Set window size in multiple of 100 milliseconds (will be rounded off to second)";
              type uint16 {
                range "10..600";
              }
            }
          }
          container frame-period {
            description
              "Errored frames in a period measured by number of frames";
            container threshold {
              description
                "Errored frame-period threshold";
              container high {
                description
                  "High Threshold";
                leaf f-thresh {
                  description
                    "Set the high errored frame-period threshold in number of frames";
                  tailf:cli-drop-node-name;
                  type uint16 {
                    range "1..65535";
                  }
                }
                leaf none {
                  description
                    "Disable high threshold";
                  type empty;
                }
              }
              leaf low {
                description
                  "Set the low errored frame-period threshold in number of frames";
                type uint16 {
                  range "0..65535";
                }
              }
            }
            leaf window {
              description
                "Set window size in number of 10000 frames";
              type uint16 {
                range "1..65535";
              }
            }
          }
          container frame-seconds {
            description
              "Errored frame seconds in a period";
            container threshold {
              description
                "Errored frame-seconds threshold";
              container high {
                description
                  "High Threshold";
                leaf e-thresh {
                  description
                    "Set the high errored frame-seconds threshold in number of seconds";
                  tailf:cli-drop-node-name;
                  type uint16 {
                    range "1..900";
                  }
                }
                leaf none {
                  description
                    "Disable high threshold";
                  type empty;
                }
              }
              leaf low {
                description
                  "Set the low errored frame-seconds threshold in number of seconds";
                type uint16 {
                  range "1..900";
                }
              }
            }
            leaf window {
              description
                "Set window size in multiple of 100 milliseconds (will be rounded off to second)";
              type uint16 {
                range "100..9000";
              }
            }
          }
          container high-threshold {
            description
              "Additional high threshold configuration";
            container action {
              description
                "Specifiy an action when the high threshold is crossed";
              leaf error-disable-interface {
                description
                  "Error-disable the interface";
                type empty;
              }
            }
          }
          leaf on {
            description
              "Enable link monitoring on the interface";
            type empty;
          }
          container receive-crc {
            description
              "Received frames with CRC errors in a period";
            container threshold {
              description
                "Errored frame-seconds threshold";
              container high {
                description
                  "High Threshold";
                leaf crc-thresh {
                  description
                    "Set the high received crc error threshold in number of frames";
                  tailf:cli-drop-node-name;
                  type uint16 {
                    range "1..65535";
                  }
                }
                leaf none {
                  description
                    "Disable high threshold";
                  type empty;
                }
              }
              leaf low {
                description
                  "Set the low received crc error threshold in number of frames";
                type uint16 {
                  range "0..65535";
                }
              }
            }
            leaf window {
              description
                "Set window size in multiple of 100 milliseconds (will be rounded off to second)";
              type uint16 {
                range "10..1800";
              }
            }
          }
          leaf supported {
            description
              "Support link monitoring on the interface";
            type empty;
          }
          container symbol-period {
            description
              "Errored symbols in a period";
            container threshold {
              description
                "Error symbol-period threshold";
              container high {
                description
                  "High Threshold";
                leaf err-thresh {
                  description
                    "Set the high error symbol-period threshold in number of symbols";
                  tailf:cli-drop-node-name;
                  type uint16 {
                    range "1..65535";
                  }
                }
                leaf none {
                  description
                    "Disable high threshold";
                  type empty;
                }
              }
              leaf low {
                description
                  "Set the low error symbol-period threshold in number of symbols";
                type uint16 {
                  range "0..65535";
                }
              }
            }
            leaf window {
              description
                "Set window size in number of 1048576 symbols";
              type uint16 {
                range "1..65535";
              }
            }
          }
        }
        leaf max-rate {
          type uint8 {
            range "1..10";
          }
        }
        leaf min-rate {
          type uint8 {
            range "1..10";
          }
        }
        leaf mode {
          type enumeration {
            enum "active";
            enum "passive";
          }
        }
        container remote-failure {
          description
            "Ethernet OAM remote failure indication";
          container critical-event {
            description
              "Critical event";
            container action {
              description
                "Specifiy an action when a remote failure is detected";
              leaf error-disable-interface {
                description
                  "Error-disable the interface";
                type empty;
              }
            }
          }
          container dying-gasp {
            description
              "Dying gasp";
            container action {
              description
                "Specifiy an action when a remote failure is detected";
              presence "true";
              leaf error-disable-interface {
                description
                  "Error-disable the interface";
                type empty;
              }
            }
          }
          container link-fault {
            description
              "Link fault";
            container action {
              description
                "Specifiy an action when a remote failure is detected";
              presence "true";
              leaf error-disable-interface {
                description
                  "Error-disable the interface";
                type empty;
              }
            }
          }
        }
        container remote-loopback {
          description
            "Ethernet OAM Remote Loopback";
          leaf supported {
            description
              "Support remote loopback functionality";
            type empty;
          }
          leaf timeout {
            description
              "Set timeout value in number of seconds";
            type uint8 {
              range "1..10";
            }
          }
        }
        leaf timeout {
          type uint8 {
            range "2..30";
          }
        }
      }
    }


    // interface * / negotiation
    container negotiation {
      description
        "Select autonegotiation mode";
      leaf auto {
        description
          "Enable link autonegotiation";
        tailf:cli-boolean-no;
        tailf:cli-trim-default;
        tailf:cli-full-command;
        type boolean;
      }
    }
    // interface * / synchronous
    container synchronous {
      description
        "Synchronous";
      leaf mode {
        description
          "Mode";
        type empty;
      }
    }
    // interface * / duplex
    leaf duplex {
      description
        "Configure duplex operation.";
      type enumeration {
        enum "auto" {
          tailf:code-name "duplex_auto";
        }
        enum "full" {
          tailf:code-name "duplex_full";
        }
        enum "half" {
          tailf:code-name "duplex_half";
        }
      }
    }
    // interface * / speed
    container speed {
      description
        "Configure speed operation";
      tailf:cli-compact-syntax;
      leaf auto {
        description
          "Enable AUTO speed configuration";
        type empty;
      }
      leaf value-10 {
        tailf:alt-name "10";
        description
          "10 Mbps operation";
        type empty;
      }
      leaf value-100 {
        tailf:alt-name "100";
        description
          "100 Mbps operation";
        type empty;
      }
      leaf value-1000 {
        tailf:alt-name "1000";
        description
          "1000 Mbps operation";
        type empty;
      }
      leaf value-10000 {
        tailf:alt-name "10000";
        description
          "10000 Mbps operation";
        type empty;
      }
      leaf nonegotiate {
        type empty;
      }
    }

    // interface * / xconnect
    container xconnect {
      description
        "Xconnect commands";
      tailf:cli-sequence-commands;
      tailf:cli-compact-syntax;
      leaf address {
        tailf:cli-drop-node-name;
        tailf:cli-incomplete-command;
        type inet:ipv4-address;
      }
      leaf vcid {
        tailf:cli-drop-node-name;
        tailf:cli-incomplete-command;
        type uint32 {
          range "1..4294967295";
        }
      }
      leaf encapsulation {
        description
          "Data encapsulation method";
        tailf:cli-optional-in-sequence;
        type enumeration {
          enum "mpls" {
            tailf:code-name "encap_mpls";
          }
          enum "l2tpv3";
        }
      }
      leaf manual {
        description
          "Manually configure L2TP session parameters";
        tailf:cli-optional-in-sequence;
        when "../encapsulation = 'l2tpv3'";
        type empty;
      }
      leaf sequence {
        description
          "Configure sequencing options for xconnect";
        tailf:cli-full-command;
        tailf:cli-optional-in-sequence;
        when "../encapsulation = 'l2tpv3'";
        type enumeration {
          enum "both";
          enum "receive";
          enum "transmit";
        }
      }
      leaf pw-class {
        description
          "Pseudowire-class to use for encapsulation and protocol configuration";
        type string;
      }
    }
    // interface * plim
    container plim {
      description
        "Configure features on the PLIM";
      container ethernet {
        description
          "Configure features on the ethernet interface";
        container vlan {
          description
            "vlan specific features";
          container filter {
            description
              "Configure VLAN filtering";
            leaf disable {
              description
                "Configure the interface to accept all VLAN traffic";
              type empty;
            }
          }
        }
      }
      container qos {
        description
          "QoS on the PLIM";
        container input {
          description
            "Configure PLIM QoS at the input of an interface";
          container queue {
            description
              "Queue number";
            choice priority {
              case low {
                container zero {
                  tailf:alt-name "0";
                  description
                    "Low priority queue";
                  container pause {
                    description
                      "Pause Frame generation and threshold";
                    leaf enable {
                      description
                        "Enable pause-frame generation";
                      tailf:cli-boolean-no;
                      tailf:cli-trim-default;
                      tailf:cli-full-command;
                      type boolean;
                    }
                    leaf threshold {
                      description
                        "Threshold as a percent of queue limit for pause frame generation";
                      type uint8 {
                        range "0..99";
                      }
                    }
                  }
                }
              }
              case high {
                container strict-priority {
                  description
                    "High priority queue";
                  container pause {
                    description
                      "Pause Frame generation and threshold";
                    leaf enable {
                      description
                        "Enable pause-frame generation";
                      tailf:cli-boolean-no;
                      tailf:cli-trim-default;
                      tailf:cli-full-command;
                      type boolean;
                    }
                    leaf threshold {
                      description
                        "Threshold as a percent of queue limit for pause frame generation";
                      type uint8 {
                        range "0..99";
                      }
                    }
                  }
                }
              }
            }
          }
        }
      }
    }
    // interface * / pppoe
    container pppoe {
      description
        "pppoe interface subcommands";
      container enable {
        description
          "Enable pppoe";
        presence "true";
        leaf group {
          description
            "attach a BBA group";
          type union {
            type string;
            type enumeration {
              enum "global";
            }
          }
        }
      }
      leaf max-sessions {
        description
          "Maximum PPPOE sessions";
        type uint16 {
          range "1..4085";
        }
      }
    }
    // interface * / service instance * ethernet
    container service {
      description
        "Configure Ether Service";
      list instance {
        description
          "Configure Ether Service Instance";
        tailf:cli-mode-name "config-if-srv";
        tailf:cli-incomplete-command;
        tailf:cli-sequence-commands;
        // interface overlay aslo has service, but not ethernet-grouping
        //tailf:cli-diff-dependency "../../switchport-conf/switchport";
        key "id";
        leaf id {
          type uint32 {
            range "1..4000";
          }
        }
        leaf trunk {
          description
            "Trunk Service Instance";
          tailf:cli-optional-in-sequence;
          tailf:cli-prefix-key;
          type empty;
        }
        leaf GigabitEthernet {
          description
            "Configure an GigabitEthernet Instance";
          tailf:cli-optional-in-sequence;
          tailf:cli-hide-in-submode;
          type empty;
        }
        leaf ethernet {
          description
            "Configure an Ethernet Instance";
          tailf:cli-hide-in-submode;
          type empty;
        }
        leaf ethernet-evc-name {
          tailf:cli-drop-node-name;
          tailf:cli-hide-in-submode;
          type string;
        }
        // interface * / service instance * ethernet / description
        leaf description {
          tailf:cli-break-sequence-commands;
          description
            "Service instance specific description";
          tailf:cli-multi-value;
          tailf:cli-full-command;
          type string {
            length "0..240";
          }
        }
        // interface * / service instance * ethernet / evc-name
        leaf evc-name {
          tailf:cli-drop-node-name;
          tailf:cli-hide-in-submode;
          type string {
            length "1..100";
          }
        }
        // interface * / service instance * ethernet / encapsulation
        container encapsulation {
          description
            "Configure ethernet frame match criteria";
          leaf default {
            description
              "catch-all unconfigured encapsulation";
            tailf:cli-full-command;
            type empty;
          }
          container dot1ad {
            description
              "802.1ad - Provider Bridges";
            tailf:cli-sequence-commands;
            tailf:cli-compact-syntax;
            leaf-list id {
              tailf:cli-drop-node-name;
              tailf:cli-range-list-syntax;
              type union {
                type uint16 {
                  range "1..4094";
                }
                type enumeration {
                  enum "any";
                }
                type string;
              }
            }
            leaf-list cos {
              description
                "CoS value to use for CFM packets";
              tailf:cli-break-sequence-commands;
              tailf:cli-range-list-syntax;
              type uint8 {
                range "0..7";
              }
            }
            leaf-list dot1q {
              description
                "Second tag (dot1q)";
              tailf:cli-range-list-syntax;
              type union {
                type uint16 {
                  range "1..4094";
                }
                type enumeration {
                  enum "any";
                }
                type string;
              }
            }
            container cos2 {
              tailf:cli-drop-node-name;
              tailf:cli-flatten-container;
              leaf-list cos {
                description
                  "CoS value to use for CFM packets";
                tailf:cli-range-list-syntax;
                type uint8 {
                  range "0..7";
                }
              }
            }
            leaf-list etype {
              description
                "payload ethertype after Vlan Field";
              tailf:cli-range-list-syntax;
              type enumeration {
                enum "ipv4";
                enum "ipv6";
                enum "pppoe-all";
                enum "pppoe-discovery";
                enum "pppoe-session";
              }
            }
            leaf exact {
              description
                "payload Ethertype does not include 802.1q/802.1ad Tags.";
              tailf:cli-full-command;
              type empty;
            }
          }
          container dot1q {
            description
              "IEEE 802.1Q Virtual LAN or S-VLAN";
            tailf:cli-compact-syntax;
            tailf:cli-sequence-commands {
              tailf:cli-reset-siblings;
            }
            leaf-list id {
              tailf:cli-drop-node-name;
              tailf:cli-range-list-syntax;
              type union {
                type uint16 {
                  range "1..4094";
                }
                type enumeration {
                  enum "any";
                }
                type string;
              }
            }
            leaf-list cos {
              description
                "cos Vlan";
              tailf:cli-range-list-syntax;
              tailf:cli-break-sequence-commands;
              type uint8 {
                range "0..7";
              }
            }
            leaf-list second-dot1q {
              description
                "inner 802.1Q Virtual LAN or C-VLAN";
              tailf:cli-range-list-syntax;
              type union {
                type uint16 {
                  range "1..4094";
                }
                type enumeration {
                  enum "any";
                }
                type string;
              }
            }
            container cos2 {
              tailf:cli-drop-node-name;
              tailf:cli-flatten-container;
              leaf-list cos {
                description
                  "cos Vlan";
                tailf:cli-range-list-syntax;
                type uint8 {
                  range "0..7";
                }
              }
            }
            leaf-list etype {
              description
                "payload ethertype after Vlan Field";
              tailf:cli-range-list-syntax;
              type enumeration {
                enum "ipv4";
                enum "ipv6";
                enum "pppoe-all";
                enum "pppoe-discovery";
                enum "pppoe-session";
              }
            }
            leaf exact {
              description
                "payload Ethertype does not include 802.1q/802.1ad Tags.";
              tailf:cli-full-command;
              type empty;
            }
            leaf vlan-type {
              description
                "Vlan Protocol Type";
              type enumeration {
                enum "0x88A8";
                enum "0x9100";
                enum "0x9200";
              }
            }
          }
          container priority-tagged {
            description
              "Priority tagged EFP";
            container cos-container {
              tailf:cli-drop-node-name;
              tailf:cli-compact-syntax;
              tailf:cli-sequence-commands;
              leaf-list cos {
                description
                  "cos Vlan";
                tailf:cli-range-list-syntax;
                type uint8 {
                  range "0..7";
                }
              }
            }
            leaf-list etype {
              description
                "payload ethertype after Vlan Field";
              tailf:cli-range-list-syntax;
              type enumeration {
                enum "ipv4";
                enum "ipv6";
                enum "pppoe-all";
                enum "pppoe-discovery";
                enum "pppoe-session";
              }
            }
          }
          container untagged {
            description
              "Untagged encapsulation";
            presence "true";
          }
        }
        // interface * / service instance * ethernet / ip
        container ip {
          description
            "Interface Internet Protocol config commands";
          container acl {
            tailf:cli-drop-node-name;
            tailf:cli-compact-syntax;
            tailf:cli-sequence-commands;
            leaf access-group {
              description
                "Specify access control for packets";
              type exp-acl-type;
            }
            leaf in {
              description
                "inbound packets";
              tailf:cli-break-sequence-commands;
              type empty;
            }
            leaf out {
              description
                "outbound packets";
              type empty;
            }
          }
          container dhcp {
            description
              "DHCP";
            container relay {
              description
                "DHCP relay";
              container information {
                description
                  "DHCP relay information";
                container option {
                  description
                    "DHCP relay information option";
                  leaf subscriber-id {
                    description
                      "DHCP relay information option subscriber-id";
                    type string;
                  }
                }
              }
            }
          }
          container verify {
            description
              "verify";
            tailf:cli-compact-syntax;
            tailf:cli-sequence-commands;
            leaf source {
              description
                "source address";
              type empty;
            }
            leaf vlan {
              description
                "vlan specification";
              type empty;
            }
            leaf dhcp-snooping {
              description
                "snooping enable vlan";
              type empty;
            }
            leaf port-security {
              description
                "port security";
              tailf:cli-optional-in-sequence;
              type empty;
            }
          }
        }
        // interface * / service instance * ethernet / ipv6
        container ipv6 {
          description
            "IPv6 interface subcommands";
          tailf:cli-compact-syntax;
          tailf:cli-sequence-commands;
          leaf traffic-filter {
            description
              "Access control list for packets";
            type string;
          }
          leaf in {
            description
              "inbound packets";
            tailf:cli-break-sequence-commands;
            type empty;
          }
          leaf out {
            description
              "outbound packets";
            type empty;
          }
        }
        // interface * / service instance * ethernet / rewrite
        container rewrite {
          description
            "Configure ethernet rewrite criteria";
          container ingress {
            description
              "Ingress Rewrite";
            container tag {
              description
                "Configure Rewrite Tag";
              container pop {
                description
                  "Pop the tag";
                tailf:cli-compact-syntax;
                tailf:cli-sequence-commands;
                leaf way {
                  tailf:cli-drop-node-name;
                  type enumeration {
                    enum "1";
                    enum "2";
                  }
                }
                leaf mode {
                  tailf:cli-drop-node-name;
                  type enumeration {
                    enum "symmetric";
                  }
                }
              }
              container push {
                description
                  "Rewrite Operation of push";
                tailf:cli-compact-syntax;
                tailf:cli-sequence-commands;
                leaf dot1q {
                  description
                    "Push dot1q tag";
                  type uint16 {
                    range "1..4094";
                  }
                }
                leaf mode {
                  tailf:cli-drop-node-name;
                  type enumeration {
                    enum "symmetric";
                  }
                }
              }
              container translate {
                description
                  "Translate Tag";
                container t1-to-1 {
                  description
                    "Translate 1-to-1";
                  tailf:alt-name "1-to-1";
                  tailf:cli-compact-syntax;
                  tailf:cli-sequence-commands;
                  leaf dot1q {
                    description
                      "Ethertype dot1q of the translation";
                    type uint16 {
                      range "1..4094";
                    }
                  }
                  leaf mode {
                    tailf:cli-drop-node-name;
                    type enumeration {
                      enum "symmetric";
                    }
                  }
                }
                container t1-to-2 {
                  description
                    "Translate 1-to-2";
                  tailf:alt-name "1-to-2";
                  tailf:cli-compact-syntax;
                  tailf:cli-sequence-commands;
                  leaf dot1q {
                    description
                      "Translate ethertype of dot1q";
                    type uint16 {
                      range "1..4094";
                    }
                  }
                  leaf second-dot1q {
                    description
                      "Second dot1q tag";
                    type uint16 {
                      range "1..4094";
                    }
                  }
                  leaf mode {
                    tailf:cli-drop-node-name;
                    type enumeration {
                      enum "symmetric";
                    }
                  }
                }
                container t2-to-1 {
                  description
                    "Translate 2-to-1";
                  tailf:alt-name "2-to-1";
                  tailf:cli-compact-syntax;
                  tailf:cli-sequence-commands;
                  leaf dot1q {
                    description
                      "Ethertype dot1q of the translation";
                    type uint16 {
                      range "1..4094";
                    }
                  }
                  leaf mode {
                    tailf:cli-drop-node-name;
                    type enumeration {
                      enum "symmetric";
                    }
                  }
                }
                container t2-to-2 {
                  description
                    "Translate 2-to-2";
                  tailf:alt-name "2-to-2";
                  tailf:cli-compact-syntax;
                  tailf:cli-sequence-commands;
                  leaf dot1q {
                    description
                      "Translate ethertype of dot1q";
                    type uint16 {
                      range "1..4094";
                    }
                  }
                  leaf second-dot1q {
                    description
                      "Second dot1q tag";
                    type uint16 {
                      range "1..4094";
                    }
                  }
                  leaf mode {
                    tailf:cli-drop-node-name;
                    type enumeration {
                      enum "symmetric";
                    }
                  }
                }
              }
            }
          }
        }
        // interface * / service instance * ethernet / group
        leaf group {
          tailf:cli-full-command;
          type uint32;
        }
        // interface * / service instance * ethernet / errdisable
        container errdisable {
          description
            "Configure error disable";
          container recovery {
            description
              "enable auto recovery";
            container cause {
              description
                "error disable cause";
              leaf mac-security {
                description
                  "mac-security violation";
                type uint32 {
                  range "30..86400";
                }
              }
            }
          }
        }
        // interface * / service instance * ethernet / ethernet
        container ethernet-container {
           //in order not to collide with submode ethernet
          tailf:cli-drop-node-name;
          container ethernet {
            description
              "ethernet";
            container lmi {
              description
                "Configure ether lmi parameters";
              container ce-vlan {
                description
                  "Configure ether lmi customer vlans";
                container map {
                  description
                    "Configure ether lmi ce-vlan/evc map";
                  container vlan-range {
                    tailf:cli-drop-node-name;
                    tailf:cli-sequence-commands;
                    tailf:cli-compact-syntax;
                    leaf vlan-id {
                      tailf:cli-drop-node-name;
                      type uint16 {
                        range "1..4094";
                      }
                    }
                    leaf comma {
                      description
                        "comma";
                      tailf:alt-name ",";
                      tailf:cli-break-sequence-commands;
                      type uint16 {
                        range "1..4094";
                      }
                    }
                    leaf hyphen {
                      description
                        "hyphen";
                      tailf:alt-name "-";
                      type uint16 {
                        range "1..4094";
                      }
                    }
                  }
                  leaf any {
                    description
                      "For all VLANS [untagged,1-4094]";
                    type empty;
                  }
                  leaf default {
                    description
                      "Default EFP";
                    type empty;
                  }
                  leaf untagged {
                    description
                      "Untagged frames";
                    type empty;
                  }
                }
              }
            }
            container loopback {
              description
                "Ethernet Dataplane Loopback";
              container permit {
                description
                  "Allow data plane loopback to be activated";
                leaf external {
                  description
                    "Allow to loopback the traffic from the wire";
                  type empty;
                }
                leaf internal {
                  description
                    "Allow to loopback the traffic from the relay";
                  type empty;
                }
              }
            }
          }
        }
        // interface * / service instance * ethernet / snmp
        container snmp {
          description
            "Modify SNMP service instance parameters";
          container trap {
            description
              "Allow a specific SNMP trap";
            leaf link-status {
              description
                "Allow SNMP LINKUP and LINKDOWN traps";
              type empty;
            }
          }
          container ifindex {
            description
              "Persist ifindex for the service instance";
            leaf persist {
              description
                "Enable/Disable ifIndex persistence";
              type empty;
            }
          }
        }
        // interface * / service instance * ethernet / bridge-domain
        container bridge-domain {
          description
            "Bridge-domain";
          tailf:cli-compact-syntax;
          tailf:cli-sequence-commands {
            tailf:cli-reset-all-siblings;
          }
          leaf bridge-id {
            tailf:cli-drop-node-name;
            type uint16;
          }
          container split-horizon {
            description
              "Configure this port as a member of a split horizon group";
            tailf:cli-optional-in-sequence;
            leaf group {
              description
                "Split-horizon group";
              type uint8 {
                range "0..13";
              }
            }
          }
          leaf from-encapsulation {
            description
              "from-encapsulation";
            type empty;
          }
        }
        // interface * / service instance * ethernet / mac
        container mac {
          description
            "Commands for MAC Address-based features";
          container security {
            description
              "MAC Security commands";
            tailf:cli-display-separated;
            tailf:cli-delete-when-empty;
            presence "true";
            container maximum {
              description
                "Configure an upper bound";
              leaf addresses {
                description
                  "Maximum addresses that can be learnt on this service instance";
                type uint16 {
                  range "1..1000";
                }
              }
            }
            leaf violation {
              description
                "Configure the response when a MAC security policy is violated";
              tailf:cli-full-command;
              type enumeration {
                enum "protect";
                enum "restrict";
              }
            }
          }
        }
        // interface * / service instance * ethernet / service-policy
        container service-policy {
          description
            "Attach a policy-map to an EFP";
          list input {
            description
              "service policy input";
            tailf:cli-suppress-mode;
            tailf:cli-delete-when-empty;
            key "name";
            leaf name {
              type string;
              tailf:non-strict-leafref {
                path "/ios:native/policy-map/name";
              }
            }
          }
          list output {
            description
              "service policy output";
            tailf:cli-suppress-mode;
            tailf:cli-delete-when-empty;
            key "name";
            leaf name {
              type string;
              tailf:non-strict-leafref {
                path "/ios:native/policy-map/name";
              }
            }
          }
        }
        // interface * / service instance * ethernet / shutdown
        leaf shutdown {
          description
            "Take the Service Instance out of Service";
          tailf:cli-full-command;
          type empty;
        }
        // interface * / service instance * ethernet / xconnect
        uses interface-xconnect-grouping;
        // interface * / service instance * ethernet / cfm
        container cfm {
          description
            "Ethernet CFM EFP subcommands";
          container encapsulation {
            description
              "Configure CFM ethernet frame encapsulation";
            container dot1ad {
              description
                "802.1ad - Provider Bridges";
              tailf:cli-sequence-commands;
              tailf:cli-compact-syntax;
              leaf vlan-id {
                tailf:cli-drop-node-name;
                type uint16 {
                  range "1..4094";
                }
              }
              leaf cos {
                description
                  "CoS value to use for CFM packets";
                tailf:cli-break-sequence-commands;
                type uint8 {
                  range "0..7";
                }
              }
              leaf dot1q {
                description
                  "Second tag (dot1q)";
                type uint16 {
                  range "1..4094";
                }
              }
            }
            container dot1q {
              description
                "IEEE 802.1Q Virtual LAN or S-VLAN";
              tailf:cli-sequence-commands;
              tailf:cli-compact-syntax;
              leaf vlan-id {
                tailf:cli-drop-node-name;
                type uint16 {
                  range "1..4094";
                }
              }
              leaf cos {
                description
                  "CoS value to use for CFM packets";
                tailf:cli-break-sequence-commands;
                type uint8 {
                  range "0..7";
                }
              }
              leaf second-dot1q {
                description
                  "inner 802.1Q Virtual LAN or C-VLAN";
                type uint16 {
                  range "1..4094";
                }
              }
            }
          }
          container mep {
            description
              "Maintenance End Point";
            tailf:cli-sequence-commands;
            tailf:cli-compact-syntax;
            leaf domain {
              description
                "Configure a domain for this mep";
              type string;
            }
            leaf mpid {
              description
                "Maintenance End Point Identifier";
              type uint16 {
                range "1..8191";
              }
            }
          }
          container mip {
            description
              "Maintenance Intermediate Point";
            leaf level {
              description
                "Maintenance Level";
              type uint8;
            }
          }
        }
        // interface * / service instance * ethernet / l2protocol
        container l2protocol {
          description
            "Configure l2 control protocol processing";
          container peer {
            description
              "peer L2 control protocol packets as data";
            presence "true";
            uses interface-ethernet-service-instance-l2protocol-grouping;
          }
          container forward {
            description
              "forward L2 control protocol packets as data";
            presence "true";
            uses interface-ethernet-service-instance-l2protocol-grouping;
          }
          container tunnel {
            description
              "tunnel L2 control protocol packets as data";
            presence "true";
            uses interface-ethernet-service-instance-l2protocol-grouping;
          }
        }
      }
    }

  } // interface-ethernet-grouping

  grouping interface-zone-member-grouping {

    // interface * / zone-member
    container zone-member {
      description
        "Apply zone name";
      leaf security {
        description
          "Security zone";
        type string;
        tailf:non-strict-leafref {
          path "/ios:native/zone/security/id";
        }
      }
    }

  }

  grouping interface-cellular-grouping {
    //interface * / dialer
    container dialer {
      leaf in-band {
        type empty;
      }
      leaf idle-timeout {
        type uint32;
      }
      leaf string {
        type string;
      }
      leaf watch-group {
        type uint32;
      }
    }
    //interface * / async
    container async {
      leaf mode {
        type enumeration {
          enum "interactive";
        }
      }
    }
  }

  grouping interface-pointtopoint-grouping {
    // interface * / ppp
    container ppp {
      description
        "Point-to-Point Protocol";
      leaf accounting {
        description
          "Set PPP network accounting method";
        type union {
          type string;
          type enumeration {
            enum "default";
          }
        }
      }
      // interface * /ppp chap
      container chap {
        description
          "Set CHAP authentication parameters";
        leaf hostname {
          description
            "Set alternate CHAP hostname";
          type string;
        }
        leaf challenge-length {
          description
            "Challenge Length for CHAP";
          type uint8 {
            range "16..63";
          }
        }
      }
      // interface * / ppp authentication
      container authentication {
        description
          "Set PPP link authentication method";
        tailf:cli-compact-syntax;
        tailf:cli-sequence-commands;
        leaf method {
          tailf:cli-drop-node-name;
          type enumeration {
            enum "chap";
            enum "eap";
            enum "ms-chap";
            enum "ms-chap-v2";
            enum "pap";
          }
        }
        leaf list-name {
          tailf:cli-break-sequence-commands;
          tailf:cli-drop-node-name;
          type string;
          tailf:cli-disallow-value "(callback)|(callin)|(callout)|(default)|(eap)|(ms-chap)|(ms-chap-v2)|(one-time)|(optional)|(pap)";
        }
        leaf chap {
          when "not(../method = 'chap')" {
            tailf:dependency "../method";
          }
          type empty;
        }
        leaf callback {
          description
            "Authenticate remote on callback only";
          type empty;
        }
        leaf callin {
          description
            "Authenticate remote on incoming call only";
          type empty;
        }
        leaf callout {
          description
            "Authenticate remote on outgoing call only";
          type empty;
        }
        leaf default {
          description
            "Use the default authentication list";
          type empty;
        }
        leaf eap {
          description
            "Extensible Authentication Protocol (EAP)";
          when "not(../method = 'eap')" {
            tailf:dependency "../method";
          }
          type empty;
        }
        leaf ms-chap {
          description
            "Microsoft Challenge Handshake Authentication Protocol (MS-CHAP)";
          when "not(../method = 'ms-chap')" {
            tailf:dependency "../method";
          }
          type empty;
        }
        leaf ms-chap-v2 {
          description
            "Microsoft CHAP Version 2 (MS-CHAP-V2)";
          when "not(../method = 'ms-chap-v2')" {
            tailf:dependency "../method";
          }
          type empty;
        }
        leaf one-time {
          description
            "Allow use of username*OTP for one-time passwords";
          type empty;
        }
        leaf optional {
          description
            "Allow peer to refuse to authenticate";
          type empty;
        }
        leaf pap {
          description
            "Password Authentication Protocol (PAP)";
          when "not(../method = 'pap')" {
            tailf:dependency "../method";
          }
          type empty;
        }
      }
      // interface * / ppp authorization
      leaf authorization {
        description
          "Set PPP network authorization method";
        type union {
          type string;
          type enumeration {
            enum "default";
          }
        }
      }
      // interface * / ppp ipcp
      container ipcp {
        description
          "Set IPCP negotiation options";
        container dns {
          description
            "Specify DNS negotiation options";
          tailf:cli-compact-syntax;
          tailf:cli-sequence-commands;
          leaf primary {
            tailf:cli-drop-node-name;
            type inet:ipv4-address;
          }
        }
      }
      // interface * / ppp multilink
      container multilink {
        description
          "Make interface multilink capable";
        tailf:cli-display-separated;
        presence "true";
        container links {
          description
            "Specify the limits on the number of links in a bundle";
          container minimum {
            description
              "Minimum number of links desired in the bundle";
            tailf:cli-compact-syntax;
            tailf:cli-sequence-commands {
              tailf:cli-reset-all-siblings;
            }
            leaf minimum-value {
              tailf:cli-drop-node-name;
              type uint8;
            }
            leaf mandatory {
              description
                "Disable network layer until minimum number of links is reach";
              type empty;
            }
          }
        }
        // interface * / ppp multilink group
        leaf group {
          description
            "Put interface in a multilink bundle";
          type uint32 {
            range "1..2147483647";
          }
        }
        // interface * / ppp multilink endpoint
        container endpoint {
          description
            "Configure the local Endpoint Discriminator";
          leaf string {
            description
              "Use specified string";
            type string;
          }
        }
        // interface * / ppp multilink fragment
        container fragment {
          description
            "Specify fragmentation parameters";
          container delay {
            description
              "Specify the maximum delay for each fragment";
            tailf:cli-compact-syntax;
            tailf:cli-sequence-commands {
              tailf:cli-reset-siblings;
            }
            leaf delay-value {
              tailf:cli-drop-node-name;
              type uint16 {
                range "0..1000";
              }
            }
            leaf additional-delay-value {
              tailf:cli-drop-node-name;
              type uint16 {
                range "1..999";
              }
            }
          }
        }
      }
    }
  }

  grouping interface-pseudowire-grouping {
    // interface * / description
    leaf description {
      description
        "Interface specific description";
      tailf:cli-multi-value;
      tailf:cli-full-command;
      type string {
        length "0..240";
      }
    }
    container label {
      description
        "MPLS local and remote pseudowire static labels";
      when "../encapsulation = 'mpls'";
      tailf:cli-compact-syntax;
      tailf:cli-sequence-commands {
        tailf:cli-reset-siblings;
      }
      leaf local {
        tailf:cli-drop-node-name;
        type uint32 {
          range "20000..40000";
        }
      }
      leaf remote {
        tailf:cli-drop-node-name;
        type uint32 {
          range "16..1048575";
        }
      }
    }
    // interface * / mtu
    leaf mtu {
      description
        "Set Maximum Transmission Unit (MTU)";
      tailf:cli-full-command;
      type uint16 {
        range "64..65535";
      }
    }
    // interface * / neighbor
    container neighbor {
      description
        "Neighbor options";
      tailf:cli-compact-syntax;
      tailf:cli-sequence-commands {
        tailf:cli-reset-siblings;
      }
      leaf peer-ip {
        tailf:cli-drop-node-name;
        type inet:ipv4-address;
      }
      leaf vc-id {
        tailf:cli-drop-node-name;
        type uint64 {
          range "1..4294967295";
        }
      }
    }
    // interface * / performance monitor
    container performance {
      description
        "Global performance monitor configuration";
      container monitor {
        description
          "monitor";
        leaf-list context {
          description
            "Select ezPM context";
          tailf:cli-list-syntax;
          type string;
        }
      }
    }
    // interface * / service-policy
    container service-policy {
      description
        "Configure CPL Service Policy";
      leaf input {
        tailf:cli-full-command;
        description
          "Assign policy-map to the input of an interface";
        type string;
        tailf:non-strict-leafref {
          path "/ios:native/policy-map/name";
        }
      }
      leaf output {
        tailf:cli-full-command;
        description
          "Assign policy-map to the output of an interface";
        type string;
        tailf:non-strict-leafref {
          path "/ios:native/policy-map/name";
        }
      }
    }
    // interface * / shutdown
    leaf shutdown {
      description
        "Shutdown the selected interface";
      tailf:cli-full-command;
      type empty;
    }
    // interface * / signaling
    container signaling {
      description
        "Signaling options";
      container protocol-mpls {
        tailf:cli-drop-node-name;
        when "../../encapsulation = 'mpls'";
        leaf protocol {
          description
            "Signaling protocol to use";
          type enumeration {
            enum "ldp";
            enum "none";
          }
        }
      }
      container protocol-l2tpv2 {
        tailf:cli-drop-node-name;
        when "../../encapsulation = 'l2tpv2'";
        leaf protocol {
          description
            "Signaling protocol to use";
          type enumeration {
            enum "l2tpv2";
            enum "none";
          }
        }
      }
      container protocol-l2tpv3 {
        tailf:cli-drop-node-name;
        when "../../encapsulation = 'l2tpv3'";
        leaf protocol {
          description
            "Signaling protocol to use";
          type enumeration {
            enum "l2tpv3";
            enum "l2tpv3ietf";
            enum "none";
          }
        }
      }
    }
    container source {
      description
        "Get config from another source";
      container template {
        description
          "Get config from a template";
        container type {
          description
            "Type of the template";
          leaf pseudowire {
            description
              "Template customized interface pseudowire";
            type string;
          }
        }
      }
    }
    container vc {
      description
        "Virtual Circuit options";
      when "../encapsulation = 'mpls'";
      leaf type {
        description
          "Virtual Circuit type to use";
        type enumeration {
          enum "ethernet";
          enum "vlan";
        }
      }
    }
  }

  grouping otv-isis-authentication-grouping {
    container authentication {
      description
        "ISIS authentication for interface related PDUs";
      leaf key-chain {
        description
          "Authentication key-chain";
        type string;
      }
      leaf mode {
        description
          "Authentication mode for PDUs";
        type enumeration {
          enum "md5";
          enum "text";
        }
      }
      leaf send-only {
        description
          "Authentication send only, receive ignore";
        type empty;
      }
    }
  }

  grouping otv-isis-hostname-grouping {
    container hostname {
      description
        "Dynamic hostname for IS-IS";
      leaf dynamic {
        description
          "Dynamic hostname";
        type empty;
      }
    }
  }

  grouping otv-isis-skeptical-grouping {
    container skeptical {
      description
        "Be a cautious NSF helper when refresh adjacency";
      leaf interval {
        description
          "Interval during which holdtime will NOT be refreshed";
        type uint32 {
          range "0..1440";
        }
      }
    }
  }

  grouping otv-isis-log-adjacency-changes-grouping {
    container log-adjacency-changes {
      description
        "Log changes in adjacency state";
      presence "true";
      leaf all {
        description
          "Include changes generated by non-IIH event";
        type empty;
      }
    }
  }

  grouping otv-isis-site-grouping {
    container default {
      description
        "Set a command to its defaults";
      leaf log-adjacency-changes {
        description
          "Log changes in adjacency state";
        type empty;
      }
      leaf net {
        description
          "A Network Entity Title for this process";
        type empty;
      }
      container skeptical {
        description
          "Be a cautious NSF helper when refresh adjacency";
        leaf interval {
          description
            "Interval during which holdtime will NOT be refreshed";
          type empty;
        }
      }
    }
    uses otv-isis-log-adjacency-changes-grouping;
    leaf net {
      description
        "A Network Entity Title for this process";
      type string;
    }
    uses otv-isis-skeptical-grouping;
  }

  grouping otv-isis-overlay-grouping {
    uses otv-isis-authentication-grouping;
    container default {
      description
        "Set a command to its defaults";
      uses otv-isis-authentication-grouping;
      uses otv-isis-hostname-grouping;
      leaf delayed-deletion-interval {
        description
          "Set delayed deletion interval";
        type empty;
      }
      leaf log-adjacency-changes {
        description
          "Log changes in adjacency state";
        type empty;
      }
      leaf lsp-gen-interval {
        description
          "Minimum interval between regenerating same LSP";
        type empty;
      }
      leaf lsp-mtu {
        description
          "Set maximum LSP size";
        type empty;
      }
      leaf lsp-refresh-interval {
        description
          "Set LSP refresh interval";
        type empty;
      }
      leaf max-lsp-lifetime {
        description
          "Set maximum LSP lifetime";
        type empty;
      }
      leaf prc-interval {
        description
          "Minimum interval between partial route calculations";
        type empty;
      }
      leaf spf-interval {
        description
          "Minimum interval between SPF calculations";
        type empty;
      }
      container nsf {
        description
          "Non-stop forwarding";
        leaf cisco {
          description
            "Checkpoint method";
          type empty;
        }
        leaf interval {
          description
            "Minimum required stable interval between restarts";
          type empty;
        }
      }
      container skeptical {
        description
          "Be a cautious NSF helper when refresh adjacency";
        leaf interval {
          description
            "Interval during which holdtime will NOT be refreshed";
          type empty;
        }
      }
    }
    leaf delayed-deletion-interval {
      description
        "Set delayed deletion interval";
      type uint32 {
        range "1..86400";
      }
    }
    uses otv-isis-hostname-grouping;
    uses otv-isis-log-adjacency-changes-grouping;
    container lsp-gen-interval {
      description
        "Minimum interval between regenerating same LSP";
      tailf:cli-sequence-commands;
      tailf:cli-compact-syntax;
      leaf seconds {
        tailf:cli-drop-node-name;
        type uint8 {
          range "1..120";
        }
      }
      leaf milliseconds {
        tailf:cli-drop-node-name;
        tailf:cli-optional-in-sequence;
        type uint32 {
          range "1..120000";
        }
      }
      leaf wait {
        tailf:cli-drop-node-name;
        tailf:cli-optional-in-sequence;
        type uint32 {
          range "1..120000";
        }
      }
    }
    leaf lsp-mtu {
      description
        "Set maximum LSP size";
      type uint32 {
        range "128..4352";
      }
    }
    leaf lsp-refresh-interval {
      description
        "Set LSP refresh interval";
      type uint32 {
        range "1..65535";
      }
    }
    leaf max-lsp-lifetime {
      description
        "Set maximum LSP lifetime";
      type uint32 {
        range "1..65535";
      }
    }
    container nsf {
      description
        "Non-stop forwarding";
      leaf cisco {
        description
          "Checkpoint method";
        type empty;
      }
      leaf interval {
        description
          "Minimum required stable interval between restarts";
        type uint32 {
          range "0..1440";
        }
      }
    }
    container prc-interval {
      description
        "Minimum interval between partial route calculations";
      tailf:cli-sequence-commands;
      tailf:cli-compact-syntax;
      leaf seconds {
        tailf:cli-drop-node-name;
        type uint8 {
          range "1..120";
        }
      }
      leaf milliseconds {
        tailf:cli-drop-node-name;
        tailf:cli-optional-in-sequence;
        type uint32 {
          range "1..120000";
        }
      }
      leaf wait {
        tailf:cli-drop-node-name;
        tailf:cli-optional-in-sequence;
        type uint32 {
          range "1..120000";
        }
      }
    }
    uses otv-isis-skeptical-grouping;
    container spf-interval {
      description
        "Minimum interval between SPF calculations";
      tailf:cli-sequence-commands;
      tailf:cli-compact-syntax;
      leaf seconds {
        tailf:cli-drop-node-name;
        type uint8 {
          range "1..120";
        }
      }
      leaf milliseconds {
        tailf:cli-drop-node-name;
        tailf:cli-optional-in-sequence;
        type uint32 {
          range "1..120000";
        }
      }
      leaf wait {
        tailf:cli-drop-node-name;
        tailf:cli-optional-in-sequence;
        type uint32 {
          range "1..120000";
        }
      }
    }
  }

  grouping otv-isis-grouping {
    container isis {
      description
        "ISIS interface subcommands";
      uses otv-isis-authentication-grouping;
      leaf bfd {
        description
          "Bidirectional Forwarding Protocol";
        type empty;
      }
      container hello {
        description
          "Add padding to IS-IS hello packets";
        container padding {
          description
            "Pad hello packets";
          presence "true";
          leaf always {
            description
              "Never pad hello packets if no prefix present";
            type empty;
          }
        }
      }
      container hello-interval {
        description
          "Set Hello interval in seconds";
        leaf value {
          tailf:cli-drop-node-name;
          type uint16 {
            range "1..65535";
          }
        }
        leaf minimal {
          description
            "Holdtime 1 second, interval depends on multiplier";
          type empty;
        }
      }
      leaf hello-multiplier {
        description
          "Set multiplier for Hello holding time";
        type uint16 {
          range "3..1000";
        }
      }
      leaf priority {
        description
          "Set priority for Designated Router election";
        type uint8 {
          range "0..127";
        }
      }
    }
  }

  grouping interface-overlay-grouping {
    container otv {
      description
        "Configure OTV information";
      container adjacency-server {
        description
          "Indicate if the box is an Adjacency Server";
        leaf unicast-only {
          description
            "Unicast Only";
          type empty;
        }
      }
      leaf control-group {
        description
          "OTV VPN control multicast group";
        type inet:ipv4-address;
      }
      leaf data-group {
        description
          "Multicast group range for data";
        type ios:ipv4-prefix;
      }
      container encapsulation-format {
        description
          "Encapsulation format";
        container ip {
          description
            "Use IP for outer header encapsulation";
          leaf gre {
            description
              "Use GRE middle header encapsulation";
            type empty;
          }
        }
      }
      leaf filter-fhrp {
        description
          "Configure to not forward HSRP, GLBP, and VRRP packets on overlay";
        type empty;
      }
      container isis {
        description
          "ISIS interface subcommands";
        uses otv-isis-authentication-grouping;
        leaf bfd {
          description
            "Bidirectional Forwarding Protocol";
          type empty;
        }
        leaf csnp-interval {
          description
            "Set CSNP interval in seconds";
          type uint16 {
            range "0..65535";
          }
        }
        container hello {
          description
            "Add padding to IS-IS hello packets";
          container padding {
            description
              "Pad hello packets";
            presence "true";
            leaf always {
              description
                "Never pad hello packets if no prefix present";
              type empty;
            }
          }
        }
        container hello-interval {
          description
            "Set Hello interval in seconds";
          leaf value {
            tailf:cli-drop-node-name;
            type uint16 {
              range "1..65535";
            }
          }
          leaf minimal {
            description
              "Holdtime 1 second, interval depends on multiplier";
            type empty;
          }
        }
        leaf hello-multiplier {
          description
            "Set multiplier for Hello holding time";
          type uint16 {
            range "3..1000";
          }
        }
        leaf lsp-interval {
          description
            "Set LSP transmission interval";
          type uint64 {
            range "1..4294967295";
          }
        }
        container metric {
          description
            "Configure the metric for interface";
          tailf:cli-sequence-commands;
          tailf:cli-compact-syntax;
          choice default-maximum {
            case default-case {
              leaf default {
                tailf:cli-drop-node-name;
                type uint32 {
                  range "1..16777214";
                }
              }
            }
            case maximum-case {
              leaf maximum {
                description
                  "Maximum metric. All routers will exclude this link from their SPF";
                type empty;
              }
            }
          }
          leaf delay {
            tailf:cli-drop-node-name;
            tailf:cli-optional-in-sequence;
            type uint32 {
              range "1..16777214";
            }
          }
          leaf expense {
            tailf:cli-drop-node-name;
            tailf:cli-optional-in-sequence;
            type uint32 {
              range "1..16777214";
            }
          }
          leaf error {
            tailf:cli-drop-node-name;
            tailf:cli-optional-in-sequence;
            type uint32 {
              range "1..16777214";
            }
          }
        }
        leaf priority {
          description
            "Set priority for Designated Router election";
          type uint8 {
            range "0..127";
          }
        }
        leaf retransmit-interval {
          description
            "Set per-LSP retransmission interval";
          type uint16;
        }
        leaf retransmit-throttle-interval {
          description
            "Set interface LSP retransmission interval";
          type uint16;
        }
      }
      container join-interface {
        description
          "OTV VPN join-interface";
        uses interface-grouping;
      }
      container suppress {
        description
          "Enable overlay packet suppression";
        leaf arp-nd {
          description
            "Suppress sending ARP and neighbor discovery packets on overlay";
          type empty;
        }
      }
      container use-adjacency-server {
        description
          "Point to remote Adjacency Server address";
        tailf:cli-compact-syntax;
        tailf:cli-sequence-commands {
          tailf:cli-reset-siblings;
        }
        leaf remote-pri-ip {
          tailf:cli-drop-node-name;
          tailf:cli-incomplete-command;
          type inet:ipv4-address;
        }
        leaf remote-sec-ip {
          tailf:cli-drop-node-name;
          tailf:cli-break-sequence-commands;
          type inet:ipv4-address;
        }
        leaf unicast-only {
          description
            "Unicast Only Capability";
          tailf:cli-full-command;
          type empty;
        }
      }
      leaf vpn-name {
        description
          "OTV VPN name";
        type string;
      }
    }
  }

  grouping crypto-pki-token-grouping {
    // max-retries  maximum number of consecutive login failures permitted
    container removal {
      description
        "actions to take after token removal";
      leaf timeout {
        description
          "seconds after token removal at which keys from the token are cleared";
        type uint16 {
          range "0..480";
        }
      }
    }
    // secondary    token-specific configuration files
    // user-pin     PIN to access token
  }

  grouping max-path-grouping {
    container max-path {
      tailf:cli-drop-node-name;
      tailf:cli-compact-syntax;
      tailf:cli-sequence-commands {
        tailf:cli-reset-siblings;
      }
      tailf:display-when "../../../../../ipv4 or ../../../../ipv4  or ../../../ipv4 or ../../ipv4 or ../../../../../ipv6 or ../../../../ipv6  or ../../../ipv6 or ../../ipv6  or ../../../nsap or ../../nsap  or ../../../vpnv4 or ../../vpnv4";
      leaf max {
        tailf:cli-drop-node-name;
        type uint16 {
          range "1..32";
        }
      }
    }
    container external-rtfilter {
      description
        "VPN prefix multipath on external RTFilter peers";
      tailf:cli-compact-syntax;
      tailf:cli-sequence-commands {
        tailf:cli-reset-siblings;
      }
      tailf:display-when "../../../rtfilter";
      leaf max {
        tailf:cli-drop-node-name;
        type uint16 {
          range "1..32";
        }
      }
    }
  }

  grouping metric-route-map-grouping {
    leaf metric {
      description
        "Metric for redistributed routes";
      type uint32 {
        range "0..4294967295";
      }
    }
    leaf route-map {
      description
        "Route map reference";
      type string;
    }
  }

  grouping route-map-metric-grouping {
    leaf route-map {
      description
        "Route map reference";
      type string;
    }
    leaf metric {
      description
        "Metric for redistributed routes";
      type uint32 {
        range "0..4294967295";
      }
    }
  }

  grouping redistribute-isis-grouping {
    choice osi-ip-choice {
      leaf ip {
        description
          "Redistribution of IP dynamic routes";
        type empty;
      }
      leaf clns {
        description
          "Redistribution of OSI dynamic routes";
        type empty;
      }
    }
    leaf routes {
      tailf:cli-drop-node-name;
      type enumeration {
        enum "level-1";
        enum "level-2";
        enum "level-1-2";
      }
    }
    uses metric-route-map-grouping;
  }

  grouping bgp-address-family-grouping {
    container aggregate-address {
      description
        "Configure BGP aggregate entries";
      tailf:cli-compact-syntax;
      tailf:cli-sequence-commands {
        tailf:cli-reset-all-siblings;
      }
      tailf:display-when "../ipv4 or ../../ipv4 or ../../../ipv4 or ../ipv6 or ../../ipv6 or ../../../ipv6";
      leaf address {
        tailf:cli-drop-node-name;
        type inet:ipv4-address;
      }
      leaf mask {
        tailf:cli-drop-node-name;
        type inet:ipv4-address;
      }
      leaf advertise-map {
        tailf:cli-break-sequence-commands;
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
    // router bgp * / bgp
    container bgp {
      description
        "BGP specific commands";
      // router bgp * / bgp router-id
      leaf router-id {
        tailf:cli-full-command;
        description
          "Override configured router identifier (peers will reset)";
        type inet:ipv4-address;
      }
      // router bgp * / bgp always-compare-med
      leaf always-compare-med {
        description
          "Allow comparing MED from different neighbors";
        tailf:cli-full-command;
        type empty;
      }
      // router bgp * / bgp aggregate-timer
      leaf aggregate-timer {
        description
          "Timer interval";
        type uint8 {
          range "6..60";
        }
      }
      // router bgp * / bgp nopeerup-delay
      container nopeerup-delay {
        description
          "Set how long BGP will wait for the first peer to come up before beginning the update delay or graceful restart timers (in seconds)";
        leaf cold-boot {
          description
            "Delay in seconds";
          type uint16 {
            range "1..3600";
          }
        }
        leaf nsf-switchover {
          description
            "Delay in seconds";
          type uint16 {
            range "1..3600";
          }
        }
        leaf post-boot {
          description
            "Delay in seconds";
          type uint16 {
            range "1..3600";
          }
        }
        leaf user-initiated {
          description
            "Delay in seconds";
          type uint16 {
            range "1..3600";
          }
        }
      }
      // router bgp * / bgp recursion
      container recursion {
        description
          "recursion rule for the nexthops";
        leaf host {
          description
            "recursion via host for the nexthops";
          type empty;
        }
      }
      // router bgp * / bgp advertise-best-external
      leaf advertise-best-external {
        description
          "Advertise best external path to internal peers";
        type empty;
      }
      // router bgp * / bgp additional-paths
      container additional-paths {
        description
          "Additional paths in the BGP table";
        leaf install {
          description
            "Additional paths to install into RIB";
          type empty;
        }
        leaf receive {
          description
            "Receive additional paths from neighbors";
          type empty;
        }
        container select {
          description
            "Selection criteria to pick the paths";
          container all {
            description
              "Select all available paths";
            presence "true";
            container best {
              description
                "Select best N paths";
              list range {
                tailf:cli-drop-node-name;
                tailf:cli-suppress-mode;
                key "range";
                leaf range {
                  description
                    "Number of best paths in additional paths to be selected";
                  type uint8 {
                    range "2..3";
                  }
                }
                leaf group-best {
                  description
                    "Select group-best path";
                  type empty;
                }
              }
            }
            container group-best {
              description
                "Select group-best path";
              presence "true";
              leaf best {
                description
                  "Number of best paths in additional paths to be selected";
                type uint8 {
                  range "2..3";
                }
              }
            }
          }
          container backup {
            description
              "Select backup path";
            presence "true";
            leaf best-external {
              description
                "Select best-external path";
              type empty;
            }
          }
          container best {
            description
              "Select best N paths";
            list range {
              tailf:cli-drop-node-name;
              tailf:cli-suppress-mode;
              key "range";
              leaf range {
                description
                  "Number of best paths in additional paths to be selected";
                type uint8 {
                  range "2..3";
                }
              }
              leaf all {
                description
                  "Select all available paths";
                type empty;
              }
              container group-best {
                description
                  "Select group-best path";
                presence "true";
                leaf all {
                  description
                    "Select all available paths";
                  type empty;
                }
              }
            }
          }
          container best-external {
            description
              "Select best-external path";
            presence "true";
            leaf backup {
              description
                "Select backup path";
              type empty;
            }
          }
          container group-best {
            description
              "Select group-best path";
            presence "true";
            leaf all {
              description
                "Select all available paths";
              type empty;
            }
            leaf best {
              description
                "Number of best paths in additional paths to be selected";
              type uint8 {
                range "2..3";
              }
            }
          }
        }
        container send {
          description
            "Send additional paths to neighbors";
          presence "true";
          leaf receive {
            description
              "Receive additional paths from neighbors";
            type empty;
          }
        }
      }
      // router bgp * / bgp bestpath
      container bestpath {
        description
          "Change the default bestpath selection";
        leaf compare-routerid {
          tailf:cli-full-command;
          type empty;
        }
        container cost-community {
          description
            "cost community";
          leaf ignore {
            description
              "Ignore cost communities in bestpath selection";
            type empty;
          }
        }
        container igp-metric {
          description
            "igp metric";
          leaf ignore {
            description
              "Ignore igp metric in bestpath selection";
            type empty;
          }
        }
        container med {
          description
            "MED attribute";
          choice med-choice {
            container confed {
              description
                "Compare MED among confederation paths";
              presence "Compare MED among confederation paths";
              leaf missing-at-worst {
                description
                  "Treat missing MED as the least preferred one";
                type empty;
              }
            }
            leaf missing-at-worst {
              description
                "Treat missing MED as the least preferred one";
              type empty;
            }
          }
        }
      }
      // router bgp * / bgp client-to-client
      container client-to-client {
        description
          "Configure client to client route reflection";
        leaf reflection {
          description
            "reflection of routes allowed";
          type empty;
        }
      }
      // router bgp * / bgp cluster-id
      leaf cluster-id {
        tailf:cli-full-command;
        type union {
          type uint32 {
            range "1..4294967295";
          }
          type inet:ipv4-address;
        }
      }
      // router bgp * / bgp confederation
      container confederation {
        description
          "AS confederation parameters";
        leaf identifier {
          tailf:cli-full-command;
          type inet:as-number;
        }
        container peers {
          description
            "Peer ASs in BGP confederation";
          leaf-list peers-as {
            tailf:cli-drop-node-name;
            tailf:cli-flat-list-syntax;
            type inet:as-number;
          }
        }
      }
      // router bgp * / bgp consistency-checker
      container consistency-checker {
        description
          "Consistency-checker";
        container auto-repair {
          description
            "Auto-Repair";
          presence "true";
          leaf interval {
            description
              "Interval (minutes)";
            type uint16 {
              range "5..1440";
            }
          }
        }
        container error-message {
          description
            "Log Error-Msg";
          presence "true";
          leaf interval {
            description
              "Interval (minutes)";
            type uint16 {
              range "5..1440";
            }
          }
        }
      }
      // router bgp * / bgp dampening
      container dampening {
        description
          "Enable route-flap dampening";
        presence "enable bgp route-flap dampening";
        choice dampening-choice {
          leaf route-map {
            description
              "Route-map to specify criteria for dampening";
            type string;
          }
          container dampen {
            tailf:cli-drop-node-name;
            tailf:cli-compact-syntax;
            tailf:cli-sequence-commands;
            leaf half-life-time {
              tailf:cli-drop-node-name;
              tailf:cli-incomplete-command;
              type uint8 {
                range "1 .. 45";
              }
            }
            leaf reuse-time {
              tailf:cli-drop-node-name;
              tailf:cli-incomplete-command;
              type uint16 {
                range "1 .. 20000";
              }
            }
            leaf suppress-time {
              tailf:cli-drop-node-name;
              tailf:cli-incomplete-command;
              type uint16 {
                range "1 .. 20000";
              }
            }
            leaf max-suppress-time {
              tailf:cli-drop-node-name;
              type uint8 {
                range "1 .. 255";
              }
            }
          }
        }
      }
      // router bgp * / bgp default
      container default {
        description
          "Configure BGP defaults";
        choice default-choice {
          leaf ipv4-unicast {
            description
              "Activate ipv4-unicast for a peer by default";
            tailf:cli-boolean-no;
            tailf:cli-trim-default;
            type boolean;
          }
          leaf ipv6-nexthop {
            description
              "Default IPv6 nexthop format";
            type empty;
          }
          leaf local-preference {
            description
              "local preference (higher=more preferred)";
            type uint32 {
              range "1..4294967295";
            }
          }
          leaf route-target {
            description
              "Control behavior based on Route-Target attributes";
            type enumeration {
              enum "filter";
            }
          }
        }
      }
      // router bgp * / bgp deterministic-med
      leaf deterministic-med {
        tailf:cli-full-command;
        description
          "Pick the best-MED path among paths advertised from the neighboring AS";
        type empty;
      }
      // router bgp * / bgp dmzlink-bw
      leaf dmzlink-bw {
        tailf:cli-full-command;
        description
          "Use DMZ Link Bandwidth as weight for BGP multipaths";
        type empty;
      }
      // router bgp * / bgp enforce-first-as
      leaf enforce-first-as {
        tailf:cli-full-command;
        description
          "Enforce the first AS for EBGP routes(default)";
        type empty;
      }
      //router bgp * /bgp enhanced-error
      leaf enhanced-error {
        description
          "Enabled BGP Enhanced error handling";
        type empty;
      }
      // router bgp * / bgp fast-external-fallover
      leaf fast-external-fallover {
        tailf:cli-full-command;
        description
          "Immediately reset session if a link to a directly connected external peer goes down";
        type empty;
      }
      // router bgp * / bgp graceful-restart
      container graceful-restart {
        description
          "Graceful restart capability parameters";
        presence "Graceful restart capability parameters";
        tailf:cli-display-separated;
        leaf extended {
          type empty;
        }
        leaf restart-time {
          tailf:cli-full-command;
          description
            "Set the max time needed to restart and come back up";
          type uint16 {
            range "1..3600";
          }
        }
        leaf stalepath-time {
          description
            "Set the max time to hold onto restarting peer's stale paths";
          type uint16 {
            range "1..3600";
          }
        }
      }
      // router bgp * / bgp ha-mode
      container ha-mode {
        description
          "Select BGP High Availability mode";
        container sso {
          description
            "BGP High Availability NSR sso mode";
          presence "true";
          leaf prefer {
            description
              "Perfer BGP High Availability NSR sso mode";
            type empty;
          }
        }
      }
      // router bgp * / bgp inject-map *
      list inject-map {
        description
          "Routemap which specifies prefixes to inject";
        tailf:cli-suppress-mode;
        tailf:cli-compact-syntax;
        tailf:cli-sequence-commands;
        tailf:cli-incomplete-command;
        tailf:cli-delete-when-empty;
        key "name";
        leaf name {
          type string;
        }
        leaf exist-map {
          description
            "Routemap which specifies exist condition";
          type string;
        }
        leaf copy-attributes {
          description
            "Copy attributes from aggregate";
          type empty;
        }
      }
      // router bgp * / bgp log-neighbor-changes
      leaf log-neighbor-changes {
        description
          "Log neighbor up/down and reset reason";
        tailf:cli-full-command;
        type empty;
      }
      // router bgp * / bgp maxas-limit
      leaf maxas-limit {
        description
          "Allow AS-PATH attribute from any neighbor imposing a limit on number of ASes";
        tailf:cli-full-command;
        type uint16 {
          range "1..2000";
        }
      }
      // router bgp * / bgp maxcommunity-limit
      leaf maxcommunity-limit {
        description
          "Number of communities in the COMMUNITY attribute";
        type uint16 {
          range "1..1018";
        }
      }
      //router bgp * / bgp route-map
      container route-map {
        description
          "bgp route-map commands";
        leaf priority {
          description
            "Have route-map set commands take priority over BGP commands such ";
          type empty;
        }
      }
      // router bgp * / bgp slow-peer
      container slow-peer {
        description
          "Configure slow-peer";
        container detection {
          description
            "Slow-peer detection";
          presence "true";
          leaf disable {
            description
              "Disable slow-peer detection";
            type empty;
          }
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      // router bgp * / bgp update-group
      container update-group {
        description
          "Manage peers in bgp update groups";
        container split {
          description
            "Split update groups based on Policy";
          leaf as-override {
            description
              "Keep peers with as-override in different update groups";
            type empty;
          }
        }
      }
      // router bgp * / bgp nexthop
      container nexthop {
        description
          "Nexthop tracking commands";
        container trigger {
          description
            "Nexthop triggering";
          leaf delay {
            tailf:cli-full-command;
            description
              "Set the delay to tigger nexthop tracking";
            type uint8 {
              range "0..100";
            }
          }
          leaf enable {
            description
              "Enable nexthop tracking";
            tailf:cli-full-command;
            tailf:cli-boolean-no;
            type boolean;
          }
        }
        leaf route-map {
          description
            "Route map for valid nexthops";
          type string;
        }
      }
      // router bgp * / bgp redistribute-internal
      leaf redistribute-internal {
        description
          "Allow redistribution of iBGP into IGPs (dangerous)";
        tailf:cli-full-command;
        type empty;
      }
      // router bgp * / bgp regexp
      container regexp {
        description
          "Select regular expression engine";
        leaf deterministic {
          description
            "Enable bounded-execution-time regular expression engine";
          type empty;
        }
      }
      // router bgp * / bgp scan-time
      leaf scan-time {
        tailf:cli-full-command;
        description
          "Configure background scanner interval";
        type uint8 {
          range "5..60";
        }
      }
      // router bgp * / bgp soft-reconfig-backup
      leaf soft-reconfig-backup {
        description
          "Use soft-reconfiguration inbound only when route-refresh is not negotiated";
        tailf:cli-full-command;
        type empty;
      }// router bgp * / bgp suppress-inactive
      leaf suppress-inactive {
        description
          "Suppress routes that are not in the routing table";
        tailf:cli-full-command;
        type empty;
      }
      //rotuer bgp * /transport //MOVED from router bgp to router bgp bgp
      container transport {
        description
          "Transport options";
        container path-mtu-discovery {
          description
            "Use transport path MTU discovery";
          presence "true";
          leaf disable {
            description
              "disable";
            type empty;
          }
        }
      }
      // router bgp * / bgp update-delay
      leaf update-delay {
        tailf:cli-full-command;
        description
          "Set the max initial delay for sending update";
        type uint16 {
          range "1..3600";
        }
      }
    }//bgp
    // router bgp * / default-information
    container default-information {
      description
        "Control distribution of default information";
      tailf:display-when "../ipv4 or ../../ipv4 or ../../../ipv4 or ../ipv6 or ../../ipv6 or ../../../ipv6 or ../../nsap or ../nsap";
      leaf originate {
        description
          "Distribute a default route";
        type empty;
      }
    }
    // router bgp * / default-metric
    leaf default-metric {
      description
        "Set metric of redistributed routes";
      tailf:cli-full-command;
      tailf:display-when "../ipv4 or ../../ipv4 or ../../../ipv4 or ../ipv6 or ../../ipv6 or ../../../ipv6 or ../../nsap or ../nsap";
      type uint32 {
        range "1..4294967295";
      }
    }
    // router bgp * / distance
    container distance {
      description
        "Define an administrative distance";
      tailf:display-when "../ipv4 or ../../ipv4 or ../../../ipv4  or ../ipv6 or ../../ipv6 or ../../../ipv6";
      container bgp {
        description
          "BGP distance";
        tailf:cli-sequence-commands;
        tailf:cli-compact-syntax;
        leaf extern-as {
          tailf:cli-drop-node-name;
          tailf:cli-incomplete-command;
          type uint16 {
            range "1..255";
          }
        }
        leaf internal-as {
          tailf:cli-drop-node-name;
          tailf:cli-incomplete-command;
          type uint16 {
            range "1..255";
          }
        }
        leaf local {
          tailf:cli-drop-node-name;
          type uint16 {
            range "1..255";
          }
        }
      }
      list adm-distance {
        tailf:cli-drop-node-name;
        tailf:cli-suppress-mode;
        tailf:cli-delete-when-empty;
        key "distance srcip wildbits";
        leaf distance {
          type uint16 {
            range "1..255";
          }
        }
        leaf srcip {
          type inet:ipv4-address;
        }
        leaf wildbits {
          type inet:ipv4-address;
        }
        leaf acl {
          tailf:cli-drop-node-name;
          type union {
            type uint16 {
              range "1..99";
            }
            type uint16 {
              range "1300..1999";
            }
            type string {
              pattern "[a-zA-Z].*";
            }
          }
        }
      }
    }
    // router bgp * / distribute-list
    list distribute-list {
      description
        "Filter networks in routing updates";
      tailf:cli-compact-syntax;
      tailf:cli-suppress-mode;
      tailf:cli-delete-when-empty;
      tailf:display-when "../../../ipv4 or ../../ipv4 or ../ipv4";
      key "id";
      leaf id {
        tailf:cli-incomplete-command;
        type bgp-distribute-list-type;
      }
      choice in-out-choice {
        container in {
          presence "enable incoming routing updates";
          description
            "Filter incoming routing updates";
          leaf interface {
            type string;
          }
        }
        container out {
          presence "enable outgoing routing updates";
          description
            "Filter outgoing routing updates";
          leaf interface {
            type string;
          }
        }
      }
    }
    // router bgp * / maximum-paths
    container maximum-paths {
      description
        "Forward packets over multiple paths";
      tailf:display-when "../../../ipv4 or ../../ipv4 or ../ipv4 or ../../../ipv6 or ../../ipv6 or ../ipv6  or ../../nsap or ../nsap  or ../../rtfilter or ../rtfilter  or ../../vpnv4 or ../vpnv4";
      uses max-path-grouping;
      choice max-path-choice {
        case eibgp-case {
          container eibgp {
            tailf:display-when "../../../ipv4  or ../../../../ipv4  or ../../../ipv6  or ../../../../ipv6 or ../../../vpnv4/flowspec or ../../vpnv4/flowspec";
            description
              "Both eBGP and iBGP paths as multipath";
            uses max-path-grouping;
          }
        }
        case ibgp-case {
          container ibgp {
            tailf:display-when "../../../ipv4  or ../../../../ipv4  or ../../../ipv6  or ../../../../ipv6 or ../../../vpnv4/flowspec or ../../vpnv4/flowspec";
            description
              "iBGP-multipath";
            choice ibgp-choice {
              case a {
                container unequal-cost {
                  description
                    "Perform Un-Equal cost multipath selection";
                  uses max-path-grouping;
                }
              }
              case b {
                uses max-path-grouping;
              }
            }
          }
        }
      }
    }
    // router bgp * / neighbor *
    list neighbor {
      description
        "Specify a neighbor router";
      tailf:cli-suppress-mode;
      tailf:cli-delete-when-empty;
      tailf:cli-incomplete-command;
      ordered-by user;
      must "count(*) > 1" {
        tailf:dependency ".";
      }
      key "id";
      leaf id {
        type union {
          type string;
          type inet:ipv4-address;
          type inet:ipv6-address;
        }
      }
      // router bgp * / neighbor * peer-group
      container peer-group {
        description
          "Member of the peer-group";
        tailf:cli-delete-when-empty;
        presence "true";
        leaf peer-group-name {
          description
            "WORD;;peer-group name";
          tailf:cli-drop-node-name;
          tailf:cli-full-command;
          tailf:cli-diff-dependency "../../remote-as";
          type string;
        }
      }
      // router bgp * / neighbor * remote-as
      leaf remote-as {
        description
          "Specify a BGP neighbor";
        tailf:cli-full-command;
        tailf:cli-delete-container-on-delete;
        type uint16 {
          range "1..65535";
        }
      }
      // router bgp * / neighbor * local-as
      container local-as {
        description
          "Specify a local-as number";
        tailf:cli-compact-syntax;
        tailf:cli-sequence-commands {
          tailf:cli-reset-siblings;
        }
        tailf:cli-delete-when-empty;
        presence "Specify a local-as number";
        leaf as-no {
          tailf:cli-drop-node-name;
          type bgp-as-number-type;
        }
        leaf no-prepend {
          description
            "Do not prepend local-as to updates from ebgp peers";
          type empty;
        }
        leaf replace-as {
          description
            "Replace real AS with local AS in the EBGP updates";
          type empty;
        }
        leaf dual-as {
          description
            "Accept either real AS or local AS from the ebgp peer";
          type empty;
        }
      }
      // router bgp * / neighbor * activate
      leaf activate {
        description
          "Enable the Address Family for this Neighbor";
        tailf:cli-full-command;
              //must "(../remote-as or ../peer-group)" {
              //  tailf:dependency "../remote-as";
              //  tailf:dependency "../peer-group";
              // }
        type empty;
      }
      // router bgp * / neighbor * additional paths
      container additional-paths {
        leaf disable {
          description
            "Disable additional paths for this neighbor";
          type empty;
        }
        leaf receive {
          description
            "Receive additional paths from neighbors";
          type empty;
        }
        container send {
          description
            "Send additional paths to this neighbor";
          presence "true";
          leaf receive {
            description
              "Receive additional paths from this neighbor";
            type empty;
          }
        }
      }
      // router bgp */ neighbor * advertise
      container advertise {
        description
          "Advertise to this neighbor";
        container additional-paths {
          description
            "Advertise additional paths";
          container all {
            description
              "Select all available paths";
            presence "true";
            container best {
              description
                "Select best N paths";
              list best-range {
                tailf:cli-drop-node-name;
                tailf:cli-suppress-mode;
                key "range";
                leaf range {
                  description
                    "Number of best paths in additional paths to be selected";
                  type uint8 {
                    range "2..3";
                  }
                }
                leaf group-best {
                  description
                    "Select group-best paths";
                  type empty;
                }
              }
            }
            container group-best {
              description
                "Select group-best paths";
              presence "true";
              leaf best {
                description
                  "Number of best paths in additional paths to be selected";
                type uint8 {
                  range "2..3";
                }
              }
            }
          }
          container best {
            description
              "Select best N paths";
            list best-range {
              tailf:cli-drop-node-name;
              tailf:cli-suppress-mode;
              key "range";
              leaf range {
                description
                  "Number of best paths in additional paths to be selected";
                type uint8 {
                  range "2..3";
                }
              }
              leaf all {
                description
                  "Select all available paths";
                type empty;
              }
              container group-best {
                description
                  "Select group-best paths";
                presence "true";
                leaf all {
                  description
                    "Select all available paths";
                  type empty;
                }
              }
            }
          }
          container group-best {
            description
              "Select group-best paths";
            presence "true";
            leaf all {
              description
                "Select all available paths";
              type empty;
            }
            leaf best {
              description
                "Number of best paths in additional paths to be selected";
              type uint8 {
                range "2..3";
              }
            }
          }
        }
        leaf best-external {
          description
            "Advertise best-external (at RRs best-internal) path";
          type empty;
        }
        container diverse-path {
          description
            "Advertise diverse path";
          container backup {
            description
              "Diverse path can be backup path";
            presence "true";
            leaf mpath {
              description
                "Diverse path can be multipath";
              type empty;
            }
          }
          leaf mpath {
            description
              "Diverse path can be multipath";
            type empty;
          }
        }
      }
      // router bgp */ neighbor * advertise-map
      container advertise-map {
        description
          "specify route-map for conditional advertisement";
        list name {
          tailf:cli-drop-node-name;
          tailf:cli-suppress-mode;
          key "word";
          leaf word {
            description
              "advertise route-map name";
            type string;
          }
          leaf exist-map {
            description
              "condition route-map name";
            type string;
          }
          leaf non-exist-map {
            description
              "condition route-map name";
            type string;
          }
        }
      }
      // router bgp */ neighbor * aigp
      container aigp {
        description
          "Enable a AIGP on neighbor";
        presence "true";
        container send {
          description
            "Cost community or MED carrying AIGP VALUE";
          container cost-community {
            description
              "Cost extended community carrying AIGP Value";
            list cc-range {
              tailf:cli-drop-node-name;
              tailf:cli-suppress-mode;
              key "range";
              leaf range {
                description
                  "Community ID";
                type uint8 {
                  range "0..255";
                }
              }
              container poi {
                description
                  "Point of Insertion";
                container igp-cost {
                  description
                    "Point of Insertion After IGP";
                  presence "true";
                  leaf transitive {
                    description
                      "Cost community is Transitive";
                    type empty;
                  }
                }
                container pre-bestpath {
                  description
                    "Point of Insertion At Beginning";
                  presence "true";
                  leaf transitive {
                    description
                      "Cost community is Transitive";
                    type empty;
                  }
                }
              }
            }
          }
          leaf med {
            description
              "Med carrying AIGP Value";
            type empty;
          }
        }
      }
      //router bgp * /neighbor * allow-policy
      leaf allow-policy {
        description
          "Enable the policy support for this IBGP Neighbor";
        type empty;
      }
      //router bgp * /neighbor * announce
      container announce {
        description
          "Announce RPKI State using an Extended Community";
        container rpki {
          description
            "Announce RPKI information using an Extended Community";
          leaf state {
            description
              "Announce RPKI State information using an Extended Community";
            type empty;
          }
        }
      }
      // router bgp * / neighbor * advertisement-interval
      leaf advertisement-interval {
        description
          "Minimum interval between sending BGP routing updates";
        tailf:cli-full-command;
        type uint16 {
          range "0..600";
        }
      }
      // router bgp * / neighbor * allowas-in
      container allowas-in {
        description
          "Accept as-path with my AS present in it";
        presence "accept as-paths";
        tailf:cli-delete-when-empty;
        leaf as-number {
          tailf:cli-drop-node-name;
          type uint8 {
            range "1..10";
          }
        }
      }
      // router bgp * / neighbor * as-override
      container as-override {
        description
          "Override matching AS-number while sending update";
        tailf:cli-delete-when-empty;
        presence "true";
        leaf disable {
          type empty;
        }
      }
      // router bgp * / neighbor * capability
      container capability {
        description
          "Advertise capability to the peer";
        container orf {
          description
            "Advertise ORF capability to the peer";
          leaf-list prefix-list {
            tailf:cli-flat-list-syntax;
            description
              "Advertise prefixlist ORF capability to this neighbor";
            max-elements "1";
            type enumeration {
              enum "both";
              enum "receive";
              enum "send";
            }
          }
        }
      }
      // router bgp * / neighbor * cluster-id
      leaf cluster-id {
        tailf:cli-full-command;
        type union {
          type uint32 {
            range "1..4294967295";
          }
          type inet:ipv4-address;
        }
      }
      // router bgp * / neighbor * default-originate
      container default-originate {
        description
          "Originate default route to this neighbour";
        tailf:cli-delete-when-empty;
        presence "enable originate default route to this neighbour";
        leaf route-map {
          description
            "Route-map to specify criteria to originate default";
          type string;
        }
      }
      // router bgp * / neighbor * description
      leaf description {
        description
          "Neighbor specific description";
        tailf:cli-full-command;
        tailf:cli-multi-value;
        type string;
      }
      // router bgp * / neighbor * disable-connected-check
      leaf disable-connected-check {
        description
          "One-hop away EBGP peer using loopback address";
        tailf:cli-full-command;
        type empty;
      }
      // router bgp * / neighbor * distribute-list *
      list distribute-list {
        description
          "Filter updates to/from this neighbor";
        tailf:cli-suppress-mode;
        tailf:cli-delete-when-empty;
        key "inout";
        leaf inout {
          type enumeration {
            enum "in" {
              tailf:code-name "dist_in";
            }
            enum "out" {
              tailf:code-name "dist_out";
            }
          }
        }
        leaf accesslist {
          tailf:cli-drop-node-name;
          tailf:cli-prefix-key;
          type bgp-distribute-list-type2;
          mandatory true;
        }
      }
      // router bgp * / neighbor * dmzlink-bw
      leaf dmzlink-bw {
        description
          "Propagate the DMZ link bandwidth";
        tailf:cli-full-command;
        type empty;
      }
      // router bgp * / neighbor * ebgp-multihop
      container ebgp-multihop {
        description
          "Allow EBGP neighbors not on directly connected networks";
        tailf:cli-delete-when-empty;
        presence "Allow EBGP neighbors not on directly connected networks";
        leaf max-hop {
          tailf:cli-drop-node-name;
          type uint8 {
            range "1..255";
          }
        }
      }
      // router bgp * / neighbor * fall-over
      container fall-over {
        description
          "session fall on peer route lost";
        container bfd {
          description
            "Use BFD to detect failure";
          presence "true";
        }
      }
      // router bgp * / neighbor * filter-list *
      list filter-list {
        description
          "Establish BGP filters";
        tailf:cli-suppress-mode;
        tailf:cli-delete-when-empty;
        key "inout";
        leaf inout {
          type enumeration {
            enum "in" {
              tailf:code-name "filter_in";
            }
            enum "out" {
              tailf:code-name "filter_out";
            }
          }
        }
        leaf as-path-list {
          tailf:cli-drop-node-name;
          tailf:cli-prefix-key;
          type uint16 {
            range "1..500";
          }
          mandatory true;
        }
      }
      // router bgp * / neighbor * inherit
      container inherit {
        description
          "Inherit a template";
        leaf peer-policy {
          description
            "Inherit a peer-policy template";
          tailf:cli-full-command;
          type string;
        }
        leaf peer-session {
          description
            "Inherit a peer-session template";
          tailf:cli-full-command;
          type string;
        }
      }
      // router bgp * / neighbor * log-neighbor-changes
      container log-neighbor-changes {
        description
          "Log neighbor up/down and reset reason";
        presence "true";
        leaf disable {
          description
            "disable";
          type empty;
        }
      }
      // router bgp * / neighbor * maximum-prefix
      container maximum-prefix {
        description
          "Maximum number of prefixes accepted from this peer";
        tailf:cli-compact-syntax;
        tailf:cli-sequence-commands {
          tailf:cli-reset-all-siblings;
        }
        leaf max-prefix-no {
          tailf:cli-drop-node-name;
          tailf:cli-delete-container-on-delete;
          type uint32 {
            range "1..2147483647";
          }
        }
        leaf threshold {
          tailf:cli-drop-node-name;
          tailf:cli-break-sequence-commands;
          type uint8 {
            range "1..100";
          }
        }
        leaf restart {
          tailf:cli-full-command;
          description
            "Restart bgp connection after limit is exceeded";
          type uint16 {
            range "1..65535";
          }
        }
        leaf warning-only {
          tailf:cli-full-command;
          description
            "Only give warning message when limit is exceeded";
          type empty;
        }
      }
      // router bgp * / neighbor * next-hop-self
      leaf next-hop-self {
        tailf:cli-full-command;
        description
          "Disable the next hop calculation for this neighbor";
        type empty;
      }
      // router bgp * / neighbor * next-hop-unchanged
      leaf next-hop-unchanged {
        tailf:cli-full-command;
        description
          "Propagate the iBGP paths's next hop unchanged for this neighbor";
        type empty;
      }
      // router bgp * / neighbor * password
      container password {
        description
          "Set a password";
        tailf:cli-compact-syntax;
        leaf enctype {
          tailf:cli-drop-node-name;
          tailf:cli-incomplete-command;
          tailf:cli-reset-container;
          type uint8 {
            range "0..7";
          }
        }
        leaf text {
          tailf:cli-drop-node-name;
          tailf:cli-full-command;
          tailf:cli-multi-value;
          tailf:cli-reset-container;
          type string;
        }
      }
      // router bgp * / neighbor * prefix-list *
      list prefix-list {
        description
          "Filter updates to/from this neighbor";
        tailf:cli-suppress-mode;
        tailf:cli-delete-when-empty;
        key "inout";
        leaf inout {
          type enumeration {
            enum "in" {
              tailf:code-name "prefix_in";
            }
            enum "out" {
              tailf:code-name "prefix_out";
            }
          }
        }
        leaf prefix-list-name {
          tailf:cli-drop-node-name;
          tailf:cli-prefix-key;
          type string;
          mandatory true;
        }
      }
      // router bgp * / neighbor * path-attribute
      container path-attribute {
        description
          "BGP optional attribute filtering";
        container discard {
          description
            "Discard matching path-attribute for this neighbor";
          uses bgp-path-range-grouping;
        }
        container treat-as-withdraw {
          description
            "Treat-as-withdraw matching path-attribute for this neighbor";
          uses bgp-path-range-grouping;
        }
      }
      // router bgp * / neighbor * remove-private-as
      leaf remove-private-as {
        tailf:cli-full-command;
        description
          "Remove private AS number from outbound updates";
        type empty;
      }
      // router bgp * / neighbor * route-map *
      list route-map {
        description
          "Apply route map to neighbor";
        tailf:cli-suppress-mode;
        tailf:cli-delete-when-empty;
        key "inout";
        leaf inout {
          type enumeration {
            enum "in" {
              tailf:code-name "route_in";
            }
            enum "out" {
              tailf:code-name "route_out";
            }
          }
        }
        leaf route-map-name {
          tailf:cli-drop-node-name;
          tailf:cli-prefix-key;
          type string;
          mandatory true;
        }
      }
      // router bgp * / neighbor * route-reflector-client
      leaf route-reflector-client {
        tailf:cli-full-command;
        description
          "Configure a neighbor as Route Reflector client";
        type empty;
      }
      //router bgp * / neighbor * route-reflector-cluster-id
      leaf route-reflector-cluster-id {
        tailf:cli-full-command;
        type union {
          type uint32 {
            range "1..4294967295";
          }
          type inet:ipv4-address;
        }
      }
      // router bgp * / neighbor * send-community
      container send-community {
        description
          "Send Community attribute to this neighbor";
        tailf:cli-delete-when-empty;
        presence "true";
        leaf send-community-where {
          tailf:cli-drop-node-name;
          type enumeration {
            enum "both";
            enum "extended";
            enum "standard" {
              tailf:code-name "send_standard";
            }
          }
        }
      }
      // router bgp * / neighbor * send-label
      container send-label {
        description
          "Send NLRI + MPLS Label to this peer";
        leaf send-label-explicit {
          tailf:cli-drop-node-name;
          type enumeration {
            enum "explicit-null" {
              tailf:code-name "send_explicit_null";
            }
          }
        }
      }
      // router bgp * / neighbor * shutdown
      leaf shutdown {
        tailf:cli-full-command;
        description
          "Administratively shut down this neighbor";
        type empty;
      }
      // router bgp * / neighbor * soft-reconfiguration
      leaf soft-reconfiguration {
        tailf:cli-full-command;
        description
          "Per neighbor soft reconfiguration";
        type enumeration {
          enum "inbound";
        }
      }
      // router bgp * / neighbor slow-peer
      container slow-peer {
        description
          "Configure slow-peer";
        container detection {
          description
            "Slow-peer detection";
          presence "true";
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      // router bgp * / neighbor * timers
      container timers {
        description
          "BGP per neighbor timers";
        tailf:cli-compact-syntax;
        tailf:cli-sequence-commands {
          tailf:cli-reset-siblings;
        }
        leaf keepalive-interval {
          tailf:cli-drop-node-name;
          tailf:cli-incomplete-command;
          type uint16 {
            range "0..65535";
          }
        }
        leaf holdtime {
          tailf:cli-drop-node-name;
          type uint16 {
            range "0..65535";
          }
        }
        leaf minimum-neighbor-hold {
          tailf:cli-drop-node-name;
          type uint16 {
            range "0..65535";
          }
        }
      }
      // router bgp * / neighbor * translate-update
      container translate-update {
        description
          "Translate Update to MBGP format";
        container ipv4 {
          description
            "Address Family";
          container multicast {
            description
              "Address Family modifier";
            tailf:cli-delete-when-empty;
            presence "Address Family modifier";
            leaf unicast {
              description
                "Address Family modifier";
              type empty;
            }
          }
        }
      }
      // router bgp * / neighbor * transport
      container transport {
        description
          "Transport options";
        leaf connection-mode {
          description
            "Specify passive or active connection";
          type enumeration {
            enum "active" {
              tailf:code-name "bgp_cm_active";
            }
            enum "passive" {
              tailf:code-name "bgp_cm_passive";
            }
          }
        }
        leaf multi-session {
          description
            "Use Multi-session for transport";
          type empty;
        }
        container path-mtu-discovery {
          description
            "Use transport path MTU discovery";
          presence "true";
          leaf disable {
            description
              "disable";
            type empty;
          }
        }
      }
      // router bgp * / neighbor * ttl-security
      container ttl-security {
        description
          "BGP ttl security check";
        leaf hops {
          description
            "IP hops";
          type uint8 {
            range "1..254";
          }
        }
      }
      // router bgp * / neighbor * unsuppress-map
      leaf unsuppress-map {
        description
          "Route-map to selectively unsuppress suppressed routes";
        tailf:cli-full-command;
        type string;
      }
      // router bgp * / neighbor * update-source
      container update-source {
        description
          "Source of routing updates";
        tailf:cli-diff-dependency "/ios:native/interface";
        uses interface-grouping;
      }
      // router bgp * / neighbor * version
      leaf version {
        tailf:cli-full-command;
        description
          "Set the BGP version to match a neighbor";
        type uint16 {
          range "4";
        }
      }
      // router bgp * / neighbor * weight
      leaf weight {
        tailf:cli-full-command;
        description
          "Set default weight for routes from this neighbor";
        type uint16 {
          range "0..65535";
        }
      }
      // router bgp * / neighbor * ha-mode
      container ha-mode {
        description
          "high availability mode";
        container graceful-restart {
          description
            "graceful-restart for this peer";
          presence "true";
          leaf disable {
            description
              "disable graceful-restart";
            type empty;
          }
        }
        container sso {
          description
            "stateful-switchover support for this peer";
          presence "true";
          leaf disable {
            description
              "disable stateful-switchover";
            type empty;
          }
        }
      }
    }
    // router bgp * / network
    list network {
      description
        "Specify a network to announce via BGP";
      tailf:cli-suppress-mode;
      tailf:cli-delete-when-empty;
      tailf:cli-compact-syntax;
      tailf:cli-reset-container;
      tailf:display-when "../../../ipv4 or ../../ipv4 or ../ipv4 or ../../../ipv6 or ../../ipv6 or ../ipv6 or ../../nsap or ../nsap";
      key "number";
      leaf number {
        type inet:ipv4-address;
      }
      leaf backdoor {
        description
          "Specify a BGP backdoor route";
        tailf:cli-full-command;
        type empty;
      }
      leaf mask {
        description
          "Network mask";
        type inet:ipv4-address;
      }
      leaf route-map {
        description
          "Route-map to modify the attributes";
        type string;
      }
    }
    // router bgp * / redistribute
    container redistribute {
      description
        "Redistribute information from another routing protocol";
      tailf:display-when "../../../ipv4 or ../../ipv4 or ../ipv4  or ../../../ipv6 or ../../ipv6 or ../ipv6  or 
../../nsap or ../nsap";
      container application {
        description
          "Application";
        presence "true";
        list name {
          tailf:cli-drop-node-name;
          tailf:cli-suppress-mode;
          key "name";
          leaf name {
            description
              "WORD;;Route map name";
            type string;
          }
          uses metric-route-map-grouping;
        }
      }
      container bgp {
        description
          "Border Gateway Protocol (BGP)";
        tailf:cli-compact-syntax;
        tailf:cli-sequence-commands {
          tailf:cli-reset-all-siblings;
        }
        leaf as-no {
          tailf:cli-drop-node-name;
          type bgp-as-number-type;
        }
        uses metric-route-map-grouping;
      }
      container connected {
        description
          "Connected";
        tailf:cli-delete-when-empty;
        presence "Connected";
        uses metric-route-map-grouping;
      }
      container dvmrp {
        description
          "Redistribution of DVMRP into BGP IPv4 Multicast";
        tailf:cli-compact-syntax;
        tailf:cli-sequence-commands {
          tailf:cli-reset-siblings;
        }
        tailf:cli-delete-when-empty;
        presence "Redistribution of DVMRP into BGP IPv4 Multicast";
        uses route-map-metric-grouping;
      }
      container eigrp {
        description
          "Enhanced Interior Gateway Routing Protocol (EIGRP)";
        tailf:cli-compact-syntax;
        tailf:cli-sequence-commands {
          tailf:cli-reset-all-siblings;
        }
        leaf as-no {
          tailf:cli-drop-node-name;
          type uint16 {
            range "1..65535";
          }
        }
        uses metric-route-map-grouping;
      }
      container isis {
        description
          "ISO IS-IS";
        list isis-area {
          tailf:cli-drop-node-name;
	  tailf:cli-suppress-mode;
          key "name";
          leaf name {
            tailf:cli-disallow-value "ip|clns|level-1|level-2|level-1-2|metric|route-map";
            type string;
          }
          uses redistribute-isis-grouping;
        }
        container default {
          tailf:cli-drop-node-name;
          uses redistribute-isis-grouping;
        }
      }
      container iso-igrp {
        description
          "IGRP for OSI networks";
        list iso-igrp-area {
          tailf:cli-compact-syntax;
          tailf:cli-sequence-commands;
          tailf:cli-drop-node-name;
          key "name";
          leaf name {
            tailf:cli-disallow-value "route-map";
            type string;
          }
          uses route-map-metric-grouping;
        }
        container default {
          tailf:cli-compact-syntax;
          tailf:cli-sequence-commands;
          uses route-map-metric-grouping;
        }
      }
      container mobile {
        presence "Mobile routes";
        description
          "Mobile routes";
        uses metric-route-map-grouping;
      }
      container odr {
        presence "On Demand stub Routes";
        description
          "On Demand stub Routes";
        uses metric-route-map-grouping;
      }
      list ospf {
        description
          "Open Shortest Path First (OSPF)";
        tailf:cli-suppress-mode;
        key "id";
        leaf id {
          type uint16 {
            range "1..65535";
          }
        }
        list vrf {
          description
            "VPN Routing/Forwarding Instance";
          tailf:cli-diff-dependency "/ios:native/ip/vrf";
          tailf:cli-diff-dependency "/ios:native/vrf/definition";
          key "name";
          leaf name {
            type string;
          }
          container match;
          uses metric-route-map-grouping;
        }
        container non-vrf {
          tailf:cli-drop-node-name;
          container match {
            tailf:cli-flatten-container;
            tailf:cli-compact-syntax;
            leaf internal {
              description
                "Redistribute OSPF internal routes";
              type empty;
            }
            leaf external {
              description
                "Redistribute OSPF external routes";
              type redist-ospf-external-type;
            }
            leaf external2 {
              tailf:alt-name "external";
              description
                "Redistribute OSPF external routes";
              type redist-ospf-external-type;
            }
            leaf nssa-external {
              description
                "Redistribute OSPF NSSA external routes";
              type redist-ospf-external-type;
            }
            uses metric-route-map-grouping;
          }
          uses metric-route-map-grouping;
        }
      }
      container rip {
        presence "Routing Information Protocol (RIP)";
        description
          "Routing Information Protocol (RIP)";
        uses metric-route-map-grouping;
      }
      container static {
        presence "Static routes";
        description
          "Static routes";
        container clns {
          description
            "Redistribution of OSI dynamic routes";
          presence "true";
          uses route-map-metric-grouping;
        }
        container ip {
          presence "true";
          uses metric-route-map-grouping;
        }
        uses metric-route-map-grouping;
      }
    }
    // router bgp * / synchronization
    leaf synchronization {
      description
        "Perform IGP synchronization";
      tailf:cli-full-command;
      tailf:display-when "../../../ipv4 or ../../ipv4 or ../ipv4  or ../../../ipv6 or ../../ipv6 or ../ipv6  or ../../nsap or ../nsap";
      type empty;
    }
    // router bgp * / auto-summary
    leaf auto-summary {
      description
        "Enable automatic network number summarization";
      tailf:display-when "../../ipv4 or ../ipv4";
      tailf:cli-boolean-no;
      tailf:cli-trim-default;
      tailf:cli-full-command;
      type boolean;
    }
    // router bgp * / table-map
    container table-map {
      tailf:cli-sequence-commands;
      tailf:cli-compact-syntax;
      presence "true";
      description
        "Map external entry attributes into routing table";
      tailf:display-when "../../../ipv4 or ../../ipv4 or ../ipv4  or ../../../ipv6 or ../../ipv6 or ../ipv6 ";
      leaf name {
        description
          "WORD;;route-map name";
        type string;
      }
      leaf filter {
        type empty;
      }
    }
    // router bgp * / snmp
    container snmp {
      description
        "Modify snmp parameters";
      presence "true";
      container context {
        description
          "Configure a SNMP context";
        list context_word {
          tailf:cli-drop-node-name;
          tailf:cli-suppress-mode;
          key "context_word";
          leaf context_word {
            description
              "Context Name";
            type string;
          }
        }
      }
    }
  }

  // neighbor path-attribute grouping 
  grouping bgp-path-range-grouping {
    container attibute_type {
      leaf type {
        description
          "path attribute type";
        type uint8 {
          range "1..255";
        }
      }
      leaf in {
        description
          "Perform inbound path-attribute filtering";
        type empty;
      }
    }
    container range {
      leaf start_value {
        description
          "path attribute range start value";
        type uint8 {
          range "1..255";
        }
      }
      leaf end_value {
        description
          "path attribute range end value";
        type uint8 {
          range "1..255";
        }
      }
      leaf in {
        description
          "Perform inbound path-attribute filtering";
        type empty;
      }
    }
  }

  grouping ospfv3-grouping {
    container authentication {
      description
        "Authentication parameters";
      leaf mode {
        description
          "Authentication operation mode";
        type enumeration {
          enum "deployment";
          enum "strict";
        }
      }
    }
    container graceful-restart {
      description
        "Graceful-restart options";
      presence "true";
      container helper {
        description
          "helper support";
        presence "true";
        leaf disable {
          description
            "disable helper support";
          type empty;
        }
        leaf strict-lsa-checking {
          description
            "enable helper strict LSA checking";
          type empty;
        }
      }
      leaf restart-interval {
        description
          "Graceful restart interval";
        type uint16;
      }
    }
    container manet {
      description
        "Specify MANET OSPF parameters";
      container cache {
        description
          "Specify MANET cache sizes";
        leaf acknowledgement {
          description
            "Specify MANET acknowledgement cache size";
          type uint64 {
            range "0..4294967295";
          }
        }
        leaf update {
          description
            "Specify MANET LSA cache size";
          type uint64 {
            range "0..4294967295";
          }
        }
      }
      leaf hello {
        description
          "Unicast Hellos rather than multicast";
        type enumeration {
          enum "unicast";
        }
      }
      container peering {
        description
          "MANET OSPF Smart Peering";
        container selective {
          description
            "Enable selective peering";
          leaf disable {
            description
              "Disable selective peering";
            tailf:cli-full-command;
            type empty;
          }
          leaf per-interface {
            description
              "Select peers per interface rather than per node";
            type empty;
          }
          leaf redundancy {
            description
              "Redundant paths";
            type uint8;
          }
        }
      }
      leaf willingness {
        description
          "Specify Relay willingness value";
        type uint8 {
          range "0..255";
        }
      }
    }
  }

  grouping ospfv3-address-family-grouping {
    container authentication {
      description
        "Authentication parameters";
      leaf mode {
        description
          "Authentication operation mode";
        type enumeration {
          enum "deployment";
          enum "normal";
          enum "strict";
        }
      }
    }
    container graceful-restart {
      description
        "Graceful-restart options";
      presence "true";
      leaf disable {
        description
          "Graceful restart disable";
        type empty;
      }
      container helper {
        description
          "helper support";
        presence "true";
        leaf disable {
          description
            "disable helper support";
          type empty;
        }
        leaf strict-lsa-checking {
          description
            "enable helper strict LSA checking";
          type empty;
        }
      }
      leaf restart-interval {
        description
          "Graceful restart interval";
        type uint16;
      }
    }
    container manet {
      description
        "Specify MANET OSPF parameters";
      container cache {
        description
          "Specify MANET cache sizes";
        leaf acknowledgement {
          description
            "Specify MANET acknowledgement cache size";
          type uint64 {
            range "0..4294967295";
          }
        }
        leaf update {
          description
            "Specify MANET LSA cache size";
          type uint64 {
            range "0..4294967295";
          }
        }
      }
      leaf hello {
        description
          "Unicast Hellos rather than multicast";
        type enumeration {
          enum "unicast";
          enum "multicast";
        }
      }
      container peering {
        description
          "MANET OSPF Smart Peering";
        container selective {
          description
            "Enable selective peering";
          leaf disable {
            description
              "Disable selective peering";
            tailf:cli-full-command;
            type empty;
          }
          leaf per-interface {
            description
              "Select peers per interface rather than per node";
            type empty;
          }
          leaf redundancy {
            description
              "Redundant paths";
            type uint8;
          }
        }
      }
      leaf willingness {
        description
          "Specify Relay willingness value";
        type uint8 {
          range "0..255";
        }
      }
    }
  }

  grouping ospf-ospfv3-common-address-family-grouping {
    container capability {
      description
        "Enable specific OSPF feature";
      leaf capability-type {
        tailf:cli-drop-node-name;
        type enumeration {
          enum "lls";
          enum "opaque";
          enum "transit";
          enum "vrf-lite";
        }
      }
    }
    container compatible {
      description
        "OSPF compatibility list";
      leaf rfc1583 {
        description
          "Compatible with RFC 1583";
        type empty;
      }
      leaf rfc1587 {
        description
          "Compatible with RFC 1587";
        type empty;
      }
      leaf rfc5243 {
        description
          "Compatible with RFC 5243";
        type empty;
      }
    }
    container default-information {
      description
        "Control distribution of default information";
      container originate {
        description
          "Distribute a default route";
        presence "Distribute a default route";
        leaf always {
          description
            "Always advertise default route";
          type empty;
        }
        leaf metric {
          description
            "OSPF default metric";
          type uint32 {
            range "0 .. 16777214";
          }
        }
        leaf metric-type {
          description
            "OSPF metric type for default routes";
          type ospf-metric-type;
        }
        leaf route-map {
          description
            "Route map reference";
          type string;
        }
      }
    }
    leaf default-metric {
      description
        "Set metric of redistributed routes";
      tailf:cli-full-command;
      type uint32 {
        range "1 .. 16777214";
      }
    }
    container discard-route {
      description
        "Enable or disable discard-route installation";
      presence "Enable or disable discard-route installation";
      tailf:cli-compact-syntax;
      leaf external {
        description
          "Discard route for redistributed summarised routes";
        type empty;
      }
      leaf internal {
        description
          "Discard route for summarised internal routes";
        type empty;
      }
      leaf metric {
        tailf:cli-drop-node-name;
        type uint32 {
          range "1 .. 255";
        }
      }
    }
    container distance {
      tailf:cli-compact-syntax;
      description
        "Define an administrative distance";
      container ospf-distance {
        tailf:cli-compact-syntax;
        tailf:cli-drop-node-name;
        leaf distance {
          tailf:cli-drop-node-name;
          type uint32 {
            range "1 .. 255";
          }
        }
        tailf:cli-sequence-commands;
        leaf ip {
          tailf:cli-drop-node-name;
          tailf:cli-incomplete-command;
          type inet:ipv4-address;
        }
        leaf wildcard {
          tailf:cli-drop-node-name;
          type inet:ipv4-address;
        }
        leaf acl-name {
          tailf:cli-drop-node-name;
          type access-list-standard-id-type;
          tailf:cli-no-value-on-delete;
        }
      }
      container ospf {
        description
          "OSPF routes Administrative distance";
        leaf external {
          description
            "External routes";
          type uint32 {
            range "1 .. 255";
          }
          tailf:cli-suppress-no;
          tailf:cli-no-value-on-delete;
          tailf:cli-no-name-on-delete;
        }
        leaf inter-area {
          description
            "Inter-area routes";
          type uint32 {
            range "1 .. 255";
          }
          tailf:cli-suppress-no;
          tailf:cli-no-name-on-delete;
          tailf:cli-no-value-on-delete;
        }
        leaf intra-area {
          description
            "Intra-area routes";
          type uint32 {
            range "1 .. 255";
          }
          tailf:cli-suppress-no;
          tailf:cli-no-name-on-delete;
          tailf:cli-no-value-on-delete;
        }
      }
    }
    leaf maximum-paths {
      description
        "Forward packets over multiple paths";
      tailf:cli-full-command;
      type uint32 {
        range "1 .. 32";
      }
    }
    container redistribute {
      description
        "Redistribute information from another routing protocol";
      uses ospf-redistribute-top-grouping;
      container maximum-prefix {
        description
          "Maximum number of prefixes redistributed to protocol";
        tailf:cli-sequence-commands;
        tailf:cli-compact-syntax;
        leaf number {
          tailf:cli-drop-node-name;
          type uint32 {
            range "1 .. 4294967295";
          }
        }
        container threshold-warning-only-container {
          tailf:cli-compact-syntax;
          tailf:cli-drop-node-name;
          leaf threshold {
            tailf:cli-drop-node-name;
            type uint32 {
              range "1 .. 100";
            }
          }
          leaf warning-only {
            description
              "Only give warning message when limit is exceeded";
            tailf:cli-full-command;
            type empty;
          }
        }
      }
      container vrf {
        description
          "Specify a source VRF";
        list non-global-vrf {
          tailf:cli-drop-node-name;
          tailf:cli-suppress-mode;
          tailf:cli-diff-dependency "/ios:native/ip/vrf";
          tailf:cli-diff-dependency "/ios:native/vrf/definition";
          key "name";
          leaf name {
            tailf:cli-incomplete-command;
            type string;
          }
          uses ospf-redistribute-top-grouping;
        }
        container global {
          description
            "global VRF";
          tailf:cli-compact-syntax;
          uses ospf-redistribute-top-grouping;
        }
      }
    }
  }

  grouping ospf-authentication-key-grouping {
    container authentication-key {
      description
        "Set authentication key";
      tailf:cli-sequence-commands;
      tailf:cli-compact-syntax;
      leaf auth-type {
        tailf:cli-drop-node-name;
        type uint8 {
          range "0 .. 7";
        }
      }
      leaf auth-key {
        tailf:cli-drop-node-name;
        tailf:cli-full-command;
        tailf:cli-multi-value;
        type string;
      }
    }
  }

  grouping ospf-area-virtual-link-grouping {
    uses ospf-authentication-key-grouping;
    list message-digest-key {
      description
        "Set message digest key";
      tailf:cli-suppress-mode;
      tailf:cli-delete-when-empty;
      tailf:cli-incomplete-command;
      key "id";
      leaf id {
        tailf:cli-suppress-range;
        type uint8 {
          range "1 .. 255";
        }
      }
      container md5 {
        description
          "Use MD5 algorithm";
        tailf:cli-sequence-commands;
	tailf:cli-compact-syntax;
        leaf auth-type {
          tailf:cli-drop-node-name;
          tailf:cli-optional-in-sequence;
          type uint8 {
            range "0 .. 7";
          }
        }
        leaf auth-key {
          tailf:cli-drop-node-name;
          type string {
            length "1 .. 16";
          }
        }
      }
    }
  }

  grouping ospfv3-af-ipv6-summary-prefix-grouping {
    list summary-prefix {
      description
        "Configure IPv6 summary prefix";
      tailf:cli-suppress-mode;
      tailf:cli-delete-when-empty;
      key "prefix";
      leaf prefix {
        type inet:ipv6-prefix;
      }
      choice tag-no-advertise-choice {
        leaf nssa-only {
          description
            "Limit summary to NSSA areas";
          type empty;
        }
        leaf tag {
          description
            "Set tag";
          tailf:cli-full-command;
          type uint32 {
            range "0 .. 4294967295";
          }
        }
        leaf not-advertise {
          description
            "Do not advertise when translating OSPF type-7 LSA";
          type empty;
          tailf:cli-full-command;
        }
      }
    }
  }

  grouping ospf-ospfv3-common-grouping {
    list area {
      description
        "OSPF area parameters";
      tailf:cli-suppress-mode;
      tailf:cli-delete-when-empty;
      tailf:cli-incomplete-command;
      key "id";
      leaf id {
        tailf:cli-suppress-range;
        type ospf-area-type;
      }
      container authentication {
        description
          "Enable authentication";
        presence "true";
        leaf message-digest {
          description
            "Use message-digest authentication";
          type empty;
        }
      }
      container capability {
        description
          "Enable area specific capability";
        leaf default-exclusion {
          description
            "Enable exclusion of links from base topology";
          type empty;
        }
      }
      leaf default-cost {
        description
          "Set the summary default-cost of a NSSA/stub area";
        tailf:cli-full-command;
        tailf:cli-no-value-on-delete;
        type uint32 {
          range "0 .. 16777215";
        }
      }
      list filter-list {
        description
          "Filter networks between OSPF areas";
        tailf:cli-suppress-mode;
        tailf:cli-delete-when-empty;
        tailf:cli-compact-syntax;
        key "in-out";
        leaf in-out {
          type enumeration {
            enum "in";
            enum "out";
          }
        }
        leaf prefix {
          tailf:cli-prefix-key;
          mandatory true;
          description
            "Filter prefixes between OSPF areas";
          type string;
        }
      }
      container nssa {
        description
          "Specify a NSSA area";
        presence "Specify a NSSA area";
        container default-information-originate {
          tailf:cli-flatten-container;
          description
            "Originate Type 7 default into NSSA area";
          presence "Originate Type 7 default into NSSA area";
          leaf metric {
            description
              "OSPF default metric";
            type int32 {
              range "0 .. 16777214";
            }
            tailf:cli-no-value-on-delete;
            tailf:cli-no-name-on-delete;
            tailf:cli-suppress-no;
          }
          leaf metric-type {
            description
              "OSPF metric type for default routes";
            type ospf-metric-type;
          }
          leaf no-ext-capability {
            description
              "Do not send domain specific capabilities into NSSA";
            type empty;
          }
          leaf no-redistribution {
            description
              "No redistribution into this NSSA area";
            type empty;
          }
          leaf no-summary {
            description
              "Do not send summary LSA into NSSA";
            type empty;
          }
          leaf nssa-only {
            description
              "Limit default advertisement to this NSSA area";
            type empty;
          }
          container translate {
            description
              "Translate LSA";
            container type7 {
              description
                "From Type 7 to Type 5";
              leaf always {
                description
                  "Always translate LSAs on this ABR";
                type empty;
              }
              leaf suppress-fa {
                description
                  "Suppress forwarding address in translated LSAs";
                type empty;
              }
            }
          }
        }
        leaf no-ext-capability {
          description
            "Do not send domain specific capabilities into NSSA";
          type empty;
        }
        leaf no-redistribution {
          description
            "No redistribution into this NSSA area";
          type empty;
        }
        leaf no-summary {
          description
            "Do not send summary LSA into NSSA";
          type empty;
        }
        leaf nssa-only {
          description
            "Limit default advertisement to this NSSA area";
          type empty;
        }
        container translate {
          description
            "Translate LSA";
          container type7 {
            description
              "From Type 7 to Type 5";
            leaf always {
              description
                "Always translate LSAs on this ABR";
              type empty;
            }
            leaf suppress-fa {
              description
                "Suppress forwarding address in translated LSAs";
              type empty;
            }
          }
        }
      }
      list range {
        description
          "Summarize routes matching address/mask (border routers only)";
        tailf:cli-suppress-mode;
        tailf:cli-delete-when-empty;
        key "ip mask";
        leaf ip {
          type inet:ipv4-address;
        }
        leaf mask {
          type inet:ipv4-address;
        }
        choice advertise-choice {
          leaf advertise {
            description
              "Advertise this range (default)";
            type empty;
          }
          leaf not-advertise {
            description
              "DoNotAdvertise this range";
            type empty;
          }
        }
        leaf cost {
          description
            "User specified metric for this range";
          tailf:cli-full-command;
          type uint32 {
            range "0 .. 16777215";
          }
        }
      }
      list sham-link {
        description
          "Define a sham link and its parameters";
        tailf:cli-suppress-mode;
        tailf:cli-delete-when-empty;
        key "source dest";
        leaf source {
          type inet:ip-address;
        }
        leaf dest {
          type inet:ip-address;
        }
        leaf cost {
          description
            "Associate a cost with the sham-link";
          type uint16 {
            range "0 .. 65535";
          }
        }
        container ttl-security {
          description
            "TTL security check";
          tailf:cli-flatten-container;
          leaf hops {
            description
              "IP hops";
            type uint8;
          }
        }
      }
      container stub {
        description
          "Specify a stub area";
        presence "Specify a stub area";
        leaf no-ext-capability {
          description
            "Do not send domain specific capabilities into stub area";
          type empty;
        }
        leaf no-summary {
          description
            "Do not send summary LSA into stub area";
          tailf:cli-full-command;
          type empty;
        }
      }
      list virtual-link {
        description
          "Define a virtual link and its parameters";
        tailf:cli-suppress-mode;
        tailf:cli-delete-when-empty;
        key "id";
        leaf id {
          type inet:ip-address;
        }
        container authentication {
          description
            "Set authentication type";
          tailf:cli-flatten-container;
          uses ospf-area-virtual-link-grouping;
          container key-chain {
            description
              "Use a key-chain for cryptographic authentication keys";
            tailf:cli-compact-syntax;
            leaf name {
              tailf:cli-drop-node-name;
              type string;
            }
            uses ospf-area-virtual-link-grouping;
          }
          container message-digest {
            description
              "Message-digest authentication";
            uses ospf-area-virtual-link-grouping;
          }
          leaf null {
            description
              "No authentication";
            type empty;
          }
        }
        container hello-interval {
          description
            "Hello packet interval";
          tailf:cli-compact-syntax;
          leaf hello-interval-value {
            tailf:cli-no-value-on-delete;
            tailf:cli-drop-node-name;
            type int32 {
              range "1 .. 8192";
            }
          }
        }
        container dead-interval {
          description
            "Dead router detection time";
          tailf:cli-compact-syntax;
          leaf dead-interval-value {
            tailf:cli-no-value-on-delete;
            tailf:cli-drop-node-name;
            type uint16 {
              range "1 .. 8192";
            }
          }
        }
        container retransmit-interval {
          description
            "LSA retransmit interval";
          tailf:cli-compact-syntax;
          leaf retransmit-interval-value {
            tailf:cli-drop-node-name;
            type uint16 {
              range "1 .. 8192";
            }
            tailf:cli-no-value-on-delete;
          }
        }
        container transmit-delay {
          description
            "LSA transmission delay";
          tailf:cli-compact-syntax;
          leaf transmit-delay-value {
            tailf:cli-drop-node-name;
            type uint16 {
              range "1 .. 8192";
            }
            tailf:cli-no-value-on-delete;
          }
        }
        container topology {
          description
            "Disable virtual link on topology";
          tailf:cli-compact-syntax;
          leaf disable {
            description
              "Disable virtual link";
            type empty;
          }
        }
        container ttl-security {
          description
            "TTL security check";
          tailf:cli-compact-syntax;
          leaf hops {
            description
              "IP hops";
            type uint8 {
              range "1..254";
            }
          }
        }
        uses ospf-area-virtual-link-grouping;
      }
    }
    container auto-cost {
      description
        "Calculate OSPF interface cost according to bandwidth";
      presence "Calculate OSPF interface cost according to bandwidth";
      leaf reference-bandwidth {
        description
          "Use reference bandwidth method to assign OSPF cost";
        type uint32 {
          range "1 .. 4294967";
        }
      }
    }
    container event-log {
      description
        "OSPF Event Logging";
      presence "true";
      leaf one-shot {
        description
          "Disable Logging When Log Buffer Becomes Full";
        type empty;
      }
      leaf pause {
        description
          "Pause Event Logging";
        type empty;
      }
      leaf size {
        description
          "Maximum Number of Events Stored in the Event Log";
        type uint32 {
          range "1..65534";
        }
      }
    }
    container bfd {
      description
        "BFD configuration commands";
      leaf all-interfaces {
        description
          "Enable BFD on all interfaces";
        type empty;
      }
    }
    container interface-id {
      description
        "Source of the interface ID";
      leaf snmp-if-index {
        description
          "SNMP MIB ifIndex";
        type empty;
      }
    }
    container log-adjacency-changes {
      description
        "Log changes in adjacency state";
      presence "true";
      leaf detail {
        description
          "Log all state changes";
        type empty;
      }
    }
    container max-lsa {
      description
        "maximum number of LSAs OSPF process will receive";
      tailf:cli-sequence-commands;
      tailf:cli-compact-syntax;
      leaf number {
        tailf:cli-drop-node-name;
        type uint32 {
          range "1 .. 4294967294";
        }
      }
      leaf threshold-value {
        tailf:cli-drop-node-name;
        tailf:cli-break-sequence-commands;
        type uint32 {
          range "1 .. 100";
        }
      }
      leaf ignore-count {
        description
          "maximum number of times adjacencies can be suppressed";
        type uint32 {
          range "1 .. 65534";
        }
      }
      leaf ignore-time {
        description
          "time during which all adjacencies are suppressed";
        type uint32 {
          range "1 .. 17895";
        }
      }
      leaf reset-time {
        description
          "time after which ignore-count is reset to zero";
        type uint32 {
          range "2 .. 35791";
        }
      }
      leaf warning-only {
        description
          "Only give warning message when limit is exceeded";
        tailf:cli-full-command;
        type empty;
      }
    }
    container max-metric {
      description
        "Set maximum metric";
      container router-lsa {
        description
          "Maximum metric in self-originated router-LSAs";
        presence "Maximum metric in self-originated router-LSAs";
        tailf:cli-compact-syntax;
        container external-lsa {
          presence "Override external-lsa metric with max-metric value";
          tailf:cli-flatten-container;
          description
            "Override external-lsa metric with max-metric value";
          leaf metric {
            tailf:cli-drop-node-name;
            type uint32 {
              range "1 .. 16777215";
            }
          }
        }
        leaf include-stub {
          description
            "Set maximum metric for stub links in router-LSAs";
          type empty;
        }
        container on-startup {
          description
            "Set maximum metric temporarily after reboot";
          presence "Set maximum metric temporarily after reboot";
          tailf:cli-flatten-container;
          choice time-wait-for-bgp-choice {
            leaf time {
              tailf:cli-drop-node-name;
              type uint32 {
                range "5 .. 86400";
              }
            }
            leaf wait-for-bgp {
              description
                "Let BGP decide when to originate router-LSA with normal metric";
              type empty;
            }
          }
        }
        container summary-lsa {
          description
            "Override summary-lsa metric with max-metric value";
          presence "Override summary-lsa metric with max-metric value";
          tailf:cli-flatten-container;
          leaf metric {
            tailf:cli-drop-node-name;
            type uint32 {
              range "1 .. 16777215";
            }
          }
        }
      }
    }
    uses passive-interface-grouping;
    container queue-depth {
      description
        "OSPF Hello/Router process queue depth";
      container hello {
        description
          "OSPF Hello process queue depth";
        uses queue-depth-grouping;
      }
      container update {
        description
          "OSPF Router process queue depth";
        uses queue-depth-grouping;
      }
    }
    container timers {
      description
        "Adjust routing timers";
      container lsa {
        description
          "OSPF LSA timers";
        leaf arrival {
          description
            "OSPF LSA arrival timer";
          type uint32 {
            range "0 .. 600000";
          }
        }
      }
      container pacing {
        description
          "OSPF pacing timers";
        leaf flood {
          description
            "OSPF flood pacing timer";
          tailf:cli-full-command;
          type uint32 {
            range "5 .. 100";
          }
        }
        leaf lsa-group {
          description
            "OSPF LSA group pacing timer";
          tailf:cli-full-command;
          type uint32 {
            range "10 .. 1800";
          }
        }
        leaf retransmission {
          description
            "OSPF retransmission pacing timer";
          tailf:cli-full-command;
          type uint32 {
            range "5 .. 200";
          }
        }
      }
      container throttle {
        description
          "OSPF throttle timers";
        container lsa {
          description
            "OSPF LSA throttle timers";
          container all {
            description
              "For all type of OSPF LSAs";
            tailf:cli-drop-node-name;
            tailf:cli-sequence-commands;
            tailf:cli-compact-syntax;
            leaf delay {
              tailf:cli-drop-node-name;
              tailf:cli-incomplete-command;
              type uint32 {
                range "0 .. 600000";
              }
            }
            leaf min-delay {
              tailf:cli-drop-node-name;
              tailf:cli-incomplete-command;
              type uint32 {
                range "0 .. 600000";
              }
            }
            leaf max-delay {
              tailf:cli-drop-node-name;
              type uint32 {
                range "0 .. 600000";
              }
            }
          }
        }
        container spf {
          description
            "OSPF SPF throttle timers";
          tailf:cli-sequence-commands;
          tailf:cli-compact-syntax;
          leaf delay {
            tailf:cli-drop-node-name;
            tailf:cli-incomplete-command;
            type uint32 {
              range "0 .. 600000";
            }
          }
          leaf min-delay {
            tailf:cli-drop-node-name;
            tailf:cli-incomplete-command;
            type uint32 {
              range "0 .. 600000";
            }
          }
          leaf max-delay {
            tailf:cli-drop-node-name;
            type uint32 {
              range "0 .. 600000";
            }
          }
        }
      }
    }
    leaf router-id {
      tailf:cli-full-command;
      description
        "Override configured router identifier (peers will reset)";
      type inet:ipv4-address;
    }
    leaf nsr {
      tailf:cli-full-command;
      description
        "Enable non-stop routing";
      type empty;
    }
    container traffic-share {
      description
        "How to compute traffic share over alternate paths";
      tailf:cli-sequence-commands;
      tailf:cli-compact-syntax;
      leaf min {
        description
          "All traffic shared among min metric paths";
        type empty;
      }
      leaf across-interfaces {
        description
          "Use different interfaces for equal-cost paths";
        type empty;
      }
    }
    container ttl-security {
      description
        "TTL security check";
      tailf:cli-sequence-commands;
      tailf:cli-compact-syntax;
      leaf all-interfaces {
        description
          "Enable TTL Security on all interfaces";
        type empty;
      }
      leaf hops {
        description
          "IP hops";
        tailf:cli-break-sequence-commands;
        type uint8 {
          range "1..254";
        }
      }
    }
  }

  //ospf ast-reroute per-prefix tie-break index
  grouping tie-break-index {
    leaf required {
      description
        "Mandatory repair path attribute";
      tailf:cli-incomplete-command;
      type empty;
    }
    leaf index {
      description
        "Tiebreak attribute priority";
      tailf:cli-full-command;
      type uint8 {
        range "1..255";
      }
    }
  }

  grouping queue-depth-grouping {
    leaf options {
      tailf:cli-drop-node-name;
      tailf:cli-full-command;
      tailf:cli-trim-default;
      type union {
        type uint32 {
          range "1 .. 2147483647";
        }
        type enumeration {
          enum "unlimited";
        }
      }
    }
  }
  grouping router-eigrp-redistribute-grouping {
    container metric {
      description
        "Metric for redistributed routes";
      tailf:cli-flatten-container;
      tailf:cli-compact-syntax;
      tailf:cli-sequence-commands;
      leaf bandwith {
        tailf:cli-drop-node-name;
        description
          "Bandwidth metric in Kbits per second";
        type uint32 {
          range "1..4294967295";
        }
      }
      leaf delay {
        tailf:cli-drop-node-name;
        description
          "EIGRP delay metric, in 10 microsecond units";
        type uint32 {
          range "0..4294967295";
        }
      }
      leaf reliability {
        tailf:cli-drop-node-name;
        description
          "EIGRP reliability metric where 255 is 100% reliable";
        type uint8 {
          range "0..255";
        }
      }
      leaf Effective {
        tailf:cli-drop-node-name;
        description
          "EIGRP Effective bandwidth metric (Loading) where 255 is 100% loaded";
        type uint8 {
          range "1..255";
        }
      }
      leaf mtu {
        tailf:cli-drop-node-name;
        description
          "EIGRP MTU of the path";
        type uint16 {
          range "1..65535";
        }
      }
    }
    leaf route-map {
      description
        "Route map reference";
      type string;
    }            
  }  
  grouping ospf-redistribute-match-grouping {
    leaf metric {
      description
        "Metric for redistributed routes";
      type uint32;
    }
    leaf metric-type {
      description
        "OSPF/IS-IS exterior metric type for redistributed routes";
      type enumeration {
        enum "1" {
          tailf:code-name "metric_type_1";
        }
        enum "2" {
          tailf:code-name "metric_type_2";
        }
      }
    }
    leaf nssa-only {
      description
        "Limit redistributed routes to NSSA areas";
      type empty;
    }
    leaf subnets {
      description
        "Consider subnets for redistribution into OSPF";
      type empty;
    }
    leaf route-map {
      description
        "Route map reference";
      type string;
    }
    leaf tag {
      description
        "Set tag for routes redistributed into OSPF";
      type uint32 {
        range "0 .. 4294967295";
      }
    }
  }

  grouping ospf-redistribute-top-match-grouping {
    container match {
      tailf:cli-compact-syntax;
      tailf:cli-flatten-container;
      description
        "Redistribution of OSPF routes";
      container internal {
        presence "Redistribute OSPF internal routes";
        description
          "Redistribute OSPF internal routes";
        tailf:cli-compact-syntax;
        tailf:cli-flatten-container;
        uses ospf-redistribute-match-grouping;
      }
      container external {
        description
          "Redistribute OSPF external routes";
        presence "Redistribute OSPF external routes";
        tailf:cli-compact-syntax;
        tailf:cli-flatten-container;
        leaf external-routes {
          tailf:cli-drop-node-name;
          type redist-ospf-external-type;
        }
        uses ospf-redistribute-match-grouping;
      }
      container nssa-external {
        description
          "Redistribute OSPF NSSA external routes";
        presence "Redistribute OSPF NSSA external routes";
        tailf:cli-compact-syntax;
        tailf:cli-flatten-container;
        leaf nssa-external-routes {
          tailf:cli-drop-node-name;
          type redist-ospf-external-type;
        }
        uses ospf-redistribute-match-grouping;
      }
    }
  }

  grouping ospf-iso-igrp-redistribute-grouping {
    leaf metric {
      description
        "Metric for redistributed routes";
      type uint32;
    }
    leaf metric-type {
      description
        "OSPF/IS-IS exterior metric type for redistributed routes";
      type enumeration {
        enum "1" {
          tailf:code-name "metric_type_1";
        }
        enum "2" {
          tailf:code-name "metric_type_2";
        }
      }
    }
    leaf tag {
      description
        "Set tag for routes redistributed into OSPF";
      type uint32 {
        range "0 .. 4294967295";
      }
    }
    leaf subnets {
      description
        "Consider subnets for redistribution into OSPF";
      type empty;
    }
  }

  grouping ospf-redistribute-grouping {
    container redist-options {
      tailf:cli-drop-node-name;
      tailf:cli-compact-syntax;
      uses ospf-iso-igrp-redistribute-grouping;
      leaf route-map {
        description
          "Route map reference";
        type string;
      }
      leaf nssa-only {
        description
          "Limit redistributed routes to NSSA areas";
        type empty;
      }
    }
  }

  grouping ospf-redistribute-top-grouping {
    list application {
      description
        "Application";
      tailf:cli-suppress-mode;
      key "name";
      leaf name {
        type string;
      }
      uses ospf-redistribute-grouping;
    }
    list bgp {
      description
        "Border Gateway Protocol (BGP)";
      tailf:cli-suppress-mode;
      key "as-number";
      uses ospf-redistribute-bgp-grouping;
    }
    container connected {
      description
        "Connected";
      presence "Connected";
      uses ospf-redistribute-grouping;
    }
    list eigrp {
      description
        "Enhanced Interior Gateway Routing Protocol (EIGRP)";
      tailf:cli-suppress-mode;
      key "as-number";
      uses ospf-redistribute-bgp-grouping;
    }
    container isis {
      presence "ISO IS-IS";
      description
        "ISO IS-IS";
      choice isis-level-routes-isis-area-choice {
        leaf isis-level-routes {
          tailf:cli-drop-node-name;
          type enumeration {
            enum "level-1";
            enum "level-2";
            enum "level-1-2";
          }
        }
        list isis-area {
          tailf:cli-suppress-mode;
          tailf:cli-delete-when-empty;
          tailf:cli-drop-node-name;
          key "name";
          leaf name {
            tailf:cli-disallow-value "level-1|level-2|level-1-2|metric|metric-type|route-map|subnets|tag";
            type string;
          }
          leaf isis-level-routes {
            tailf:cli-drop-node-name;
            type enumeration {
              enum "level-1";
              enum "level-2";
              enum "level-1-2";
            }
          }
          uses ospf-redistribute-grouping;
        }
      }
      uses ospf-redistribute-grouping;
    }
    container iso-igrp {
      description
        "IGRP for OSI networks";
      presence "IGRP for OSI networks";
      tailf:cli-sequence-commands;
      tailf:cli-compact-syntax;
      choice area-tag-route-map-choice {
        container area-tag-route-map-container {
          tailf:cli-drop-node-name;
          tailf:cli-flatten-container;
          tailf:cli-sequence-commands;
	  tailf:cli-compact-syntax;
          leaf area-tag {
            tailf:cli-drop-node-name;
            tailf:cli-disallow-value "route-map";
            type string;
          }
          leaf route-map {
            description
              "Route map reference";
            type string;
          }
        }
        leaf route-map {
          description
            "Route map reference";
          type string;
        }
      }
      container iso-igrp-container {
        tailf:cli-drop-node-name;
        tailf:cli-compact-syntax;
        uses ospf-iso-igrp-redistribute-grouping;
      }
    }
    container lisp {
      description
        "Locator ID Separation Protocol (LISP)";
      uses ospf-redistribute-grouping;
    }
    container mobile {
      description
        "Mobile routes";
      presence "Mobile routes";
      uses ospf-redistribute-grouping;
    }
    container odr {
      description
        "On Demand stub Routes";
      presence "On Demand stub Routes";
      uses ospf-redistribute-grouping;
    }
    list ospf {
      description
        "Open Shortest Path First (OSPF)";
      tailf:cli-suppress-mode;
      tailf:cli-delete-when-empty;
      key "id";
      leaf id {
        tailf:cli-suppress-range;
        type uint32 {
          range "1 .. 65535";
        }
      }
      uses ospf-redistribute-top-match-grouping;
      uses ospf-redistribute-match-grouping;
      leaf vrf {
        description
          "VPN Routing/Forwarding Instance";
        tailf:cli-diff-dependency "/ios:native/ip/vrf";
        tailf:cli-diff-dependency "/ios:native/vrf/definition";
        type string;
      }
    }
    list ospfv3 {
      description
        "OSPFv3";
      tailf:cli-suppress-mode;
      tailf:cli-delete-when-empty;
      key "id";
      leaf id {
        tailf:cli-suppress-range;
        type uint32 {
          range "1 .. 65535";
        }
      }
      uses ospf-redistribute-top-match-grouping;
      uses ospf-redistribute-match-grouping;
    }
    list rip {
      description
        "Routing Information Protocol (RIP)";
      tailf:cli-suppress-mode;
      tailf:cli-delete-when-empty;
      key "id";
      leaf id {
        description
          "User selected string identifying this rip process";
        type string;
      }
      uses ospf-redistribute-grouping;
    }
    container static {
      description
        "Static routes";
      presence "Static routes";
      uses ospf-redistribute-grouping;
    }
  }

  grouping ospf-redistribute-bgp-grouping {
    leaf as-number {
      type bgp-as-number-type;
    }
    uses ospf-redistribute-grouping;
  }

  grouping router-snmp-grouping {
    container snmp {
      description
        "Modify snmp parameters";
      list context {
        description
          "Configure a SNMP context";
        tailf:cli-suppress-mode;
        key "name";
        leaf name {
          description
            "Context Name";
          tailf:cli-drop-node-name;
          type string;
        }
        container community {
          description
            "Configure a SNMP v2c Community string and access privs";
          tailf:cli-compact-syntax;
          tailf:cli-sequence-commands;
          leaf community-string {
            tailf:cli-drop-node-name;
            type string;
          }
          container access {
            tailf:cli-drop-node-name;
            tailf:cli-flatten-container;
            leaf standard-acl {
              tailf:cli-drop-node-name;
              tailf:cli-full-command;
              type uint32 {
                range "1..99";
              }
            }
            leaf expanded-acl {
              tailf:cli-drop-node-name;
              tailf:cli-full-command;
              type uint32 {
                range "1300..1999";
              }
            }
            leaf acl-name {
              tailf:cli-drop-node-name;
              tailf:cli-full-command;
              type string;
            }
            leaf ipv6 {
              description
                "Specify IPv6 Named Access-List";
              tailf:cli-full-command;
              type string;
            }
            leaf ro {
              description
                "Read-only access with this community string";
              type empty;
            }
            leaf rw {
              description
                "Read-write access with this community string";
              type empty;
            }
          }
        }
        container user {
          description
            "Configure a SNMP v3 user";
          tailf:cli-compact-syntax;
          tailf:cli-sequence-commands;
          leaf name {
            tailf:cli-drop-node-name;
            type string;
          }
          container permisssion {
            tailf:cli-drop-node-name;
            tailf:cli-flatten-container;
            container access {
              description
                "specify an access-list associated with this group";
              tailf:cli-flatten-container;
              leaf standard-acl {
                tailf:cli-drop-node-name;
                tailf:cli-full-command;
                type uint32;
              }
              leaf acl-name {
                tailf:cli-drop-node-name;
                tailf:cli-full-command;
                type string;
              }
              leaf ipv6 {
                tailf:cli-full-command;
                type string;
              }
            }
            container auth {
              description
                "authentication parameters for the user";
              tailf:cli-flatten-container;
              leaf md5 {
                description
                  "Use HMAC MD5 algorithm for authentication";
                tailf:cli-full-command;
                type string;
              }
              leaf sha {
                description
                  "Use HMAC SHA algorithm for authentication";
                tailf:cli-full-command;
                type string;
              }
            }
            leaf credential {
              description
                "If the user password is already configured and saved";
              type empty;
            }
            leaf encrypted {
              description
                "specifying passwords as MD5 or SHA digests";
              type empty;
            }
          }
        }
      }
    }
  }

  grouping ospf-address-family-grouping {
    uses router-snmp-grouping;
    container topology {
      description
        "Associate the routing protocol to a topology instance";
      tailf:cli-compact-syntax;
      tailf:cli-sequence-commands;
      leaf name {
        tailf:cli-drop-node-name;
        type string;
      }
      leaf tid {
        description
          "Configuring the routing protocol topology tid";
        tailf:cli-optional-in-sequence;
        type uint32 {
          range "32..127";
        }
      }
    }
  }

  grouping router-rip-grouping {
    uses address-family-vrf-grouping;
    leaf flash-update-threshold {
      description
        "Specify flash update threshold in second";
      tailf:cli-full-command;
      type uint8 {
        range "0 .. 30";
      }
    }
    leaf input-queue {
      description
        "Specify input queue depth";
      tailf:cli-full-command;
      type uint16 {
        range "0 .. 1024";
      }
    }
    leaf output-delay {
      description
        "Interpacket delay for RIP updates";
      tailf:cli-full-command;
      type uint8 {
        range "8 .. 50";
      }
    }
    uses passive-interface-grouping;
    container traffic-share {
      description
        "How to compute traffic share over alternate paths";
      container min {
        description
          "All traffic shared among min metric paths";
        leaf across-interfaces {
          description
            "Use different interfaces for equal-cost paths";
          type empty;
        }
      }
    }
  }

  grouping default-redistribute-grouping {
    container connected {
      presence "Connected";
      description
        "Connected";
      uses rip-metric-route-map-grouping;
    }
    list bgp {
      description
        "Border Gateway Protocol (BGP)";
      tailf:cli-suppress-mode;
      tailf:cli-delete-when-empty;
      key "as-number";
      leaf as-number {
        type bgp-as-number-type;
      }
      uses rip-metric-route-map-grouping;
    }
    list eigrp {
      description
        "Enhanced Interior Gateway Routing Protocol (EIGRP)";
      tailf:cli-suppress-mode;
      tailf:cli-delete-when-empty;
      key "as-number";
      leaf as-number {
        type uint16 {
          range "1 .. 65535";
        }
      }
      uses rip-metric-route-map-grouping;
    }
    container isis {
      presence "ISO IS-IS";
      description
        "ISO IS-IS";
      list isis-area {
        tailf:cli-suppress-mode;
        tailf:cli-delete-when-empty;
        tailf:cli-drop-node-name;
        key "name";
        leaf name {
          tailf:cli-disallow-value "level-1|level-2|level-1-2|metric|route-map";
          type string;
        }
        uses redist-isis-grouping;
      }
      uses redist-isis-grouping;
    }
    container iso-igrp {
      presence "IGRP for OSI networks";
      description
        "IGRP for OSI networks";
      list isoigrp-list {
        description
          "Border Gateway Protocol (BGP)";
        tailf:cli-suppress-mode;
        tailf:cli-delete-when-empty;
        tailf:cli-drop-node-name;
        key "iso-area-tag";
        leaf iso-area-tag {
          tailf:cli-disallow-value "route-map";
          type string;
        }
        uses rip-iso-igrp-metric-route-map-grouping;
      }
      uses rip-iso-igrp-metric-route-map-grouping;
    }
    container mobile {
      presence "Mobile routes";
      description
        "Mobile routes";
      uses rip-metric-route-map-grouping;
    }
    container odr {
      presence "On Demand stub Routes";
      description
        "On Demand stub Routes";
      uses rip-metric-route-map-grouping;
    }
    list ospf {
      description
        "Open Shortest Path First (OSPF)";
      tailf:cli-suppress-mode;
      tailf:cli-delete-when-empty;
      key "process-id";
      leaf process-id {
        tailf:cli-suppress-range;
        type uint16 {
          range "1 .. 65535";
        }
      }
      list vrf {
        description
          "VPN Routing/Forwarding Instance";
        tailf:cli-diff-dependency "/ios:native/ip/vrf";
        tailf:cli-diff-dependency "/ios:native/vrf/definition";
        key "name";
        leaf name {
          type string;
        }
      }
      container match {
        tailf:cli-compact-syntax;
        tailf:cli-flatten-container;
        description
          "Redistribution of OSPF routes";
        container internal {
          presence "Redistribute OSPF internal routes";
          description
            "Redistribute OSPF internal routes";
          tailf:cli-compact-syntax;
          tailf:cli-flatten-container;
          uses rip-metric-route-map-grouping;
        }
        container external {
          description
            "Redistribute OSPF external routes";
          presence "Redistribute OSPF external routes";
          tailf:cli-compact-syntax;
          tailf:cli-flatten-container;
          leaf external-routes {
            tailf:cli-drop-node-name;
            type redist-ospf-external-type;
          }
          uses rip-metric-route-map-grouping;
        }
        container nssa-external {
          description
            "Redistribute OSPF NSSA external routes";
          presence "Redistribute OSPF NSSA external routes";
          tailf:cli-compact-syntax;
          tailf:cli-flatten-container;
          leaf nssa-external-routes {
            tailf:cli-drop-node-name;
            type redist-ospf-external-type;
          }
          uses rip-metric-route-map-grouping;
        }
      }
      uses rip-metric-route-map-grouping;
    }
    container static {
      presence "Static routes";
      description
        "Static routes";
      uses rip-metric-route-map-grouping;
    }
    container rip {
      presence "Routing Information Protocol (RIP)";
      description
        "Routing Information Protocol (RIP)";
      uses rip-metric-route-map-grouping;
    }
  }

  grouping ipv6-router-rip-redistribute-grouping {
    leaf include-connected {
      description
        "Include connected";
      type empty;
    }
    uses metric-route-map-grouping;
  }

  grouping distance-grouping {
    container distance {
      tailf:cli-compact-syntax;
      description
        "Define an administrative distance";
      leaf distance-leaf {
        tailf:cli-drop-node-name;
        tailf:cli-full-command;
        type uint8 {
          range "1..255";
        }
      }
      list distance-list {
        tailf:cli-suppress-mode;
        tailf:cli-delete-when-empty;
        tailf:cli-drop-node-name;
        key "number ip mask";
        leaf number {
          tailf:cli-suppress-range;
          type uint8 {
            range "1 .. 255";
          }
        }
        leaf ip {
          type inet:ipv4-address;
        }
        leaf mask {
          type inet:ipv4-address;
        }
      }
    }
  }

  grouping offset-list-grouping {
    list offset-list {
      description
        "Add or subtract offset from RIP metrics";
      tailf:cli-compact-syntax;
      tailf:cli-suppress-mode;
      tailf:cli-delete-when-empty;
      tailf:cli-suppress-list-no;
      tailf:cli-sequence-commands;
      key "in-out";
      leaf in-out {
        tailf:cli-incomplete-command;
        type offset-list-in-out-type;
      }
      leaf offset {
        tailf:cli-drop-node-name;
        mandatory true;
        type uint8 {
          range "0 .. 16";
        }
      }
    }
  }

  grouping default-router-rip-grouping {
    leaf auto-summary {
      description
        "Enable automatic network number summarization";
      type empty;
    }
    leaf maximum-paths {
      tailf:cli-full-command;
      description
        "Forward packets over multiple paths";
      type uint8 {
        range "1 .. 32";
      }
    }
    list neighbor {
      description
        "Specify a neighbor router";
      tailf:cli-suppress-mode;
      tailf:cli-delete-when-empty;
      key "ip";
      leaf ip {
        type inet:ipv4-address;
      }
    }
    list network {
      description
        "Enable routing on an IP network";
      tailf:cli-suppress-mode;
      tailf:cli-delete-when-empty;
      key "ip";
      leaf ip {
        type inet:ipv4-address;
      }
    }
    leaf validate-update-source {
      description
        "Perform sanity checks against source address of routing updates";
      tailf:cli-full-command;
      tailf:cli-boolean-no;
      tailf:cli-trim-default;
      type boolean;
    }
  }

  grouping address-family-vrf-grouping {
    uses default-router-rip-grouping;
    container default-information {
      tailf:cli-incomplete-no;
      description
        "Control distribution of default information";
      container originate {
        tailf:cli-full-no;
        presence "Distribute a default route";
        description
          "Distribute a default route";
        leaf route-map {
          description
            "Route-map reference";
          tailf:cli-no-value-on-delete;
          type string;
        }
      }
    }
    leaf default-metric {
      description
        "Set metric of redistributed routes";
      tailf:cli-full-command;
      type uint32 {
        range "1..4294967295";
      }
    }
    uses distance-grouping;
    uses distribute-list-grouping;
    uses offset-list-grouping;
    container redistribute {
      description
        "Redistribute information from another routing protocol";
      uses rip-metric-route-map-grouping;
      uses default-redistribute-grouping;
    }
    container timers {
      description
        "Adjust routing timers";
      tailf:cli-incomplete-no;
      tailf:cli-compact-syntax;
      container basic {
        description
          "Basic routing protocol update timers";
        tailf:cli-sequence-commands;
	tailf:cli-compact-syntax;
        tailf:cli-full-no;
        leaf updates {
          tailf:cli-drop-node-name;
          tailf:cli-incomplete-command;
          tailf:cli-no-value-on-delete;
          type uint32 {
            range "1 .. 4294967295";
          }
        }
        leaf invalid {
          tailf:cli-drop-node-name;
          tailf:cli-incomplete-command;
          tailf:cli-no-value-on-delete;
          type uint32 {
            range "1 .. 4294967295";
          }
        }
        leaf holddown {
          tailf:cli-drop-node-name;
          tailf:cli-incomplete-command;
          tailf:cli-no-value-on-delete;
          type uint32 {
            range "1 .. 4294967295";
          }
        }
        leaf flush {
          tailf:cli-drop-node-name;
          tailf:cli-incomplete-command;
          tailf:cli-no-value-on-delete;
          type uint32 {
            range "1 .. 4294967295";
          }
        }
        leaf sleep {
          tailf:cli-drop-node-name;
          tailf:cli-no-value-on-delete;
          type uint32 {
            range "1 .. 4294967295";
          }
        }
      }
    }
    leaf version {
      description
        "Set routing protocol version";
      type uint8 {
        range "1 .. 2";
      }
    }
  }

  grouping redist-isis-grouping {
    container rip-isis-redist {
      tailf:cli-drop-node-name;
      leaf isis-level-routes {
        tailf:cli-drop-node-name;
        type enumeration {
          enum "level-1";
          enum "level-2";
          enum "level-1-2";
        }
      }
      uses rip-metric-route-map-grouping;
    }
  }

  grouping rip-metric-route-map-grouping {
    container rip-metric-route-map {
      tailf:cli-drop-node-name;
      tailf:cli-compact-syntax;
      container metric {
        tailf:cli-compact-syntax;
        tailf:cli-flatten-container;
        description
          "Metric for redistributed routes";
        choice metric-transparent-choice {
          leaf metric-value {
            tailf:cli-drop-node-name;
            description
              "Metric for redistributed routes";
            type uint32 {
              range "0 .. 16";
            }
          }
          leaf transparent {
            description
              "Transparently redistribute metric";
            type empty;
          }
        }
      }
      leaf route-map {
        description
          "Route map reference";
        type string;
      }
    }
  }

  grouping rip-iso-igrp-metric-route-map-grouping {
    container rip-metric-route-map {
      tailf:cli-drop-node-name;
      tailf:cli-compact-syntax;
      tailf:cli-sequence-commands;
      leaf route-map {
        description
          "Route map reference";
        type string;
      }
      container metric {
        tailf:cli-compact-syntax;
        description
          "Metric for redistributed routes";
        choice metric-transparent-choice {
          leaf metric-value {
            tailf:cli-drop-node-name;
            description
              "Metric for redistributed routes";
            type uint32 {
              range "0 .. 16";
            }
          }
          leaf transparent {
            description
              "Transparently redistribute metric";
            type empty;
          }
        }
      }
    }
  }

  // router/isis grouping
  grouping narrow-wide-transition-grouping {
    leaf narrow-wide {
      tailf:cli-drop-node-name;
      tailf:cli-full-command;
      type isis-level-type;
    }
    leaf transition {
      description
        "Accept both styles of TLVs during transition";
      type isis-level-type;
      tailf:cli-full-command;
    }
  }

  // router/isis grouping
  grouping spf-intervals-grouping {
    leaf interval {
      tailf:cli-drop-node-name;
      type uint32 {
        range "1 .. 120";
      }
    }
    leaf initial-wait {
      tailf:cli-drop-node-name;
      type uint32 {
        range "1 .. 120000";
      }
    }
    leaf minimum-wait {
      tailf:cli-drop-node-name;
      type uint32 {
        range "1 .. 120000";
      }
    }
  }

  // router/isis grouping
  grouping authenticate-snp-grouping {
    leaf authenticate {
      description
        "Authentication";
      tailf:cli-optional-in-sequence;
      type empty;
    }
    leaf snp {
      description
        "SNP PDUs";
      tailf:cli-optional-in-sequence;
      type enumeration {
        enum "send-only";
        enum "validate";
      }
    }
  }

  // router/isis grouping
  grouping lsp-gen-interval-grouping {
    leaf interval {
      tailf:cli-drop-node-name;
      type uint32 {
        range "1 .. 120";
      }
    }
    leaf initial-wait {
      tailf:cli-drop-node-name;
      type uint32 {
        range "1 .. 120000";
      }
    }
    leaf wait {
      tailf:cli-drop-node-name;
      type uint32 {
        range "1 .. 120000";
      }
    }
  }

  // router/isis grouping
  grouping set-overload-bit-suppress-grouping {
    leaf external {
      description
        "If overload-bit set, don't advertise IP prefixes learned from other protocols";
      type empty;
    }
    leaf interlevel {
      description
        "If overload-bit set, don't advertise IP prefixes learned from another ISIS level";
      type empty;
    }
  }

  // router/isis grouping
  grouping summary-address-metric-tag-grouping {
    leaf metric {
      description
        "Set metric for summay route";
      tailf:cli-full-command;
      type uint32 {
        range "1 .. 4294967295";
      }
    }
    leaf tag {
      description
        "Set tag";
      type uint32 {
        range "1 .. 4294967295";
      }
    }
  }

  // router/isis grouping
  grouping authentication-level-grouping {
    leaf levels {
      tailf:cli-drop-node-name;
      type authentication-level-type;
    }
  }

  // router/isis grouping
  grouping isis-authentication-grouping {
    container mode {
      description
        "Authentication mode";
      container md5 {
        description
          "Keyed message digest";
        presence "Keyed message digest";
        uses authentication-level-grouping;
      }
      container text {
        description
          "Clear text password";
        presence "Clear text password";
        uses authentication-level-grouping;
      }
    }
    container key-chain {
      description
        "Authentication key-chain";
      choice key-chain-choice {
        case key-chain-level-case {
          list key-chain-list {
            tailf:cli-drop-node-name;
            tailf:cli-suppress-mode;
            key "levels";
            uses authentication-level-grouping;
            leaf name {
              tailf:cli-drop-node-name;
              tailf:cli-prefix-key;
              type string;
            }
          }
        }
        case key-chain-only-case {
          leaf name {
            tailf:cli-drop-node-name;
            type string;
          }
        }
      }
    }
    container send-only {
      description
        "Authentication send only, receive ignore";
      presence "Authentication send only, receive ignore";
      uses authentication-level-grouping;
    }
  }

  grouping isis-metric-grouping {
    container metric {
      description
        "Configure the metric for interface";
      choice metric-choice {
        case metric-level-case {
          list metric-list {
            tailf:cli-drop-node-name;
            tailf:cli-suppress-mode;
            key "levels";
            leaf levels {
              type enumeration {
                enum "level-1";
                enum "level-2";
              }
            }
            leaf value {
              tailf:cli-drop-node-name;
              tailf:cli-prefix-key;
              type union {
                type uint32 {
                  range "1..16777214";
                }
                type enumeration {
                  enum "maximum";
                }
              }
            }
          }
        }
        case metric-only-case {
          leaf value {
            tailf:cli-drop-node-name;
            type union {
              type uint32 {
                range "1..16777214";
              }
              type enumeration {
                enum "maximum";
              }
            }
          }
        }
      }
    }
  }

  // router/isis grouping
  grouping redist-level-grouping {
    leaf levels {
      tailf:cli-drop-node-name;
      tailf:cli-break-sequence-commands;
      type isis-routes-level-type;
    }
  }

  // router/isis grouping
  grouping isis-redist-grouping {
    leaf levels {
      tailf:cli-drop-node-name;
      type isis-routes-level-type;
    }
    leaf metric {
      description
        "ISIS default metric";
      type uint32 {
        range "0 .. 4294967295";
      }
    }
    leaf metric-type {
      description
        "OSPF/IS-IS exterior metric type for redistributed routes";
      type enumeration {
        enum "external";
        enum "internal";
        enum "rib-metric-as-external";
        enum "rib-metric-as-internal";
      }
    }
    leaf route-map {
      description
        "Route map reference";
      type string;
    }
  }

  grouping isis-redist-af-grouping {
    leaf include-connected {
      description
        "Include connected";
      type empty;
    }
    uses isis-redist-grouping;
  }

  grouping isis-redist-ospf-match-grouping {
    uses redist-level-grouping;
    leaf metric {
      description
        "ISIS default metric";
      type uint32 {
        range "0 .. 4294967295";
      }
    }
    leaf route-map {
      description
        "Route map reference";
      type string;
    }
  }

  grouping isis-redist-clns-ip-grouping {
    container clns {
      description
        "Redistribution of BGP NSAP routes";
      presence "Redistribution of BGP NSAP routes";
      uses isis-redist-grouping;
    }
    container ip {
      description
        "Redistribution of BGP IP routes";
      uses isis-redist-grouping;
    }
  }

  grouping isis-ipv4-ipv6-common-grouping {
    leaf adjacency-check {
      description
        "Check ISIS neighbor protocol support";
      tailf:cli-full-command;
      type empty;
    }
    container bfd {
      description
        "BFD configuration commands";
      leaf all-interfaces {
        description
          "Enable BFD on all interfaces";
        type empty;
      }
      leaf check-ctrl-plane-failure {
        description
          "BFD check control plane failure";
        type empty;
      }
    }
    leaf router-id {
      description
        "Interface of stable IP address for system";
      type string;
    }
  }

  grouping isis-common-grouping {
    container advertise {
      description
        "Control which IP routes flow in L1 and L2 LSPs";
      leaf passive-only {
        description
          "only interface address of passive interfaces";
        type empty;
      }
    }
    container default-information {
      tailf:cli-incomplete-no;
      description
        "Control distribution of default information";
      container originate {
        tailf:cli-full-no;
        presence "Distribute a default route";
        description
          "Distribute a default route";
        leaf route-map {
          description
            "Route-map reference";
          tailf:cli-no-value-on-delete;
          type string;
        }
      }
    }
    leaf help {
      description
        "Description of the interactive help system";
      tailf:cli-full-command;
      type empty;
    }
    leaf maximum-paths {
      description
        "Forward packets over multiple paths";
      tailf:cli-full-command;
      type uint32 {
        range "1 .. 32";
      }
    }
    container metric {
      description
        "Set ISIS metric for all interfaces";
      choice metric-choice {
        case metric-level-case {
          list metrics {
            tailf:cli-suppress-mode;
            tailf:cli-drop-node-name;
            key "level";
            leaf level {
              tailf:cli-drop-node-name;
              type enumeration {
                enum "level-1";
                enum "level-2";
              }
            }
            leaf metric {
              tailf:cli-drop-node-name;
              tailf:cli-prefix-key;
              type uint32 {
                range "1..16777214";
              }
            }
          }
        }
        case metric-only-case {
          leaf metric {
            tailf:cli-drop-node-name;
            type uint32 {
              range "1..16777214";
            }
          }
        }
      }
    }
    container prc-interval {
      description
        "Minimum interval between partial route calculations";
      tailf:cli-compact-syntax;
      tailf:cli-sequence-commands;
      leaf interval {
        tailf:cli-drop-node-name;
        type uint32 {
          range "1 .. 120";
        }
      }
      leaf initial-wait {
        tailf:cli-drop-node-name;
        tailf:cli-optional-in-sequence;
        type uint32 {
          range "1 .. 120000";
        }
      }
      leaf minimum-wait {
        tailf:cli-drop-node-name;
        tailf:cli-optional-in-sequence;
        type uint32 {
          range "1 .. 120000";
        }
      }
    }
    container set-overload-bit {
      description
        "Signal other routers not to use us in SPF";
      presence "Signal other routers not to use us in SPF";
      choice set-overload-bit-choice {
        container on-startup {
          description
            "Set overload-bit only temporarily after reboot";
          choice on-startup-choice {
            container time {
              tailf:cli-drop-node-name;
              tailf:cli-compact-syntax;
              tailf:cli-sequence-commands;
              leaf time {
                tailf:cli-drop-node-name;
                type uint32 {
                  range "5 .. 86400";
                }
              }
              leaf suppress {
                description
                  "If overload-bit set, suppress the following types of IP prefixes";
                tailf:cli-incomplete-command;
                type empty;
              }
              leaf external {
                description
                  "If overload-bit set, don't advertise IP prefixes learned from other protocols";
                tailf:cli-break-sequence-commands;
                type empty;
              }
              leaf interlevel {
                description
                  "If overload-bit set, don't advertise IP prefixes learned from another ISIS level";
                type empty;
              }
            }
            container wait-for-bgp {
              description
                "Let BGP decide when to unset the overload bit";
              presence "Let BGP decide when to unset the overload bitW";
              container suppress {
                description
                  "If overload-bit set, suppress the following types of IP prefixes";
                tailf:cli-compact-syntax;
                uses set-overload-bit-suppress-grouping;
              }
            }
          }
        }
        container suppress {
          description
            "If overload-bit set, suppress the following types of IP prefixes";
          tailf:cli-compact-syntax;
          uses set-overload-bit-suppress-grouping;
        }
      }
    }
    container spf-interval {
      description
        "Minimum interval between SPF calculations";
      tailf:cli-compact-syntax;
      choice spf-interval-choice {
        list level-1-2 {
          tailf:cli-drop-node-name;
          tailf:cli-suppress-mode;
          tailf:cli-delete-when-empty;
          tailf:cli-compact-syntax;
          tailf:cli-sequence-commands;
          tailf:cli-incomplete-command;
          key "level";
          leaf level {
            type enumeration {
              enum "level-1";
              enum "level-2";
            }
          }
          uses spf-intervals-grouping;
        }
        container intervals {
          tailf:cli-drop-node-name;
          tailf:cli-compact-syntax;
          tailf:cli-sequence-commands;
          uses spf-intervals-grouping;
        }
      }
    }
  }

  grouping isis-address-family-grouping {
    uses isis-common-grouping;
    uses isis-ipv4-ipv6-common-grouping;
    leaf distance {
      description
        "Administrative distance";
      tailf:cli-full-command;
      type uint32 {
        range "1 .. 254";
      }
    }
    container distribute-list {
      description
        "Filter networks in routing updates";
      list prefix-list {
        description
          "Filter connections based on an IPv6 prefix-list";
        tailf:cli-suppress-mode;
        key "name";
        leaf name {
          type string;
        }
        container in {
          description
            "Filter incoming routing updates";
          presence "true";
          container interface {
            description
              "Specify interface";
            tailf:cli-drop-node-name;
            tailf:cli-compact-syntax;
            tailf:cli-flatten-container;
            uses interface-grouping;
          }
        }
      }
    }
    container ipv6 {
      description
        "IPv6 specific commands";
      container route {
        description
          "ISIS IPV6 routes";
        container priority {
          description
            "Assign priority to IPV6 prefixes";
          container high {
            description
              "Assign high priority to important IPV6 prefixes in ISIS IPV6 local RIB";
            leaf tag {
              description
                "Assign high priority to IPV6 prefixes with a specific route tag";
              type uint32;
            }
          }
        }
      }
    }
    container multi-topology {
      description
        "Enable multi-topology mode";
      presence "Enable multi-topology mode";
      leaf transition {
        description
          "Accept and generate both IS-IS IPv6 and Multi-topology IPv6 TLVs";
        type empty;
      }
    }
    container redistribute {
      description
        "Redistribute IPv6 prefixes from another routing protocol";
      container application {
        description
          "Application Protocol";
        presence "Application Protocol";
        uses isis-redist-af-grouping;
      }
      container bgp {
        description
          "Border Gateway Protocol (BGP)";
        tailf:cli-compact-syntax;
        leaf as-number {
          tailf:cli-drop-node-name;
          type bgp-as-number-type;
        }
        uses isis-redist-af-grouping;
      }
      container connected {
        description
          "Connected";
        tailf:cli-compact-syntax;
        presence "Connected";
        uses isis-redist-grouping;
      }
      list eigrp {
        description
          "Enhanced Interior Gateway Routing Protocol (EIGRP)";
        tailf:cli-suppress-mode;
        tailf:cli-delete-when-empty;
        key "as-number";
        leaf as-number {
          tailf:cli-drop-node-name;
          type uint32 {
            range "1 .. 65535";
          }
        }
        uses isis-redist-af-grouping;
      }
      container isis {
        description
          "ISO IS-IS";
        presence "true";
        list isis-redistribute {
          tailf:cli-drop-node-name;
          tailf:cli-suppress-mode;
          tailf:cli-compact-syntax;
          key "area-tag";
          leaf area-tag {
            tailf:cli-disallow-value "ip";
            type string;
          }
          uses isis-redist-af-grouping;
        }
        list isis-leak {
          tailf:cli-drop-node-name;
          tailf:cli-suppress-mode;
          key "isis-redist-levels1 isis-redist-levels2";
          leaf isis-redist-levels1 {
            tailf:cli-incomplete-command;
            type enumeration {
              enum "level-1";
              enum "level-2";
            }
          }
          leaf isis-redist-levels2 {
            tailf:cli-incomplete-command;
            type enumeration {
              enum "level-1";
              enum "level-2";
            }
          }
          leaf into {
            description
              "from level-n into level-m";
            tailf:cli-incomplete-command;
            tailf:cli-prefix-key {
              tailf:cli-before-key "2";
            }
            type empty;
          }
          choice isis-redist-isis-ip-choice {
            leaf distribute-list {
              description
                "select routes";
              type string;
            }
            leaf route-map {
              description
                "Route map for route matching";
              type string;
            }
          }
        }
      }
      container lisp {
        description
          "Locator ID Separation Protocol (LISP)";
        presence "Locator ID Separation Protocol (LISP)";
        uses isis-redist-af-grouping;
      }
      container nd {
        description
          "Neighbor Discovery";
        presence "Neighbor Discovery";
        uses isis-redist-af-grouping;
      }
      container nemo {
        description
          "Network Mobility (NEMO)";
        tailf:cli-compact-syntax;
        uses isis-redist-af-grouping;
      }
      list ospf {
        description
          "Open Shortest Path First (OSPF)";
        tailf:cli-suppress-mode;
        tailf:cli-delete-when-empty;
        key "process-id";
        leaf process-id {
          tailf:cli-suppress-range;
          type uint32 {
            range "1 .. 65535";
          }
        }
        uses isis-redist-af-grouping;
        container match {
          tailf:cli-compact-syntax;
          tailf:cli-flatten-container;
          description
            "Redistribution of OSPF routes";
          container internal {
            presence "Redistribute OSPF internal routes";
            description
              "Redistribute OSPF internal routes";
            tailf:cli-compact-syntax;
            tailf:cli-flatten-container;
            uses isis-redist-grouping;
          }
          container external {
            description
              "Redistribute OSPF external routes";
            presence "Redistribute OSPF external routes";
            tailf:cli-compact-syntax;
            tailf:cli-flatten-container;
            leaf external-routes {
              tailf:cli-drop-node-name;
              type redist-ospf-external-type;
            }
            uses isis-redist-grouping;
          }
          container nssa-external {
            description
              "Redistribute OSPF NSSA external routes";
            presence "Redistribute OSPF NSSA external routes";
            tailf:cli-compact-syntax;
            tailf:cli-flatten-container;
            leaf nssa-external-routes {
              tailf:cli-drop-node-name;
              type redist-ospf-external-type;
            }
            uses isis-redist-grouping;
          }
        }
      }
      list rip {
        description
          "IPv6 Routing Information Protocol (RIPv6)";
        tailf:cli-suppress-mode;
        tailf:cli-delete-when-empty;
        key "process";
        leaf process {
          type string;
        }
        uses isis-redist-af-grouping;
      }
      container static {
        description
          "Static routes";
        presence "Static routes";
        uses isis-redist-grouping;
      }
    }
    list summary-prefix {
      description
        "Configure IPv6 summary prefix";
      tailf:cli-suppress-mode;
      tailf:cli-delete-when-empty;
      key "prefix";
      leaf prefix {
        type inet:ipv6-prefix;
      }
      leaf levels {
        tailf:cli-drop-node-name;
        type enumeration {
          enum "level-1";
          enum "level-1-2";
          enum "level-2";
        }
      }
    }
    container table-map {
      description
        "Map external entry attributes into routing table";
      tailf:cli-compact-syntax;
      tailf:cli-sequence-commands;
      leaf name {
        tailf:cli-drop-node-name;
        type string;
      }
      leaf filter {
        description
          "Selective route download";
        tailf:cli-optional-in-sequence;
        type empty;
      }
    }
  }

  grouping isis-redist-vrf-grouping {
    container application {
      description
        "Application";
      list appname {
        tailf:cli-drop-node-name;
        tailf:cli-suppress-mode;
        key "appname";
        leaf appname {
          description
            "Application name";
          type string;
        }
        uses isis-redist-grouping;
      }
    }
    container bgp {
      description
        "Border Gateway Protocol (BGP)";
      list bp-as-num {
        tailf:cli-drop-node-name;
        tailf:cli-suppress-mode;
        key "bp-as-num";
        leaf bp-as-num {
          description
            "Autonomous system number";
          type bgp-as-number-type;
        }
        uses isis-redist-clns-ip-grouping;
        uses isis-redist-grouping;
      }
      leaf a_LESSER_1_PERIOD_0-XX_PERIOD_YY_GREATER_ {
        tailf:alt-name "_LT_1.0-XX.YY_GT_";
        description
          "Autonomous system number";
        type empty;
      }
    }
    container connected {
      description
        "Connected";
      presence "true";
      uses isis-redist-grouping;
    }
    container eigrp {
      description
        "Enhanced Interior Gateway Routing Protocol (EIGRP)";
      list eigrp-as {
        tailf:cli-drop-node-name;
        tailf:cli-suppress-mode;
        key "eigrp-as";
        leaf eigrp-as {
          description
            "AS number";
          type uint16 {
            range "1..65535";
          }
        }
        uses isis-redist-grouping;
      }
    }
    container isis {
      description
        "ISO IS-IS";
      list isis-atag {
        tailf:cli-drop-node-name;
        tailf:cli-suppress-mode;
        key "isis-atag";
        leaf isis-atag {
          description
            "ISO routing area tag";
          type string;
        }
        container ip {
          description
            "Redistribution of IP routes between levels or processes";
          uses isis-redist-grouping;
        }
      }
      container ip {
        description
          "Redistribution of IP routes between levels or processes";
        presence "true";
        uses isis-redist-grouping;
      }
    }
    container iso-igrp {
      description
        "IGRP for OSI networks";
      presence "true";
      list iso-atag {
        tailf:cli-drop-node-name;
        tailf:cli-suppress-mode;
        key "iso-atag";
        leaf iso-atag {
          description
            "ISO routing area tag";
          type string;
        }
        leaf route-map {
          description
            "Route map reference";
          type empty;
        }
      }
      container route-map {
        description
          "Route map reference";
        presence "true";
        leaf rm-point {
          description
            "Pointer to route-map entries";
          tailf:cli-drop-node-name;
          type string;
        }
      }
    }
    container lisp {
      description
        "Locator ID Separation Protocol (LISP)";
      presence "true";
      uses isis-redist-grouping;
    }
    container mobile {
      description
        "Mobile routes";
      presence "true";
      uses isis-redist-grouping;
    }
    leaf ospf {
      description
        "Process ID";
      type uint16 {
        range "1..65535";
      }
    }
    container ospfv3 {
      description
        "OSPFv3";
      list os3-id {
        tailf:cli-drop-node-name;
        tailf:cli-suppress-mode;
        key "os3-id";
        leaf os3-id {
          description
            "Process ID";
          type uint16 {
            range "1..65535";
          }
        }
        uses isis-redist-grouping;
      }
    }
    container rip {
      description
        "Routing Information Protocol (RIP)";
      presence "true";
      uses isis-redist-grouping;
    }
    container static {
      description
        "Static routes";
      presence "true";
      uses isis-redist-clns-ip-grouping;
      uses isis-redist-grouping;
    }
  }
   
  // router/isis grouping
  grouping tie-break-prefer-repair-grouping {
    leaf downstream {
      description
        "priority number";
      type uint8 {
        range "1..255";
      }
    }
    leaf linecard-disjoint {
      description
        "priority number";
      type uint8 {
        range "1..255";
      }
    }
    leaf lowest-backup-path-metric {
      description
        "priority number";
      type uint8 {
        range "1..255";
      }
    }
    leaf node-protecting {
      description
        "priority number";
      type uint8 {
        range "1..255";
      }
    }
    leaf primary-path {
      description
        "priority number";
      type uint8 {
        range "1..255";
      }
    }
    leaf secondary-path {
      description
        "priority number";
      type uint8 {
        range "1..255";
      }
    }
    leaf srlg-disjoint {
      description
        "priority number";
      type uint8 {
        range "1..255";
      }
    }
  }

  grouping isis-topology-grouping {
    list distance {
      description
        "Define an administrative distance";
      tailf:cli-compact-syntax;
      tailf:cli-suppress-mode;
      key "number";
      leaf number {
        type uint8 {
          range "1 .. 255";
        }
      }
      list ip-list {
        tailf:cli-drop-node-name;
        tailf:cli-suppress-mode;
        tailf:cli-compact-syntax;
        key "ip";
        leaf ip {
          description
            "IP Source address";
          type inet:ipv4-address;
        }
        list wildcard-bits {
          tailf:cli-drop-node-name;
          tailf:cli-suppress-mode;
          key "w-bits";
          leaf w-bits {
            type inet:ipv4-address;
          }
          leaf access-list {
            tailf:cli-drop-node-name;
            type default-access-list-standard-id-type;
          }
        }
      }
      leaf clns {
        description
          "Distance applied for CLNS derived routes";
        tailf:cli-hide-in-submode;
        type empty;
      }
      leaf ip {
        description
          "Distance applied for IP derived routes";
        tailf:cli-hide-in-submode;
        type empty;
      }
    }
    container ip {
      description
        "IP specific commands";
      container route {
        description
          "ISIS IP routes";
        container priority {
          description
            "Assign priority to IP prefixes";
          container high {
            description
              "Assign high priority to important IP prefixes in ISIS IP local RIB";
            leaf tag {
              description
                "Assign high priority to IP prefixes with a specific route tag";
              type uint32 {
                range "1 .. 4294967295";
              }
            }
          }
        }
      }
    }
    leaf priority {
      description
        "priority value";
      type uint8 {
        range "0..127";
      }
    }
    container redistribute {
      description
        "Redistribute information from another routing protocol";
      list application {
        description
          "Application";
        tailf:cli-suppress-mode;
        tailf:cli-compact-syntax;
        key "name";
        leaf name {
          description
            "Application name";
          type string;
        }
        uses isis-redist-grouping;
      }
      container bgp {
        description
          "Border Gateway Protocol (BGP)";
        tailf:cli-compact-syntax;
        leaf as-number {
          tailf:cli-drop-node-name;
          type bgp-as-number-type;
        }
        uses isis-redist-grouping;
        uses isis-redist-clns-ip-grouping;
      }
      container connected {
        description
          "Connected";
        presence "Connected";
        uses isis-redist-grouping;
      }
      list eigrp {
        description
          "Enhanced Interior Gateway Routing Protocol (EIGRP)";
        tailf:cli-suppress-mode;
        tailf:cli-delete-when-empty;
        key "as-number";
        leaf as-number {
          tailf:cli-drop-node-name;
          type uint32 {
            range "1 .. 65535";
          }
        }
        uses isis-redist-grouping;
      }
      container isis {
        description
          "ISO IS-IS";
        list isis-redistribute {
          tailf:cli-drop-node-name;
          tailf:cli-suppress-mode;
          key "area-tag";
          leaf area-tag {
            tailf:cli-disallow-value "ip";
            type string;
          }
          container ip {
            description
              "Redistribution of IP routes between levels or processes";
            tailf:cli-compact-syntax;
            presence "true";
            uses isis-redist-grouping;
          }
        }
        list ip {
          description
            "Redistribution of IP routes between levels";
          tailf:cli-suppress-mode;
          key "isis-redist-levels1 isis-redist-levels2";
          leaf isis-redist-levels1 {
            tailf:cli-incomplete-command;
            type enumeration {
              enum "level-1";
              enum "level-2";
            }
          }
          leaf isis-redist-levels2 {
            tailf:cli-incomplete-command;
            type enumeration {
              enum "level-1";
              enum "level-2";
            }
          }
          leaf into {
            description
              "from level-n into level-m";
            tailf:cli-incomplete-command;
            tailf:cli-prefix-key {
              tailf:cli-before-key "2";
            }
            type empty;
          }
          choice isis-redist-isis-ip-choice {
            leaf distribute-list {
              description
                "select routes";
              type uint32 {
                range "100 .. 199";
              }
            }
            leaf route-map {
              description
                "Route map for route matching";
              type string;
            }
          }
        }
      }
      container iso-igrp {
        description
          "IGRP for OSI networks";
        presence "IGRP for OSI networks";
        tailf:cli-sequence-commands;
	tailf:cli-compact-syntax;
        choice iso-igrp-choice {
          container area-tag-route-map-container {
            tailf:cli-drop-node-name;
            tailf:cli-sequence-commands;
	    tailf:cli-compact-syntax;
            tailf:cli-flatten-container;
            leaf area-tag {
              tailf:cli-drop-node-name;
              tailf:cli-disallow-value "route-map";
              type string;
            }
            leaf route-map {
              description
                "Route map reference";
              type string;
            }
          }
          leaf route-map {
            description
              "Route map reference";
            type string;
          }
        }
        uses redist-level-grouping;
        leaf metric {
          description
            "ISIS default metric";
          type uint32 {
            range "0 .. 4294967295";
          }
        }
        leaf metric-type {
          description
            "OSPF/IS-IS exterior metric type for redistributed routes";
          type enumeration {
            enum "external";
            enum "internal";
            enum "rib-metric-as-external";
            enum "rib-metric-as-internal";
          }
        }
      }
      container lisp {
        description
          "Locator ID Separation Protocol (LISP)";
        presence "true";
        uses isis-redist-af-grouping;
      }
      container maximum-prefix {
        description
          "Maximum number of prefixes redistributed to protocol";
        tailf:cli-compact-syntax;
        tailf:cli-sequence-commands;
        leaf number {
          tailf:cli-drop-node-name;
          type uint32 {
            range "1 .. 4294967295";
          }
        }
        leaf threshold-value {
          tailf:cli-drop-node-name;
          tailf:cli-break-sequence-commands;
          type uint32 {
            range "1 .. 100";
          }
        }
        leaf warning-only {
          description
            "Only give warning message when limit is exceeded";
          tailf:cli-full-command;
          type empty;
        }
        leaf withdraw {
          description
            "Withdraw redistibuted prefixes";
          tailf:cli-full-command;
          type empty;
        }
      }
      container mobile {
        description
          "Mobile routes";
        presence "Mobile routes";
        uses isis-redist-grouping;
      }
      container odr {
        description
          "On Demand stub Routes";
        presence "On Demand stub Routes";
        uses isis-redist-grouping;
      }
      list ospf {
        description
          "Open Shortest Path First (OSPF)";
        tailf:cli-suppress-mode;
        tailf:cli-compact-syntax;
        tailf:cli-delete-when-empty;
        key "process-id";
        leaf process-id {
          tailf:cli-suppress-range;
          type uint32 {
            range "1 .. 65535";
          }
        }
        uses isis-redist-grouping;
        container match {
          tailf:cli-compact-syntax;
          tailf:cli-flatten-container;
          description
            "Redistribution of OSPF routes";
          container internal {
            presence "Redistribute OSPF internal routes";
            description
              "Redistribute OSPF internal routes";
            tailf:cli-compact-syntax;
            tailf:cli-flatten-container;
            uses isis-redist-grouping;
          }
          container external {
            description
              "Redistribute OSPF external routes";
            presence "Redistribute OSPF external routes";
            tailf:cli-compact-syntax;
            tailf:cli-flatten-container;
            leaf external-routes {
              tailf:cli-drop-node-name;
              type redist-ospf-external-type;
            }
            uses isis-redist-grouping;
          }
          container nssa-external {
            description
              "Redistribute OSPF NSSA external routes";
            presence "Redistribute OSPF NSSA external routes";
            tailf:cli-compact-syntax;
            tailf:cli-flatten-container;
            leaf nssa-external-routes {
              tailf:cli-drop-node-name;
              type redist-ospf-external-type;
            }
            uses isis-redist-grouping;
          }
        }
        leaf vrf {
          description
            "VPN Routing/Forwarding Instance";
          tailf:cli-diff-dependency "/ios:native/ip/vrf";
          tailf:cli-diff-dependency "/ios:native/vrf/definition";
          type string;
        }
      }
      list ospfv3 {
        description
          "Open Shortest Path First (OSPF)";
        tailf:cli-suppress-mode;
        tailf:cli-compact-syntax;
        tailf:cli-delete-when-empty;
        key "process-id";
        leaf process-id {
          tailf:cli-suppress-range;
          type uint32 {
            range "1 .. 65535";
          }
        }
        uses isis-redist-grouping;
        container match {
          tailf:cli-compact-syntax;
          tailf:cli-flatten-container;
          description
            "Redistribution of OSPF routes";
          container internal {
            presence "Redistribute OSPF internal routes";
            description
              "Redistribute OSPF internal routes";
            tailf:cli-compact-syntax;
            tailf:cli-flatten-container;
            uses isis-redist-grouping;
          }
          container external {
            description
              "Redistribute OSPF external routes";
            presence "Redistribute OSPF external routes";
            tailf:cli-compact-syntax;
            tailf:cli-flatten-container;
            leaf external-routes {
              tailf:cli-drop-node-name;
              type redist-ospf-external-type;
            }
            uses isis-redist-grouping;
          }
          container nssa-external {
            description
              "Redistribute OSPF NSSA external routes";
            presence "Redistribute OSPF NSSA external routes";
            tailf:cli-compact-syntax;
            tailf:cli-flatten-container;
            leaf nssa-external-routes {
              tailf:cli-drop-node-name;
              type redist-ospf-external-type;
            }
            uses isis-redist-grouping;
          }
        }
        leaf vrf {
          description
            "VPN Routing/Forwarding Instance";
          tailf:cli-diff-dependency "/ios:native/ip/vrf";
          tailf:cli-diff-dependency "/ios:native/vrf/definition";
          type string;
        }
      }
      container rip {
        description
          "Routing Information Protocol (RIP)";
        presence "Routing Information Protocol (RIP)";
        uses isis-redist-grouping;
      }
      container static {
        description
          "Static routes";
        presence "Static routes";
        uses isis-redist-clns-ip-grouping;
      }
      container vrf {
        description
          "Specify a source VRF";
        list vrf-nm {
          tailf:cli-drop-node-name;
          tailf:cli-suppress-mode;
          key "vrf-nm";
          leaf vrf-nm {
            description
              "Source VRF name";
            type string;
          }
          uses isis-redist-vrf-grouping;
        }
        container global {
          description
            "global VRF";
          uses isis-redist-vrf-grouping;
        }
      }
    }
    container set-attached-bit {
      description
        "Conditionally advertise us as attached to L2";
      leaf route-map {
        description
          "Route-map reference";
        type string;
      }
    }
    uses router-snmp-grouping;
    list summary-address {
      description
        "Configure IP address summaries";
      tailf:cli-suppress-mode;
      tailf:cli-delete-when-empty;
      key "ip mask";
      leaf ip {
        type inet:ipv4-address;
      }
      leaf mask {
        type inet:ipv4-address;
      }
      container level-1 {
        description
          "Summarize into level-1 area";
        presence "Summarize into level-1 area";
        tailf:cli-compact-syntax;
        uses summary-address-metric-tag-grouping;
      }
      container level-1-2 {
        description
          "Summarize into both area and sub-domain";
        presence "Summarize into both area and sub-domain";
        tailf:cli-compact-syntax;
        uses summary-address-metric-tag-grouping;
      }
      container level-2 {
        description
          "Summarize into level-2 sub-domain";
        presence "Summarize into level-2 sub-domain";
        tailf:cli-compact-syntax;
        uses summary-address-metric-tag-grouping;
      }
      container metric-tag-container {
        tailf:cli-drop-node-name;
        tailf:cli-compact-syntax;
        uses summary-address-metric-tag-grouping;
      }
    }
    container traffic-share {
      description
        "How to compute traffic share over alternate paths";
      container min {
        description
          "All traffic shared among min metric paths";
        leaf across-interfaces {
          description
            "Use different interfaces for equal-cost paths";
          type empty;
        }
      }
    }
    uses isis-common-grouping;
  }

  grouping isis-af-ipv4-grouping {
    leaf help {
      description
        "Description of the interactive help system";
      tailf:cli-full-command;
      type empty;
    }
    uses router-snmp-grouping;
    list topology {
      description
        "Associate the routing protocol to a topology instance";
      tailf:cli-mode-name "config-router-af-topology";
      tailf:cli-exit-command "exit-router-topology";
      key "name";
      leaf name {
        type string;
      }
      leaf tid {
        description
          "Configuring the routing protocol topology tid";
        tailf:cli-hide-in-submode;
        type uint32 {
          range "5..4095";
        }
      }
      leaf ignore-attached-bit {
        description
          "Never install default route to closest L2 router";
        tailf:cli-full-command;
        type empty;
      }
      uses isis-topology-grouping;
    }
  }

  grouping isis-main-grouping {
    container metric-style {
      description
        "Use old-style (ISO 10589) or new-style packet formats";
      choice metric-style-choice {
        container narrow {
          description
            "Use old style of TLVs with narrow metric";
          presence "true";
          uses narrow-wide-transition-grouping;
        }
        container transition {
          description
            "Send and accept both styles of TLVs during transition";
          presence "true";
          leaf transition {
            type isis-level-type;
            tailf:cli-drop-node-name;
          }
        }
        container wide {
          description
            "Use new style of TLVs to carry wider metric";
          presence "true";
          uses narrow-wide-transition-grouping;
        }
      }
    }
    container address-family {
      description
        "Enter Address Family command mode";
      container ipv4 {
        description
          "Address family";
        tailf:cli-add-mode;
        tailf:cli-mode-name "config-router-af";
        tailf:cli-exit-command "exit-address-family";
        leaf unicast-multicast {
          tailf:cli-drop-node-name;
          tailf:cli-hide-in-submode;
          type enumeration {
            enum "unicast";
            enum "multicast";
          }
        }
        uses isis-af-ipv4-grouping;
      }
      container ipv6 {
        description
          "Address family";
        tailf:cli-add-mode;
        tailf:cli-mode-name "config-router-af";
        tailf:cli-exit-command "exit-address-family";
        leaf unicast {
          tailf:cli-hide-in-submode;
          type empty;
        }
        uses isis-address-family-grouping;
      }
    }
    uses isis-topology-grouping;
    container area-password {
      description
        "Configure the authentication password for an area";
      tailf:cli-sequence-commands;
      tailf:cli-compact-syntax;
      leaf name {
        tailf:cli-drop-node-name;
        type string;
      }
      uses authenticate-snp-grouping;
    }
    container authentication {
      description
        "ISIS authentication for LSPs";
      uses isis-authentication-grouping;
    }
    container distribute-list {
      description
        "Filter networks in routing updates";
      tailf:cli-compact-syntax;
      tailf:cli-sequence-commands;
      choice distribute-list-choice {
        case acl-case {
          leaf acl-name {
            tailf:cli-drop-node-name;
            tailf:cli-no-value-on-delete;
            type access-list-standard-id-type;
          }
          leaf in {
            description
              "Filter incoming routing updates";
            type string;
          }
        }
        case gateway-prefix-case {
          leaf gateway {
            description
              "Filtering incoming updates based on gateway";
            tailf:cli-optional-in-sequence;
            type string;
          }
          leaf prefix {
            description
              "Filter prefixes in routing updates";
            tailf:cli-optional-in-sequence;
            type string;
          }
          leaf gateway-prefix-in {
            tailf:alt-name "in";
            description
              "Filter incoming routing updates";
            type string;
          }
        }
        case route-map-case {
          leaf route-map {
            description
              "Filter prefixes based on the route-map";
            type string;
          }
          leaf route-map-in {
            tailf:alt-name "in";
            description
              "Filter incoming routing updates";
            type empty;
          }
        }
      }
    }
    container domain-password {
      description
        "Set the authentication password for a routing domain";
      tailf:cli-sequence-commands;
      tailf:cli-compact-syntax;
      leaf name {
        tailf:cli-drop-node-name;
        type string;
      }
      uses authenticate-snp-grouping;
    }
    container fast-flood {
      description
        "Flood LSPs (that triggered SPF) before running SPF";
      presence "Flood LSPs (that triggered SPF) before running SPF";
      leaf number {
        tailf:cli-drop-node-name;
        type uint32 {
          range "1 .. 15";
        }
      }
    }
    container fast-reroute {
      description
        "Configure Fast-Reroute";
      container load-sharing {
        description
          "Distributes repair paths equally among links and prefixes";
        container level-1 {
          description
            "Apply to level-1";
          presence "true";
          leaf disable {
            description
              "Disable load-sharing";
            type empty;
          }
        }
        container level-2 {
          description
            "Apply to level-2";
          presence "true";
          leaf disable {
            description
              "Disable load-sharing";
            type empty;
          }
        }
      }
      container per-prefix {
        description
          "Enable Fast-Reroute Per-Prefix";
        container level-1 {
          description
            "Apply to level-1";
          leaf all {
            description
              "Enable Fast-Reroute for primary paths";
            type empty;
          }
          leaf route-map {
            description
              "route-map name";
            type string;
          }
        }
        container level-2 {
          description
            "Apply to level-2";
          leaf all {
            description
              "Enable Fast-Reroute for primary paths";
            type empty;
          }
          leaf route-map {
            description
              "route-map name";
            type string;
          }
        }
      }
      container remote-lfa {
        description
          "Configuring fast-reroute remote-lfa";
        container level-1 {
          description
            "Apply to level-1";
          container mpls-ldp {
            description
              "Use mpls-ldp tunnel type";
            presence "true";
            container maximum-metric {
              description
                "maximum metric to reach release node";
              presence "true";
              leaf max-met {
                description
                  "metric value";
                tailf:cli-drop-node-name;
                type uint32 {
                  range "1..4294967295";
                }
              }
            }
          }
        }
        container level-2 {
          description
            "Apply to level-2";
          container mpls-ldp {
            description
              "Use mpls-ldp tunnel type";
            presence "true";
            container maximum-metric {
              description
                "maximum metric to reach release node";
              presence "true";
              leaf max-met {
                description
                  "metric value";
                tailf:cli-drop-node-name;
                type uint32 {
                  range "1..4294967295";
                }
              }
            }
          }
        }
      }
      container tie-break {
        description
          "Set repair path preference";
        container level-1 {
          description
            "Apply to level-1";
          uses tie-break-prefer-repair-grouping;
        }
        container level-2 {
          description
            "Apply to level-2";
          uses tie-break-prefer-repair-grouping;
        }
      }
    }
    container hello {
      description
        "Pad ISIS hello PDUs to full MTU";
      container padding {
        description
          "Pad hello PDU";
        presence "Pad hello PDU";
        leaf pad-type {
          tailf:cli-drop-node-name;
          type enumeration {
            enum "multi-point";
            enum "point-to-point";
          }
        }
      }
    }
    container hostname {
      description
        "Dynamic hostname for IS-IS";
      leaf dynamic {
        description
          "Dynamic hostname";
        type empty;
      }
    }
    leaf ignore-lsp-errors {
      description
        "Ignore LSPs with bad checksums";
      tailf:cli-full-command;
      type empty;
    }
    leaf is-type {
      description
        "IS Level for this routing process (OSI only)";
      tailf:cli-full-command;
      type enumeration {
        enum "level-1";
        enum "level-1-2";
        enum "level-2-only";
      }
    }
    container ispf {
      description
        "Configure execution of incremental SPF";
      tailf:cli-compact-syntax;
      tailf:cli-sequence-commands;
      leaf level {
        tailf:cli-drop-node-name;
        type enumeration {
          enum "level-1";
          enum "level-1-2";
          enum "level-2";
        }
      }
      leaf number {
        tailf:cli-drop-node-name;
        type uint32 {
          range "1 .. 600";
        }
      }
    }
    container log-adjacency-changes {
      description
        "Log changes in adjacency state";
      presence "Log changes in adjacency state";
      leaf all {
        description
          "Include changes generated by non-IIH event";
        type empty;
      }
    }
    container lsp-full {
      description
        "If we run out of LSP fragments";
      container suppress {
        description
          "suppress the following types of IP prefixes";
        choice lsp-full-choince {
          container external-interlevel-container {
            tailf:cli-drop-node-name;
            tailf:cli-compact-syntax;
            leaf external {
              description
                "don't advertise IP prefixes learned from other protocols";
              type empty;
            }
            leaf interlevel {
              description
                "don't advertise IP prefixes learned from another ISIS level";
              type empty;
            }
          }
          leaf none {
            description
              "don't suppress any prefixes";
            type empty;
          }
        }
      }
    }
    container lsp-gen-interval {
      description
        "Minimum interval between regenerating same LSP";
      choice lsp-gen-interval-choice {
        container intervals {
          tailf:cli-drop-node-name;
          tailf:cli-compact-syntax;
          tailf:cli-sequence-commands;
          uses lsp-gen-interval-grouping;
        }
        container intervals-levels {
          tailf:cli-drop-node-name;
          container intervals-level-1 {
            tailf:cli-drop-node-name;
            tailf:cli-compact-syntax;
            tailf:cli-sequence-commands;
            leaf level-1 {
              description
                "Set interval for level 1 only";
              type empty;
            }
            uses lsp-gen-interval-grouping;
          }
          container intervals-level-2 {
            tailf:cli-drop-node-name;
            tailf:cli-compact-syntax;
            tailf:cli-sequence-commands;
            leaf level-2 {
              description
                "Set interval for level 2 only";
              type empty;
            }
            uses lsp-gen-interval-grouping;
          }
        }
      }
    }
    leaf lsp-mtu {
      description
        "Set maximum LSP size";
      tailf:cli-full-command;
      type uint32 {
        range "128 .. 4352";
      }
    }
    leaf lsp-refresh-interval {
      description
        "Set LSP refresh interval";
      tailf:cli-full-command;
      type uint32 {
        range "1 .. 65535";
      }
    }
    leaf max-area-addresses {
      description
        "Allow configuration of more manual area addresses";
      tailf:cli-full-command;
      type uint32 {
        range "3 .. 254";
      }
    }
    leaf max-lsp-lifetime {
      description
        "Set maximum LSP lifetime";
      tailf:cli-full-command;
      type uint32 {
        range "1 .. 65535";
      }
    }
    container microloop {
      description
        "Enable microloop protection configuration commands";
      container avoidance {
        description
          "Enable local microloop avoidance";
        presence "true";
        leaf disable {
          description
            "Disable Microloop avoidance";
          type empty;
        }
        leaf protected {
          description
            "Microloop avoidance for protected link or prefix only";
          type empty;
        }
        leaf rib-update-delay {
          description
            "Value of the delay in milliseconds";
          type uint32 {
            range "1..600000";
          }
        }
      }
    }
    container mpls {
      description
        "Configure MPLS routing protocol parameters";
      container ldp {
        description
          "routing protocol commands for MPLS LDP";
        container autoconfig {
          description
            "Configure LDP automatic configuration";
          presence "true";
          leaf level-1 {
            description
              "Configure ISIS level-1 to run MPLS LDP";
            type empty;
          }
          leaf level-2 {
            description
              "Configure ISIS level-2 to run MPLS LDP";
            type empty;
          }
        }
        leaf sync {
          description
            "Configure LDP-IGP Synchronization";
          type empty;
        }
        leaf sync-igp-shortcuts {
          description
            "Configure LDP-IGP Synchronization on MPLS shortcuts";
          type empty;
        }
      }
      container traffic-eng {
        description
          "routing protocol commands for MPLS Traffic Engineering";
        leaf level-1 {
          description
            "Run MPLS TE on IS-IS level 1 only";
          tailf:cli-full-command;
          type empty;
        }
        leaf level-2 {
          description
            "Run MPLS TE on IS-IS level 2 only";
          tailf:cli-full-command;
          type empty;
        }
        leaf multicast-intact {
          description
            "MPLS TE and PIM interaction";
          tailf:cli-full-command;
          type empty;
        }
        container router-id {
          description
            "Traffic Engineering stable IP address for system";
          tailf:cli-diff-dependency "/ios:native/interface";
          uses interface-grouping;
        }
        container scanner {
          description
            "Timer parameters for TE database";
          presence "Timer parameters for TE database";
          tailf:cli-compact-syntax;
          leaf interval {
            description
              "time (secs) between LSPDB walks for TE";
            type uint32 {
              range "1 .. 60";
            }
          }
          leaf max-flash {
            description
              "Number of ISIS LSPs to be processed with no delay";
            type uint32 {
              range "0 .. 200";
            }
          }
        }
      }
    }
    list net {
      description
        "A Network Entity Title for this process (OSI only)";
      tailf:cli-suppress-mode;
      tailf:cli-delete-when-empty;
      key "tag";
      leaf tag {
        type isis-net;
      }
    }
    container nsf {
      description
        "Non-stop forwarding";
      leaf cisco {
        description
          "Checkpoint method";
        type empty;
      }
      leaf ietf {
        description
          "IETF method";
        type empty;
      }
      container interface {
        description
          "Interface properties";
        leaf wait {
          description
            "Seconds";
          type uint8 {
            range "1..60";
          }
        }
      }
      leaf interval {
        description
          "Minutes";
        type uint16 {
          range "0..1440";
        }
      }
    }
    container partition {
      description
        "CLNS area partition";
      leaf avoidance {
        description
          "Withdraw area prefix if partition detected";
        type empty;
      }
    }
    uses passive-interface-grouping;
    container protocol {
      description
        "Set protocol's administrative state";
      leaf shutdown {
        description
          "Set protocol's administrative state to disable";
        type empty;
      }
    }
    container segment-routing {
      description
        "Enable Segment Routing Feature";
      leaf mpls {
        description
          "Enable Segment Routing Feature using MPLS encapsulation";
        type empty;
      }
      container prefix-sid-map {
        description
          "Enable prefix-sid-map";
        leaf advertise-local {
          description
            "Advertise active local prefix-SID mappings";
          type empty;
        }
        container receive {
          description
            "Enable prefix-SID mapping client";
          presence "true";
          leaf disable {
            description
              "Disable prefix-SID mapping";
            type empty;
          }
        }
      }
    }
    container skeptical {
      description
        "Be a cautious NSF helper when refresh adjacency";
      leaf interval {
        description
          "Minutes";
        type uint16 {
          range "0..1440";
        }
      }
    }
    leaf update-queue-depth {
      description
        "Set Update process queue depth";
      type uint32 {
        range "1 .. 2147483647";
      }
    }
    container use {
      description
        "Use different algorithms during SPF";
      leaf external-metrics {
        description
          "Honour external metrics during SPF";
        type empty;
      }
    }
    leaf vrf {
      description
        "VRF name for this process";
      type string;
    }
    uses isis-ipv4-ipv6-common-grouping;
  }

  grouping interface-switch-grouping {
    // this should probably only be a part of Catalyst
    // device models.
    container auto {
      description "Configure Automation";
      container qos {
        description "Configure AutoQoS";
        container video {
          description "Configure AutoQoS for video devices";
          leaf cts {
            description "Trust the QoS marking of the Cisco Telepresence System";
            type empty;
          }
          leaf ip-camera {
            description "Trust the QoS marking of the Ip Video Surveillance camera";
            type empty;
          }
          leaf media-player {
            description "Trust the Qos marking of the Cisco Media Player";
            type empty;
          }
        }
        container voip {
          description "Configure AutoQoS for VoIP";
          leaf cisco-phone {
            description "Trust the QoS marking of Cisco IP Phone";
            type empty;
          }
          leaf cisco-softphone {
            description "Trust the QoS marking of Cisco IP SoftPhone";
            type empty;
          }
        }
        leaf trust {
          description
            "Trust the DSCP/CoS marking";
          type empty;
        }
      }
    }
    container datalink {
      description "Interface Datalink commands";
      container flow {
        description "Interface Flow configuration subcommands";
        container monitor {
          description "Apply a Flow Monitor";
          presence true;
          tailf:cli-compact-syntax;
          leaf User-defined-flow {
            description "User defined";
            tailf:cli-drop-node-name;
            type string;
          }
          leaf input-output {
            description "Apply Flow Monitor on input/output traffic";
            tailf:cli-drop-node-name;
            type enumeration{
              enum "input";
              enum "output";
            }
          }          
        }
      }
    }
    container energywise {
      description 
        "EnergyWise interface configurations";
      presence true;
      leaf activitycheck {
	description 
	  "Apply an activity check before turning off power to this PoE port";
        type empty;	 
      } 
    }
    container location {
      description "Interface location information";
      container civic-location-id {
        description "Civic location information";
        leaf  location-identifier{
          description "civic location identifier string";
          tailf:cli-drop-node-name;
          type string;
        }
        container host {
          description "Globally defined host location identifer";
          presence true;
          leaf port-location {
            description "Port specific attributes";
            type string;
          }
        }
        container none {
          description "No globally defined location identifer";
          presence true;
          leaf port-location {
            description "Port specific attributes";
            type string;
          }
        }
      }
    }
    container mac {
      description "MAC interface commands";
      container access-group {
        description "MAC access-group configuration commands";
        container ACL-name {
          description "ACL name";
          tailf:cli-drop-node-name;
          tailf:cli-compact-syntax;
          leaf acl-name{
            tailf:cli-drop-node-name;
            type string;
          }
          leaf apply-to{
            tailf:cli-drop-node-name;
            type enumeration{
              enum "in";
              enum "out";
            }
          }
        }
      }
    }
    container macro {
      description "Command macro";
      leaf description {
        description "Macro description for this interface";
          type string;
      }
      container auto {
        description "Smartport interface macro configurations";
        leaf processing {
          description "Enable smartport macro auto execution on this interface";
          tailf:cli-boolean-no;
          type boolean;
        }
      }
    }
    // interface * / macsec
    container macsec {
      description
        "Enable macsec on the interface";
      presence "true";
      leaf network-link {
        description 
          "Enable macsec on switch connected interface";
        type empty;
      }
    }
    // interface * / mka
    container mka {
      description
        "MACsec Key Agreement (MKA) interface configuration";
      container pre-shared-key {
        description
          "Configure MKA Pre-Shared-Key";
        container key-chain {
          description
            "Configure the key-chain name";
          leaf name {
            description
              "Name of key-chain to be used to get keys";
            tailf:cli-drop-node-name;
            type string;
          }
        }
      }
    }
    // interface * / dual-active
    container dual-active {
      leaf fast-hello {
        type empty;
      }
    }
    // interface * / lldp
    container lldp {
      description
        "LLDP interface subcommands";
      leaf receive {
        description
          "Enable LLDP reception on interface";
        tailf:cli-boolean-no;
        tailf:cli-trim-default;
        type boolean;
      }
      leaf transmit {
        description
          "Enable LLDP transmission on interface";
        tailf:cli-boolean-no;
        tailf:cli-trim-default;
        type boolean;
      }
    }
    // interface * / load-balancing
    container load-balancing {
      description
        "Etherchannel Load-Balancing";
      leaf flow {
        description
          "Based on the traffic flows identified by the packet headers";
        tailf:cli-full-command;
        type empty;
      }
      leaf vlan {
        description
          "Based on the VLAN to member links manual configuration";
        tailf:cli-full-command;
        type empty;
      }
    }
    // interface * / vlan-range
    list vlan-range {
      key "id";
      leaf id {
        type union {
          type uint16 {
            range "1..4096";
          }
          type string;
        }
      }
      container service-policy {
        description
          "Configure QoS Service Policy";
        leaf input {
          tailf:cli-full-command;
          description
            "Assign policy-map to the input of an interface";
          type string;
          tailf:non-strict-leafref {
            path "/ios:native/policy-map/name";
          }
        }
        leaf output {
          tailf:cli-full-command;
          description
            "Assign policy-map to the output of an interface";
          type string;
          tailf:non-strict-leafref {
            path "/ios:native/policy-map/name";
          }
        }
      }
    }
    // interface * / switch
    container switch {
      container virtual {
        leaf link {
          type uint8;
        }
      }
    }
    // interface * / no switchport
    container switchport-conf {
      tailf:cli-no-keyword;
      tailf:cli-drop-node-name;
      leaf switchport {
        tailf:cli-boolean-no;
        type boolean;
      }
    }
    // interface * / switchport
    container switchport {
      description
        "Set switching mode characteristics";
      tailf:cli-display-separated;
      tailf:cli-incomplete-no;
      // interface * / switchport access
      container access {
        description
          "Set access mode characteristics of the interface";
        container vlan {
          description
            "Set VLAN when interface is in access mode";
          leaf vlan {
            tailf:cli-diff-dependency "/ios:native/vlan/vlan-list/id";
            tailf:cli-drop-node-name;
            type union {
              type uint16 {
                range "1..4094";
              }
              type enumeration {
                enum "dynamic";
              }
            }
          }
          leaf name {
            description
              "Vlan name";
            type string;
          }
        }
      }
      //  backup         Set backup for the interface
      // interface * / switchport block
      container block {
        description
          "Disable forwarding of unknown uni/multi cast addresses";
        leaf multicast {
          description
            "Block unknown multicast addresses";
          tailf:cli-full-command;
          type empty;
        }
        leaf unicast {
          tailf:cli-full-command;
          description
            "Block unknown unicast addresses";
          type empty;
        }
      }
      //  dot1q          Set interface dot1q properties

      // interface * / switchport mode
      container mode {
        description
          "Set trunking mode of the interface";
        choice mode-choice {
          container access {
            presence "true";
            description
              "Set trunking mode to ACCESS unconditionally";
          }
          container dot1q-tunnel {
            presence "true";
            description
              "set trunking mode to TUNNEL unconditionally";
          }
          leaf dynamic {
            description
              "Set trunking mode to dynamically negotiate access or trunk mode";
            type enumeration {
              enum "auto";
              enum "desirable";
            }
          }
          container private-vlan {
            description
              "Set private-vlan mode";
            leaf host {
              description
                "Set the mode to private-vlan host";
              type empty;
            }
            leaf promiscuous {
              description
                "Set the mode to private-vlan promiscuous";
              type empty;
            }
          }
          container trunk {
            presence "true";
            description
              "Set trunking mode to TRUNK unconditionally";
          }
        }
      }
      // interface * / switchport nonegotiate
      leaf nonegotiate {
        description
          "Device will not engage in negotiation protocol on this interface";
        type empty;
      }
      // interface * / switchport port-security
      container port-security {
        description
          "Security related command";
        presence "true";
        tailf:cli-display-separated;
        container aging {
          description
            "Port-security aging commands";
          leaf static {
            description
              "Enable aging for configured secure addresses";
            type empty;
          }
          leaf time {
            description
              "Port-security aging time";
            type uint16 {
              range "1..1440";
            }
          }
          leaf type {
            description
              "Port-security aging type";
            type enumeration {
              enum "absolute";
              enum "inactivity";
            }
          }
        }
        container mac-address {
          description
            "Secure mac address";
          tailf:cli-sequence-commands {
            tailf:cli-reset-siblings;
          }
          tailf:cli-compact-syntax;
          leaf sticky {
            description
              "Configure dynamic secure addresses as sticky";
            tailf:cli-optional-in-sequence;
            type empty;
          }
          leaf hw-address {
            tailf:cli-drop-node-name;
            type cisco-mac-address-type;
          }
          leaf vlan {
            description
              "set VLAN ID of the VLAN on which this address can be learned";
            type uint16 {
              range "1..4094";
            }
          }
        }
        container maximum {
          description
            "Max secure addresses";
          tailf:cli-sequence-commands {
            tailf:cli-reset-siblings;
          }
          tailf:cli-compact-syntax;
          leaf max-addresses {
            tailf:cli-drop-node-name;
            type uint16 {
              range "1..4097";
            }
          }
          leaf vlan {
            description
              "Max secure addresses per vlan";
            type string;
          }
        }
        leaf violation {
          description
            "Security violation mode";
          type enumeration {
            enum "protect";
            enum "restrict";
            enum "shutdown";
          }
        }
      }
      // interface * / switchport trunk
      container trunk {
        description
          "Set trunking characteristics of the interface";
          // interface * / switchport trunk allowed
        container allowed {
          description
            "Set allowed VLAN characteristics when interface is in trunking mode";
            // interface * / switchport trunk allowed vlan
          container vlan {
            description
              "Set allowed VLANs when interface is in trunking mode";
            choice vlan-choice {
              leaf vlans {
                tailf:cli-drop-node-name;
                type string;
              }
              leaf add {
                description
                  "VLAN IDs of the allowed VLANs when this port is in trunking mode";
                type union {
                  type uint16;
                  type string;
                }
              }
              leaf all {
                description
                  "all VLANs";
                type empty;
              }
              leaf-list except {
                description
                  "all VLANs except the following";
                tailf:cli-range-list-syntax;
                type union {
                  type uint16;
                  type string;
                }
              }
              leaf none {
                description
                  "no VLANs";
                type empty;
              }
              leaf remove {
                description
                  "VLAN IDs of disallowed VLANS when this port is in trunking mode";
                type union {
                  type uint16;
                  type string;
                }
              }
            }
          }
        }
        // interface * / switchport trunk encapsulation
        leaf encapsulation {
          description
            "Set encapsulation format on trunk port";
          type enumeration {
            enum "dot1q";
            enum "isl";
            enum "negotiate";
          }
        }
        // interface * / switchport trunk native
        container native {
          description
            "Set trunking native characteristics when interface is in trunking mode";
          leaf vlan {
            description
              "Set native VLAN when interface is in trunking mode";
            type union {
              type enumeration {
                enum "tag";
              }
              type uint16 {
                range "1..4094";
              }
            }
          }
        }
        // interface * / switchport trunk pruning
        container pruning {
          description
            "Set pruning VLAN characteristics when interface is in trunking mode";
          container vlan {
            description
              "Set VLANs enabled for pruning when interface is in trunking mode";
            choice vlan-choice {
              leaf-list vlans {
                tailf:cli-range-list-syntax;
                tailf:cli-drop-node-name;
                type union {
                  type uint16;
                  type string;
                }
              }
              leaf add {
                description
                  "VLAN IDs of the allowed VLANs when this port is in trunking mode";
                type union {
                  type uint16;
                  type string;
                }
              }
              leaf-list except {
                description
                  "all VLANs except the following";
                tailf:cli-range-list-syntax;
                type union {
                  type uint16;
                  type string;
                }
              }
              leaf none {
                description
                  "no VLANs";
                type empty;
              }
              leaf remove {
                description
                  "VLAN IDs of disallowed VLANS when this port is in trunking mode";
                type union {
                  type uint16;
                  type string;
                }
              }
            }
          }
        }
      }
      // interface * / switchport voice
      container voice {
        description
          "Voice appliance attributes";
        container vlan {
          description
            "Vlan for voice traffic";
          leaf vlan {
            tailf:cli-drop-node-name;
            type union {
              type enumeration {
                enum "dot1p";
                enum "none";
                enum "untagged";
              }
              type uint16 {
                range "1..4094";
              }
              type string;
            }
          }
          leaf name {
            description
              "Vlan name";
            type string;
          }
        }
        container detect {
          description
            "detection enhancement keyword";
          tailf:cli-incomplete-command;
          container cisco-phone {
            description
              "Cisco IP phone";
            presence "true";
            leaf full-duplex {
              description
                "full duplex keyword";
              type empty;
            }
          }
        }
      }
      // interface * / switchport priority
      container priority {
        description
          "Set appliance 802.1p priority";
        tailf:cli-incomplete-command;
        container extend {
          description
            "Set appliance 802.1p priority";
          tailf:cli-incomplete-command;
          choice trust-choice {
            leaf trust {
              tailf:cli-full-command;
              description
                "Trust 802.1p priorities of devices on appliance";
              type empty;
            }
            leaf cos {
              description
                "Override 802.1p priority of devices on appliance";
              tailf:cli-full-command;
              type uint8 {
                range "0..7";
              }
            }
          }
        }
      }
      // interface * / switchport autostate
      container autostate {
        description
          "Include or exclude this port from vlan link up calculation";
        tailf:cli-incomplete-command;
        leaf exclude {
          description
            "Exclude this port from vlan link up calculation";
          type empty;
        }
      }
      // interface * / switchport protected
      leaf protected {
        description
          "Configure an interface to be a protected port";
        type empty;
      }
      // interface * / switchport host
      leaf host {
        description
          "Set port host";
        type empty;
      }
      //interface * /switchport private-vlan
      container private-vlan {
        description
          "Set the private VLAN configuration";
        container association {
          description
            "Set the private VLAN association";
          container host {
            description
              "Set the private VLAN host association";
            tailf:cli-sequence-commands;
            tailf:cli-compact-syntax;
            leaf primary-range {
              description
                "Primary normal range VLAN ID of the private VLAN port association";
              tailf:cli-drop-node-name;
              type uint16 {
                range "2..1001 | 1006..4094";
              }
            }
            leaf secondary-range {
              description
                "Secondary normal range VLAN ID of the private VLAN host port association";
              tailf:cli-drop-node-name;
              type uint16 {
                range "2..1001 | 1006..4094";
              }
            }
          }
          container mapping {
            description
              "Set the private VLAN promiscuous mapping";
            tailf:cli-sequence-commands;
            tailf:cli-compact-syntax;
            leaf primary-range {
              description
                "Primary normal range VLAN ID of the private VLAN promiscuous port mapping";
              tailf:cli-drop-node-name;
              type uint16 {
                range "2..1001 | 1006..4094";
              }
            }
            leaf secondary-range {
              description
                "Secondary VLAN IDs of the private VLAN promiscuous port mapping";
              tailf:cli-drop-node-name;
              type string;
            }
            leaf add {
              description
                "Secondary VLAN IDs of the private VLAN promiscuous port mapping";
              tailf:cli-optional-in-sequence;
              type string;
            }
            leaf remove {
              description
                "Secondary VLAN IDs of the private VLAN promiscuous port mapping";
              tailf:cli-optional-in-sequence;
              type string;
            }
          }
        }
        container host-association {
          description
            "Set the private VLAN host association";
          tailf:cli-sequence-commands;
          tailf:cli-compact-syntax;
          leaf primary-range {
            description
              "Primary normal range VLAN ID of the private VLAN port association";
            tailf:cli-drop-node-name;
            type uint16 {
              range "2..1001 | 1006..4094";
            }
          }
          leaf secondary-range {
            description
              "Secondary normal range VLAN ID of the private VLAN host port association";
            tailf:cli-drop-node-name;
            type uint16 {
              range "2..1001 | 1006..4094";
            }
          }
        }
        container mapping {
          description
            "Set the private VLAN promiscuous mapping";
          tailf:cli-sequence-commands;
          tailf:cli-compact-syntax;
          leaf primary-range {
            description
              "Primary normal range VLAN ID of the private VLAN promiscuous port mapping";
            tailf:cli-drop-node-name;
            type uint16 {
              range "2..1001 | 1006..4094";
            }
          }
          leaf secondary-range {
            description
              "Secondary VLAN IDs of the private VLAN promiscuous port mapping";
            tailf:cli-drop-node-name;
            type string;
          }
          leaf add {
            description
              "Secondary VLAN IDs of the private VLAN promiscuous port mapping";
            tailf:cli-optional-in-sequence;
            type string;
          }
          leaf remove {
            description
              "Secondary VLAN IDs of the private VLAN promiscuous port mapping";
            tailf:cli-optional-in-sequence;
            type string;
          }
        }
      }
    }
    // interface * / authentication
    // NOTE: Called 'dot1x' on some versions
    container authentication {
      description
        "Auth Manager Interface Configuration Commands";
      leaf control-direction {
        description
          "Set the control-direction on the interface";
        type enumeration {
          enum "both";
          enum "in";
        }
      }
      container event {
        description
          "Set action for authentication events";
        container server {
          description
            "Configure actions for AAA server events";
          container alive {
            description
              "Configure AAA server alive action";
            container action {
              description
                "Required action for authentication event";
              leaf reinitialize {
                description
                  "Reinitialize all authorized clients";
                type empty;
              }
            }
          }
          container dead {
            description
              "Configure AAA server dead action";
            container action {
              description
                "Required action for authentication event";
              container authorize {
                description
                  "Authorize the port";
                presence "true";
                leaf vlan {
                  description
                    "Configure Critical Authorization VLAN";
                  tailf:cli-full-command;
                  type uint16;
                }
                leaf voice {
                  description
                    "Authorize the port for VOICE traffic";
                  tailf:cli-full-command;
                  type empty;
                }
              }
              container reinitialize {
                description
                  "Reinitialize all client on the port";
                leaf vlan {
                  description
                    "Configure Critical Authorization VLAN";
                  type uint16;
                }
              }
            }
          }
        }
        container fail {
          description
            "Configure actions for AAA fail events";
          container action {
            description
              "Required action for fail event";
            container authorize {
              description
                "Reinitialize all authorized clients";
              leaf vlan {
                type uint16;
              }
            }
          }
        }
        container no-response {
          description
            "Configure actions for AAA no-response events";
          container action {
            description
              "Required action for no-response event";
            container authorize {
              description
                "Reinitialize all authorized clients";
              leaf vlan {
                type uint16;
              }
            }
          }
        }
      }
      leaf fallback {
        description
          "Enable the Webauth fallback mechanism";
        tailf:cli-full-command;
        type string;
      }
      leaf host-mode {
        description
          "Set the Host mode for authentication on this interface";
        type enumeration {
          enum "multi-auth";
          enum "multi-domain";
          enum "multi-host";
          enum "single-host";
        }
      }
      leaf open {
        description
          "Enable or Disable open access on this port";
        tailf:cli-full-command;
        type empty;
      }
      container order {
        description
          "Add an authentication method to the order list";
        tailf:cli-compact-syntax;
        leaf dot1x {
          description
            "Authentication method dot1x allowed";
          type empty;
        }
        leaf mab {
          description
            "Authentication method mab allowed";
          type empty;
        }
        leaf webauth {
          description
            "Authentication method webauth allowed";
          type empty;
        }
      }
      container priority {
        description
          "Add an authentication method to the priority list";
        tailf:cli-compact-syntax;
        leaf dot1x {
          description
            "Authentication method dot1x allowed";
          type empty;
        }
        leaf mab {
          description
            "Authentication method mab allowed";
          type empty;
        }
        leaf webauth {
          description
            "Authentication method webauth allowed";
          type empty;
        }
      }
      leaf port-control {
        description
          "set the port-control value";
        type enumeration {
          enum "auto";
          enum "force-authorized";
          enum "force-unauthorized";
        }
      }
      leaf periodic {
        description
          "Enable or Disable Reauthentication for this port";
        tailf:cli-full-command;
        type empty;
      }
      container timer {
        description
          "Set authentication timer values";
        container inactivity {
          description
            "Interval in seconds after which if there is no activity fromthe client then it will be unauthorized (default OFF)";
          container value {
            tailf:cli-drop-node-name;
            tailf:cli-sequence-commands;
            tailf:cli-compact-syntax;
            leaf value {
              tailf:cli-drop-node-name;
              type uint16;
            }
            leaf dynamic {
              description
                "Initiate a dynamic probe on inactivity timeout";
              tailf:cli-optional-in-sequence;
              type empty;
            }
          }
          container server {
            description
              "Obtain inactivity timeout value from the server";
            presence "true";
            leaf dynamic {
              description
                "Initiate a dynamic probe on inactivity timeout";
              tailf:cli-optional-in-sequence;
              type empty;
            }
          }
        }
        container reauthenticate {
          description
            "Time in seconds after which an automatic re-authenticationshould be initiated (default 1 hour)";
          leaf value {
            tailf:cli-drop-node-name;
            tailf:cli-full-command;
            type uint16;
          }
          leaf server {
            description
              "Obtain re-authentication timeout value from the server";
            tailf:cli-full-command;
            type empty;
          }
        }
        leaf restart {
          description
            "Interval in seconds after which an attempt should be made toauthenticate an unauthorized port (default 60 sec)";
          tailf:cli-full-command;
          type uint16;
        }
      }
      leaf violation {
        description
          "Configure action to take on security violations";
        tailf:cli-full-command;
        type enumeration {
          enum "protect";
          enum "replace";
          enum "restrict";
          enum "shutdown";
        }
      }
    }
    // interface * / dot1x
    container dot1x {
      description
        "Interface Config Commands for IEEE 802.1X";
      container authenticator {
        description
          "Configure authenticator parameters";
        container eap {
          description
            "Configure EAP authenticator parameters";
          leaf profile {
            description
              "EAP authenticator profile configuration";
            type string;
          }
        }
      }
      leaf credentials {
        description
          "Credentials profile configuration";
        tailf:cli-full-command;
        type string;
      }
      leaf max-reauth-req {
        description
          "Max No. of Reauthentication Attempts";
        tailf:cli-full-command;
        type uint8 {
          range "1..10";
        }
      }
      leaf max-req {
        description
          "Max No. of Retries";
        tailf:cli-full-command;
        type uint8 {
          range "1..10";
        }
      }
      leaf max-start {
        description
          "Max No. of EAPOL-Start requests";
        tailf:cli-full-command;
        type uint8 {
          range "1..10";
        }
      }
      leaf pae {
        description
          "Set 802.1x interface pae type";
        tailf:cli-full-command;
        type enumeration {
          enum "authenticator";
          enum "supplicant";
          enum "both";
        }
      }
      container supplicant {
        description
          "Configure supplicant parameters";
        container eap {
          description
            "Configure EAP supplicant parameters";
          leaf profile {
            description
              "EAP supplicant profile configuration";
            type string;
          }
        }
      }
      container timeout {
        description
          "Various Timeouts";
        leaf auth-period {
          description
            "Timeout for authenticator reply";
          tailf:cli-full-command;
          type uint16;
        }
        leaf held-period {
          description
            "Timeout for authentication retries";
          tailf:cli-full-command;
          type uint16;
        }
        leaf quiet-period {
          description
            "QuietPeriod in Seconds";
          tailf:cli-full-command;
          type uint16;
        }
        leaf ratelimit-period {
          description
            "Ratelimit Period in seconds";
          tailf:cli-full-command;
          type uint16;
        }
        leaf server-timeout {
          description
            "Timeout for Radius Retries";
          tailf:cli-full-command;
          type uint16;
        }
        leaf start-period {
          description
            "Timeout for EAPOL-start retries";
          tailf:cli-full-command;
          type uint16;
        }
        leaf supp-timeout {
          description
            "Timeout for supplicant reply";
          tailf:cli-full-command;
          type uint16;
        }
        leaf tx-period {
          description
            "Timeout for supplicant retries";
          tailf:cli-full-command;
          type uint16;
        }
      }
    }
    // no                      Negate a command or set its defaults
    // ntp                     Configure NTP
    // priority-group          Assign a priority group to an interface
    // random-detect     Enable Weighted Random Early Detection (WRED) on an
    //                         Interface
    // rate-limit              Rate Limit
    // rmon                    Configure Remote Monitoring on an interface
    // shutdown                Shutdown the selected interface
    // snapshot                Configure snapshot support on the interface
    // snmp                    Modify SNMP interface parameters

    // interface * / spanning-tree
    container spanning-tree {
      description
        "Spanning Tree Subsystem";
      leaf bpdufilter {
        description
          "Don't send or receive BPDUs on this interface";
        type enumeration {
          enum "disable";
          enum "enable";
        }
      }
      // interface * / spanning-tree bpduguard
      container bpduguard {
        description
          "Don't accept BPDUs on this interface";
        choice bpduguard-choice {
          leaf disable {
            description
              "Disable BPDU guard for this interface";
            type empty;
          }
          leaf enable {
            type empty;
            description
              "Enable BPDU guard for this interface";
          }
        }
      }
      // interface * / spanning-tree cost
      leaf cost {
        description
          "To set the path cost of the interface";
        tailf:cli-full-command;
        type uint32 {
          range "1..200000000";
        }
      }
      // interface * / spanning-tree guard
      leaf guard {
        description
          "Change an interface's spanning tree guard mode";
        tailf:cli-full-command;
        type enumeration {
          enum "loop";
          enum "none";
          enum "root";
        }
      }
      // interface * / spanning-tree link-type
      leaf link-type {
        description
          "Specify a link type for spanning tree tree protocol use";
        tailf:cli-full-command;
        type enumeration {
          enum "auto" {
            tailf:code-name "link_type_auto";
          }
          enum "none";
          enum "point-to-point";
          enum "root";
          enum "shared";
        }
      }
      // interface * / spanning-tree portfast
      container portfast {
        description
          "Spanning tree portfast options";
        tailf:cli-delete-when-empty;
        presence "true";
        leaf disable {
          description
            "Disable portfast for this interface";
          type empty;
        }
        leaf trunk {
          description
            "Enable portfast on the interface even in trunk mode";
          type empty;
        }
        leaf edge {
          description 
            "Enable portfast edge on the interface";
          type empty;    
        }
      }
      // interface * / spanning-tree port-priority
      leaf port-priority {
        description
          "Spanning tree port-priority options";
        tailf:cli-full-command;
        type uint8 {
          range "0..240";
        }
      }
      // interface * / spanning-tree vlan
      container vlan {
        description
          "VLAN Switch Spanning Tree";
        tailf:cli-sequence-commands;
        tailf:cli-compact-syntax;
        leaf-list vlan-ids {
          description
            "vlan range, example: 1,3-5,7,9-11";
          tailf:cli-drop-node-name;
          tailf:cli-range-list-syntax;
          type union {
            type uint16 {
              range "1..4095";
            }
            type string;
          }
        }
        leaf cost {
          description
            "<1-200000000> Spanning-tree cost";
          tailf:cli-optional-in-sequence;
          tailf:cli-full-command;
          type uint32 {
            range "1..200000000";
          }
        }
        leaf port-priority {
          description
            "<0-240> port priority in increments of 16";
          tailf:cli-optional-in-sequence;
          tailf:cli-full-command;
          type uint16 {
            range "0..240";
          }
        }
      }
      // interface * / spanning-tree loopguard default
      container loopguard {
        description
          "Spanning tree loopguard options";
        leaf default {
          description
            "Enable loopguard by default on all ports";
          type empty;
        }
      }
      // interface * /spanning-tree mst
      container mst {
        description
          "Per interface MST configurations";
        tailf:cli-sequence-commands;
        tailf:cli-compact-syntax;
        leaf instance {
          description
            "MST instance list, example 0,2-4,6,8-12";
          tailf:cli-drop-node-name;
          tailf:cli-optional-in-sequence;
          type string;
        }
        leaf cost {
          description
            "<1-200000000> Spanning-tree cost";
          tailf:cli-optional-in-sequence;
          tailf:cli-full-command;
          type uint32 {
            range "1..200000000";
          }
        }
        leaf port-priority {
          description
            "<0-240> port priority in increments of 16";
          tailf:cli-optional-in-sequence;
          tailf:cli-full-command;
          type uint16 {
            range "0..240";
          }
        }
        leaf pre-standard {
          description
            "Force pre-standard MST BPDU transmission on port";
          tailf:cli-optional-in-sequence;
          tailf:cli-full-command;
          type empty;
        }
      }
    }
    // interface * / srr-queue
    container srr-queue {
      container bandwidth {
        // interface * / srr-queue bandwidth shape
        container shape {
          tailf:cli-compact-syntax;
          tailf:cli-sequence-commands;
          tailf:cli-reset-container;
          leaf weight1 {
            tailf:cli-drop-node-name;
            tailf:cli-incomplete-command;
            type uint16;
          }
          leaf weight2 {
            tailf:cli-drop-node-name;
            tailf:cli-incomplete-command;
            type uint16;
          }
          leaf weight3 {
            tailf:cli-drop-node-name;
            tailf:cli-incomplete-command;
            type uint16;
          }
          leaf weight4 {
            tailf:cli-drop-node-name;
            type uint16;
          }
        }
        // interface * / srr-queue bandwidth share
        container share {
          tailf:cli-compact-syntax;
          tailf:cli-sequence-commands;
          tailf:cli-reset-container;
          leaf weight1 {
            tailf:cli-drop-node-name;
            tailf:cli-incomplete-command;
            type uint8 {
              range "1..255";
            }
          }
          leaf weight2 {
            tailf:cli-drop-node-name;
            tailf:cli-incomplete-command;
            type uint8 {
              range "1..255";
            }
          }
          leaf weight3 {
            tailf:cli-drop-node-name;
            tailf:cli-incomplete-command;
            type uint8 {
              range "1..255";
            }
          }
          leaf weight4 {
            tailf:cli-drop-node-name;
            type uint8 {
              range "1..255";
            }
          }
        }
      }
    }
  }

  grouping password-07-grouping {
    leaf level {
      description
        "Set exec level password";
      tailf:cli-optional-in-sequence;
      type uint8;
    }
    leaf type {
      tailf:cli-drop-node-name;
      tailf:cli-optional-in-sequence;
      type enumeration {
        enum "0";
        enum "7";
      }
    }
    leaf secret {
      tailf:cli-drop-node-name;
      type string;
    }
  }

  grouping aaa-authentication-dot1x-grouping {
    leaf group {
      description
        "Use Server-group";
      type union {
        type string;
        type enumeration {
          enum "radius";
          enum "tacacs+";
        }
      }
    }
  }

  grouping aaa-accounting-grouping {
    choice accounting-choice {
      leaf none {
        description
          "No accounting.";
        type empty;
      }
      container start-stop {
        description
          "Record start and stop without waiting";
        tailf:cli-compact-syntax;
        tailf:cli-sequence-commands;
        tailf:cli-reset-container;
        leaf broadcast {
          description
            "Use Broadcast for Accounting";
          tailf:cli-optional-in-sequence;
          type empty;
        }
        leaf group {
          description
            "Use Server-group";
          type union {
            type string;
            type enumeration {
              enum "radius";
              enum "tacacs+";
            }
          }
        }
      }
      container stop-only {
        description
          "Record stop when service terminates.";
        tailf:cli-compact-syntax;
        tailf:cli-sequence-commands;
        tailf:cli-reset-container;
        leaf broadcast {
          description
            "Use Broadcast for Accounting";
          tailf:cli-optional-in-sequence;
          type empty;
        }
        leaf group {
          description
            "Use Server-group";
          type union {
            type string;
            type enumeration {
              enum "radius";
              enum "tacacs+";
            }
          }
        }
      }
    }
  }

  grouping mpls-static-binding-ipv4-grouping {
    leaf label {
      tailf:cli-drop-node-name;
      tailf:cli-full-command;
      type uint32;
    }
    container input {
      description
        "Incoming (local) label";
      tailf:cli-flatten-container;
      tailf:cli-display-separated;
      leaf label {
        tailf:cli-drop-node-name;
        tailf:cli-full-command;
        type uint32;
      }
    }
    container output {
      description
        "Outgoing (remote) label";
      tailf:cli-sequence-commands {
        tailf:cli-reset-all-siblings;
      }
      tailf:cli-compact-syntax;
      tailf:cli-display-separated;
      leaf dst-next-hop {
        tailf:cli-drop-node-name;
        tailf:cli-incomplete-command;
        type inet:ipv4-address;
      }
      leaf label {
        tailf:cli-drop-node-name;
        tailf:cli-full-command;
        tailf:cli-break-sequence-commands;
        type union {
          type uint32;
          type enumeration {
            enum "explicit-null" {
              tailf:code-name "lbl_explicit_null";
            }
            enum "implicit-null" {
              tailf:code-name "lbl_implicit_null";
            }
          }
        }
      }
    }
  }

  grouping next-hop-address-grouping {
    container next-hop {
      description
        "Next hop along path";
      tailf:cli-flatten-container;
      leaf-list address {
        tailf:cli-drop-node-name;
        tailf:cli-flat-list-syntax;
        type inet:ipv4-address;
      }
    }
  }

  grouping ip-access-list-grouping {
    leaf-list access-list {
      tailf:cli-drop-node-name;
      tailf:cli-full-command;
      tailf:cli-flat-list-syntax;
      type exp-acl-type;
    }
    leaf-list prefix-list {
      description
        "Match entries of prefix-lists";
      tailf:cli-flat-list-syntax;
      tailf:cli-full-command;
      type string;
    }
  }

  grouping ipv6-access-list-grouping {
    leaf access-list {
      tailf:cli-drop-node-name;
      type string {
        pattern "[a-zA-Z].*";
      }
    }
    leaf prefix-list {
      description
        "IPv6 prefix-list";
      type string;
      tailf:non-strict-leafref {
        path "/ios:native/ipv6/prefix-list/prefixes/name";
      }
    }
  }

  grouping route-map-community-grouping {
    list community-id {
      tailf:cli-drop-node-name;
      tailf:cli-suppress-mode;
      key "community-id cost-value";
      leaf community-id {
        description
          "Community ID";
        tailf:cli-drop-node-name;
        type uint8 {
          range "0..255";
        }
      }
      leaf cost-value {
        description
          "Cost Value (No-preference Cost = 2147483647)";
        tailf:cli-drop-node-name;
        type uint32 {
          range "0..4294967295";
        }
      }
    }
  }
  grouping ipv4-acl-icmp-match {
    choice icmp-msg-choice {
      case icmp-msg-type-code {
        leaf msg-type {
          tailf:cli-drop-node-name;
          type uint8;
        }
        leaf msg-code {
          tailf:cli-drop-node-name;
          type uint8;
        }
      }
      case named-msg-type-case {
        leaf named-msg-type {
          tailf:cli-drop-node-name;
          type enumeration {
            enum "administratively-prohibited";
            enum "alternate-address";
            enum "conversion-error";
            enum "dod-host-prohibited";
            enum "dod-net-prohibited";
            enum "echo";
            enum "echo-reply";
            enum "general-parameter-problem";
            enum "host-isolated";
            enum "host-precedence-unreachable";
            enum "host-redirect";
            enum "host-tos-redirect";
            enum "host-tos-unreachable";
            enum "host-unknown";
            enum "host-unreachable";
            enum "information-reply";
            enum "information-request";
            enum "mask-reply";
            enum "mask-request";
            enum "mobile-redirect";
            enum "net-redirect";
            enum "net-tos-redirect";
            enum "net-tos-unreachable";
            enum "net-unreachable";
            enum "network-unknown";
            enum "no-room-for-option";
            enum "option-missing";
            enum "packet-too-big";
            enum "parameter-problem";
            enum "port-unreachable";
            enum "precedence-unreachable";
            enum "protocol-unreachable";
            enum "reassembly-timeout";
            enum "redirect";
            enum "router-advertisement";
            enum "router-solicitation";
            enum "source-quench";
            enum "source-route-failed";
            enum "time-exceeded";
            enum "timestamp-reply";
            enum "timestamp-request";
            enum "traceroute";
            enum "ttl-exceeded";
            enum "unreachable";
          }
        }
      }
    }
  }
  grouping ipv6-acl-icmp-match {
    choice icmp_choice {
      case msg-type-code {
        leaf msg-type-case {
          tailf:cli-drop-node-name;
          type uint8;
        }
        leaf msg-code {
          tailf:cli-drop-node-name;
          type uint8;
        }
      }
      case named-msg-type-case {
        leaf named-msg-type {
          tailf:cli-drop-node-name;
          type enumeration {
            enum "beyond-scope";
            enum "destination-unreachable";
            enum "dhaad-reply";
            enum "dhaad-request";
            enum "echo-reply";
            enum "echo-request";
            enum "header";
            enum "hop-limit";
            enum "mld-query";
            enum "mld-reduction";
            enum "mld-report";
            enum "mpd-advertisement";
            enum "mpd-solicitation";
            enum "nd-na";
            enum "nd-ns";
            enum "next-header";
            enum "no-admin";
            enum "no-route";
            enum "packet-too-big";
            enum "parameter-option";
            enum "parameter-problem";
            enum "port-unreachable";
            enum "reassembly-timeout";
            enum "redirect";
            enum "reject-route";
            enum "renum-command";
            enum "renum-result";
            enum "renum-seq-number";
            enum "router-advertisement";
            enum "router-renumbering";
            enum "router-solicitation";
            enum "source-policy";
            enum "time-exceeded";
            enum "unreachable";
          }
        }
      }
    }
  }
  grouping ipv4-acl-tcp-bit-match {
    leaf plusack {
      tailf:alt-name "+ack";
      description
        "Match on ACK set";
      type empty;
    }
    leaf plusfin {
      tailf:alt-name "+fin";
      description
        "Match on FIN set";
      type empty;
    }
    leaf pluspsh {
      tailf:alt-name "+psh";
      description
        "Match on PSH set";
      type empty;
    }
    leaf plusrst {
      tailf:alt-name "+rst";
      description
        "Match on RST set";
      type empty;
    }
    leaf plussyn {
      tailf:alt-name "+syn";
      description
        "Match on SYN set";
      type empty;
    }
    leaf plusurg {
      tailf:alt-name "+urg";
      description
        "Match on URG set";
      type empty;
    }
    leaf minusack {
      tailf:alt-name "-ack";
      description
        "Match on ACK not set";
      type empty;
    }
    leaf minusfin {
      tailf:alt-name "-fin";
      description
        "Match on FIN not set";
      type empty;
    }
    leaf minuspsh {
      tailf:alt-name "-psh";
      description
        "Match on PSH not set";
      type empty;
    }
    leaf minusrst {
      tailf:alt-name "-rst";
      description
        "Match on RST not set";
      type empty;
    }
    leaf minussyn {
      tailf:alt-name "-syn";
      description
        "Match on SYN not set";
      type empty;
    }
    leaf minusurg {
      tailf:alt-name "-urg";
      description
        "Match on URG not set";
      type empty;
    }
  }

  grouping ipv4-acl-tcp-match {
    container match-all {
      description
        "Match if all specified flags are present";
      tailf:cli-flatten-container;
      tailf:cli-incomplete-command;
      uses ipv4-acl-tcp-bit-match;
    }
    container match-any {
      description
        "Match if any specified flags is present";
      tailf:cli-flatten-container;
      tailf:cli-incomplete-command;
      uses ipv4-acl-tcp-bit-match;
    }
  }

  grouping acl-tcp-common-match {
    leaf ack {
      description
        "Match on the ACK bit";
      type empty;
    }
    leaf fin {
      description
        "Match on the FIN bit";
      type empty;
    }
    leaf psh {
      description
        "Match on the PSH bit";
      type empty;
    }
    leaf rst {
      description
        "Match on the RST bit";
      type empty;
    }
    leaf syn {
      description
        "Match on the SYN bit";
      type empty;
    }
    leaf urg {
      description
        "Match on the URG bit";
      type empty;
    }
    leaf established {
      description
        "Match established connections";
      type empty;
    }
  }

  grouping ipv4-acl-match-common-attribute {
    leaf dscp {
      description
        "Match packets with given dscp value";
      tailf:cli-break-sequence-commands;
      type dscp-type;
    }
    leaf fragments {
      description
        "Check non-initial fragments";
      type empty;
    }
    leaf log {
      description
        "Log matches against this entry";
      type empty;
    }
    leaf log-input {
      description
        "Log matches against this entry, including input interface";
      type empty;
    }
    leaf option {
      description
        "Match packets with given IP Options value";
      type union {
        type uint8;
        type enumeration {
          enum "add-ext";
          enum "any-options";
          enum "com-security";
          enum "dps";
          enum "encode";
          enum "eool";
          enum "ext-ip";
          enum "ext-security";
          enum "finn";
          enum "imitd";
          enum "lsr";
          enum "mtup";
          enum "mtur";
          enum "no-op";
          enum "nsapa";
          enum "record-route";
          enum "router-alert";
          enum "sdb";
          enum "security";
          enum "ssr";
          enum "stream-id";
          enum "timestamp";
          enum "traceroute";
          enum "ump";
          enum "visa";
          enum "zsu";
        }
      }
    }
    leaf precedence {
      description
        "Match packets with given precedence value";
      type union {
        type uint8 {
          range "0..7";
        }
        type enumeration {
          enum "critical";
          enum "flash";
          enum "flash-override";
          enum "immediate";
          enum "internet";
          enum "network";
          enum "priority";
          enum "routine";
        }
      }
    }
    leaf time-range {
      description
        "Specify a time-range";
      type string;
    }
    leaf tos {
      description
        "Match packets with given TOS value";
      type union {
        type uint8 {
          range "0..15";
        }
        type enumeration {
          enum "max-reliability";
          enum "max-throughput";
          enum "min-delay";
          enum "min-monetary-cost";
          enum "normal";
        }
      }
    }
    container ttl {
      description
        "Match packets with given TTL value";
      tailf:cli-flatten-container;
      tailf:cli-incomplete-command;
      choice ttl-choice {
        case eq-case {
          leaf eq {
            description
              "Match only packets on a given TTL number";
            type uint8;
          }
        }
        case gt-case {
          leaf gt {
            description
              "Match only packets on a given TTL number";
            type uint8;
          }
        }
        case lt-case {
          leaf lt {
            description
              "Match only packets on a given TTL number";
            type uint8;
          }
        }
        case neq-case {
          leaf neq {
            description
              "Match only packets on a given TTL number";
            type uint8;
          }
        }
        case range-case {
          container range {
            description
              "Match only packets in the range of TTLs";
            tailf:cli-flatten-container;
            tailf:cli-sequence-commands;
            tailf:cli-compact-syntax;
            tailf:cli-incomplete-command;
            leaf value1 {
              tailf:cli-drop-node-name;
              type uint8;
            }
            leaf value2 {
              tailf:cli-drop-node-name;
              type uint8;
            }
          }
        }
      }
    }
  }

  grouping ipv6-acl-match-common-attribute {
    leaf auth {
      description
        "Match on authentication header";
      tailf:cli-break-sequence-commands;
      type empty;
    }
    leaf dest-option {
      description
        "Destination Option header (all types)";
      type empty;
    }
    leaf dscp {
      description
        "Match packets with given dscp value";
      type dscp-type;
    }
    leaf flow-label {
      description
        "Flow label";
      type uint32 {
        range "0..1048575";
      }
    }
    leaf hbh {
      description
        "Match on hop-by-hop option";
      type empty;
    }
    leaf log {
      description
        "Log matches against this entry";
      type empty;
    }
    leaf log-input {
      description
        "Log matches against this entry, including input";
      type empty;
    }
    leaf mobility {
      description
        "Mobility header (all types)";
      type empty;
    }
    leaf mobility-type {
      description
        "Mobility header with type";
      type mobility-type;
    }
    leaf routing {
      description
        "Routing header (all types)";
      type empty;
    }
    leaf routing-type {
      description
        "Routing header with type";
      type uint8;
    }
    leaf time-range {
      description
        "Specify a time-range";
      type string;
    }
  }

  grouping ace-log-grouping {
    leaf log {
      description
        "Log matches against this entry";
      tailf:cli-optional-in-sequence;
      type empty;
    }
  }

  grouping ipv4-std-ace-grouping {
    container std-ace {
      tailf:cli-drop-node-name;
      tailf:cli-flatten-container;
      tailf:cli-sequence-commands;
      tailf:cli-compact-syntax;
      choice source-choice {
        case ipv4-prefix-case {
          leaf ipv4-prefix {
            tailf:cli-drop-node-name;
            type ipv4-host-type;
          }
          leaf mask {
            tailf:cli-drop-node-name;
            tailf:cli-optional-in-sequence;
            type inet:ipv4-address;
          }
        }
        case any-case {
          leaf any {
            description
              "Any source prefix";
            type empty;
          }
        }
        case host-case {
          leaf host {
            description
              "A single source host";
            type ipv4-host-type;
          }
        }
      }
      uses ace-log-grouping;
    }
  }

  grouping ipv4-acl-src-dst-addr-port-grouping {
    choice source-choice {
      case ipv4-prefix-case {
        leaf ipv4-address {
          tailf:cli-drop-node-name;
          tailf:cli-incomplete-command;
          mandatory true;
          type inet:ipv4-address;
        }
        leaf mask {
          mandatory true;
          tailf:cli-drop-node-name;
          tailf:cli-incomplete-command;
          type inet:ipv4-address;
        }
      }
      case any-case {
        leaf any {
          tailf:cli-incomplete-command;
          description
            "Any source host";
          type empty;
        }
      }
      case host-case {
        leaf host {
          description
            "A single source host";
          tailf:cli-incomplete-command;
          type ipv4-host-type;
        }
      }
      case object-group-case {
        leaf object-group {
          tailf:cli-incomplete-command;
          tailf:cli-diff-dependency "/ios:native/object-group";
          description
            "Source network object group";
          type string;
        }
      }
    }
    choice src-port-choice {
      case src-eq-case {
        leaf src-eq {
          tailf:alt-name "eq";
          tailf:cli-optional-in-sequence;
          description
            "Match only packets on a given port number";
          type acl-port-type;
        } 
      } 
      case src-gt-case {
        leaf src-gt {
          tailf:alt-name "gt";
          tailf:cli-optional-in-sequence;
          description
            "Match only packets with a greater port number";
          type acl-port-type;
        } 
      } 
      case src-lt-case {
        leaf src-lt {
          tailf:alt-name "lt";
          tailf:cli-optional-in-sequence;
          description
            "Match only packets with a lower port number";
          type acl-port-type;
        } 
      } 
      case src-neq-case {
        leaf src-neq {
          tailf:alt-name "neq";
          tailf:cli-optional-in-sequence;
          description
            "Match only packets not on a given port number";
          type acl-port-type;
        } 
      } 
      case src-range-case {
        leaf src-range1 { 
          tailf:alt-name "range";
          tailf:cli-optional-in-sequence;
          description
            "Match only packets in the range of port numbers";
          type acl-port-type;
        } 
        leaf src-range2 {
          description
            "Match only packets in the range of port numbers";
          tailf:cli-optional-in-sequence;
          tailf:cli-drop-node-name;
          type acl-port-type;
        } 
      } 
    } 
    choice destination-choice {
      case ipv4-prefix-case {
        leaf dest-ipv4-address {
          tailf:cli-drop-node-name;
          tailf:cli-incomplete-command;
          mandatory true;
          type inet:ipv4-address;
        }
        leaf dest-mask {
          tailf:cli-drop-node-name;
          mandatory true;
          type inet:ipv4-address;
        }
      }
      case any-case {
        leaf dst-any {
          tailf:alt-name "any";
          description
            "Any destination host";
          type empty;
        }
      }
      case host-case {
        leaf dst-host {
          tailf:alt-name "host";
          description
            "A single destination host";
          type ipv4-host-type;
        }
      }
      case object-group-case {
        leaf dst-object-group {
          tailf:alt-name "object-group";
          tailf:cli-diff-dependency "/ios:native/object-group";
          description
            "Destination network object group";
          type string;
        }
      }
    }
    choice dst-port-choice {
      case dst-eq-case {
        leaf dst-eq {
          tailf:alt-name "eq";
          tailf:cli-optional-in-sequence;
          description
            "Match only packets on a given port number";
          type acl-port-type;
        } 
      } 
      case dst-gt-case {
        leaf dst-gt {
          tailf:alt-name "gt";
          tailf:cli-optional-in-sequence;
          description
            "Match only packets with a greater port number";
          type acl-port-type;
        } 
      } 
      case dst-lt-case {
        leaf dst-lt {
          tailf:alt-name "lt";
          tailf:cli-optional-in-sequence;
          description
            "Match only packets with a lower port number";
          type acl-port-type;
        } 
      } 
      case dst-neq-case {
        leaf dst-neq {
          tailf:alt-name "neq";
          tailf:cli-optional-in-sequence;
          description
            "Match only packets not on a given port number";
          type acl-port-type;
        } 
      } 
      case dst-range-case {
        leaf dst-range1 { 
          tailf:alt-name "range";
          tailf:cli-optional-in-sequence;
          description
            "Match only packets in the range of port numbers";
          type acl-port-type;
        } 
        leaf dst-range2 {
          description
            "Match only packets in the range of port numbers";
          tailf:cli-drop-node-name;
          tailf:cli-optional-in-sequence;
          type acl-port-type;
        } 
      } 
    } 
  } 
  grouping ipv6-acl-src-dst-addr-port-grouping {
    choice source-choice {
      case host-case {
        leaf source-host {
          tailf:alt-name "host";
          tailf:cli-incomplete-command;
	  type host-type;
        }
      }
      case address-case {
        leaf source-address {
          tailf:cli-drop-node-name;
          tailf:cli-incomplete-command;
          type inet:ipv6-address;
        }
        leaf source-wildcard-bits {
          tailf:cli-drop-node-name;
	  tailf:cli-incomplete-command;
	  type inet:ipv6-address;
        }
      } 
      case prefix-case {
        leaf source-prefix {
          tailf:cli-drop-node-name;
          tailf:cli-incomplete-command;
          type inet:ipv6-prefix;
        } 
      }
      case any-case {
        leaf any {
          tailf:cli-incomplete-command;
          type empty;
        }	 
      }
    }
    choice src-port-choice {
      case src-eq-case {
        leaf src-eq {
          tailf:alt-name "eq";
          description
            "Match only packets on a given port number";
          tailf:cli-optional-in-sequence;
          type acl-port-type;
        } 
      } 
      case src-gt-case {
        leaf src-gt {
          tailf:alt-name "gt";
          description
            "Match only packets with a greater port number";
          tailf:cli-optional-in-sequence;
          type acl-port-type;
        } 
      } 
      case src-lt-case {
        leaf src-lt {
          tailf:alt-name "lt";
          tailf:cli-optional-in-sequence;
          description
            "Match only packets with a lower port number";
          type acl-port-type;
        } 
      } 
      case src-neq-case {
        leaf src-neq {
          tailf:alt-name "neq";
          tailf:cli-optional-in-sequence;
          description
            "Match only packets not on a given port number";
          type acl-port-type;
        } 
      } 
      case src-range-case {
        leaf src-range1 { 
          tailf:alt-name "range";
          tailf:cli-optional-in-sequence;
          description
            "Match only packets in the range of port numbers";
          type acl-port-type;
        } 
        leaf src-range2 {
          description
            "Match only packets in the range of port numbers";
          tailf:cli-drop-node-name;
          tailf:cli-optional-in-sequence;
          type acl-port-type;
        } 
      } 
    } 
    choice destination-choice {
      case host-case {
        leaf destination-host {
          tailf:alt-name "host";
          type host-type;
        }
      }
      case address-case {
        leaf destination-address {
          tailf:cli-drop-node-name;
          tailf:cli-incomplete-command;
          type inet:ipv6-address;
        }
        leaf destination-wildcard-bits {
          tailf:cli-drop-node-name;
	  type inet:ipv6-address;
        }
      } 
      case prefix-case {
        leaf destination-prefix {
          tailf:cli-drop-node-name;
          type inet:ipv6-prefix;
        } 
      }
      case any-case {
        leaf destination-any {
          tailf:alt-name "any";
	  type empty;
        }	 
      }
    }
    choice dst-port-choice {
      case dst-eq-case {
        leaf dst-eq {
          tailf:alt-name "eq";
          tailf:cli-optional-in-sequence;
          description
            "Match only packets on a given port number";
          type acl-port-type;
        } 
      } 
      case dst-gt-case {
        leaf dst-gt {
          tailf:alt-name "gt";
          tailf:cli-optional-in-sequence;
          description
            "Match only packets with a greater port number";
          type acl-port-type;
        } 
      } 
      case dst-lt-case {
        leaf dst-lt {
          tailf:alt-name "lt";
          tailf:cli-optional-in-sequence;
          description
            "Match only packets with a lower port number";
          type acl-port-type;
        } 
      } 
      case dst-neq-case {
        leaf dst-neq {
          tailf:alt-name "neq";
          tailf:cli-optional-in-sequence;
          description
            "Match only packets not on a given port number";
          type acl-port-type;
        } 
      } 
      case dst-range-case {
        leaf dst-range1 { 
          tailf:alt-name "range";
          tailf:cli-optional-in-sequence;
          description
           "Match only packets in the range of port numbers";
          type acl-port-type;
        } 
        leaf dst-range2 {
          description
            "Match only packets in the range of port numbers";
          tailf:cli-drop-node-name;
          tailf:cli-optional-in-sequence;
          type acl-port-type;
        } 
      } 
    } 
  } 

  grouping acl-remark-grouping {
    leaf remark {
      description
        "Access list entry comment";
      tailf:cli-multi-value;
      type string {
        length "1..100";
      }
    }
  }

  grouping ipv6-acl-grouping {
    list access-list-seq-rule {
      tailf:cli-suppress-mode;
      tailf:cli-delete-when-empty;
      tailf:cli-drop-node-name;
      tailf:cli-show-long-obu-diffs;
      ordered-by user;
      key "sequence";
      leaf sequence {
        description
          "Sequence number for this entry";
        tailf:cli-expose-key-name;
        type uint64 {
          range "1..4294967294";
        }
      }
      container ace-rule {
        tailf:cli-drop-node-name;
        tailf:cli-flatten-container;
	tailf:cli-sequence-commands;
        tailf:cli-compact-syntax;
	leaf action {
	  tailf:cli-drop-node-name;
	  type enumeration {
	    enum deny;
	    enum permit;
	  }
	}
        leaf protocol {
          tailf:cli-drop-node-name;
	  tailf:cli-optional-in-sequence;
	  type union {
	    type uint8 {
	      range "0..255";
	    }
	    type enumeration {
	      enum ahp;
	      enum esp;
	      enum hbh;
	      enum icmp;
	      enum ipv6;
	      enum pcp;
	      enum sctp;
	      enum tcp;
	      enum udp;
            }
	  }
        }
        uses ipv6-acl-src-dst-addr-port-grouping;
        uses ipv6-acl-match-common-attribute;
	uses acl-tcp-common-match;
        uses ipv6-acl-icmp-match;
      }

      uses acl-remark-grouping;
    }
  }

  grouping ipv4-std-acl-grouping {
    list access-list-seq-rule {
      tailf:cli-suppress-mode;
      tailf:cli-delete-when-empty;
      tailf:cli-drop-node-name;
      tailf:cli-show-long-obu-diffs;
      key "sequence";
      leaf sequence {
        tailf:cli-incomplete-command;
        type uint64 {
          range "1..2147483647";
        }
      }
      choice deny-permit {
        container deny {
          description
            "Specify packets to reject";
          uses ipv4-std-ace-grouping;
        }
        container permit {
          description
            "Specify packets to forward";
          uses ipv4-std-ace-grouping;
        }
      }
      uses acl-remark-grouping;
    }
  }
  grouping ipv4-ext-acl-grouping {
    list access-list-seq-rule {
      tailf:cli-suppress-mode;
      tailf:cli-delete-when-empty;
      tailf:cli-drop-node-name;
      tailf:cli-show-long-obu-diffs;
      key "sequence";
      leaf sequence {
        type uint64 {
          range "1..2147483647";
        }
      }
      container ace-rule {
        tailf:cli-drop-node-name;
        tailf:cli-flatten-container;
	tailf:cli-sequence-commands;
        tailf:cli-compact-syntax;
        leaf action {
          tailf:cli-drop-node-name;
          tailf:cli-incomplete-command;
          type enumeration {
            enum deny;
            enum permit;
          }
        }
        leaf protocol {
          tailf:cli-drop-node-name;
          tailf:cli-incomplete-command;
          type union {
            type uint8 {
              range "0..255";
            }
            type enumeration {
              enum ahp;
              enum eigrp;
              enum esp;
              enum gre;
              enum icmp;
              enum igmp;
              enum ip;
              enum ipinip;
              enum nos;
	      enum object-group;
              enum ospf;
              enum pcp;
              enum pim;
              enum tcp;
              enum udp;
            }
          }
        }
	leaf object-group-str {
	  tailf:cli-drop-node-name;
          tailf:cli-incomplete-command;
	  tailf:cli-optional-in-sequence;
	  description
	    "Service object group name";
          tailf:cli-diff-dependency "/ios:native/object-group";
          type string;
	}
        uses ipv4-acl-src-dst-addr-port-grouping;
        uses ipv4-acl-match-common-attribute;
	uses ipv4-acl-tcp-match;
	uses acl-tcp-common-match;
        uses ipv4-acl-icmp-match;
      }

      uses acl-remark-grouping;
    }
  }
  grouping ipv4-role-acl-grouping {
    list access-list-seq-rule {
      tailf:cli-suppress-mode;
      tailf:cli-delete-when-empty;
      tailf:cli-drop-node-name;
      tailf:cli-show-long-obu-diffs;
      key "sequence";
      leaf sequence {
        type uint64 {
          range "1..2147483647";
        }
      }
      container ace-rule {
        tailf:cli-drop-node-name;
        tailf:cli-flatten-container;
        tailf:cli-sequence-commands;
        tailf:cli-compact-syntax;
        leaf action {
          tailf:cli-drop-node-name;
          tailf:cli-incomplete-command;
          type enumeration {
            enum deny;
            enum permit;
          }
        }
        leaf protocol {
          tailf:cli-drop-node-name;
          tailf:cli-incomplete-command;
          type union {
            type uint8 {
              range "0..255";
            }
            type enumeration {
              enum ahp;
              enum eigrp;
              enum esp;
              enum gre;
              enum icmp;
              enum igmp;
              enum ip;
              enum ipinip;
              enum nos;
              enum object-group;
              enum ospf;
              enum pcp;
              enum pim;
              enum tcp;
              enum udp;
            }
          }
        }
        leaf object-group-str {
          tailf:cli-drop-node-name;
          tailf:cli-incomplete-command;
          tailf:cli-optional-in-sequence;
          description
            "Service object group name";
          tailf:cli-diff-dependency "/ios:native/object-group";
          type string;
        }
        uses ipv4-acl-match-common-attribute;
        uses ipv4-acl-tcp-match;
        uses acl-tcp-common-match;
        uses ipv4-acl-icmp-match;
      }

      uses acl-remark-grouping;
    }
  }

  grouping flow-name-grouping {
    container name {
      description
        "Application name";
      presence "true";
      leaf account-on-resolution {
        description
          "Account on resolution";
        type empty;
      }
    }
  }

  grouping flow-vendor-version-grouping {
    leaf vendor {
      description
        "Application vendor id";
      tailf:cli-full-command;
      type empty;
    }
    leaf version {
      description
        "Application version id";
      tailf:cli-full-command;
      type empty;
    }
  }

  grouping flow-client-ipv4-ipv6-transport-grouping {
    container ipv4 {
      description
        "Client side IPv4 metrics";
      leaf address {
        description
          "IPv4 address of the flow initiator";
        tailf:cli-full-command;
        type empty;
      }
    }
    container ipv6 {
      description
        "Client side IPv6 metrics";
      leaf address {
        description
          "IPv6 address of the flow initiator";
        tailf:cli-full-command;
        type empty;
      }
    }
    container transport {
      description
        "Client side transport metrics";
      leaf port {
        description
          "Transport port of the flow initiator";
        tailf:cli-full-command;
        type empty;
      }
    }
  }

  grouping flow-server-ipv4-ipv6-transport-grouping {
    container ipv4 {
      description
        "Server side IPv4 metrics";
      leaf address {
        description
          "IPv4 address of the flow responder";
        tailf:cli-full-command;
        type empty;
      }
    }
    container ipv6 {
      description
        "Server side IPv6 metrics";
      leaf address {
        description
          "IPv6 address of the flow responder";
        tailf:cli-full-command;
        type empty;
      }
    }
    container transport {
      description
        "Server side transport metrics";
      leaf port {
        description
          "Transport port of the flow responder";
        tailf:cli-full-command;
        type empty;
      }
    }
  }

  grouping flow-transaction-id-grouping {
    leaf transaction-id {
      description
        "An identifier for a transaction between client and server";
      tailf:cli-full-command;
      type empty;
    }
  }

  grouping flow-id-initiator-grouping {
    leaf id {
      description
        "An identifier for a connection between client and server";
      tailf:cli-full-command;
      type empty;
    }
    leaf initiator {
      description
        "The direction of the flow";
      tailf:cli-full-command;
      type empty;
    }
  }

  grouping flow-datalink-grouping {
    leaf destination-vlan-id {
      description
        "ID of the VLAN that the packet is going to";
      tailf:cli-full-command;
      type empty;
    }
    container mac {
      description
        "MAC fields";
      container destination {
        description
          "destination MAC fields";
        container address {
          description
            "Destination MAC address from packet";
          leaf input {
            description
              "Destination MAC address from packet at input";
            tailf:cli-full-command;
            type empty;
          }
          leaf output {
            description
              "Destination MAC address from packet at output";
            tailf:cli-full-command;
            type empty;
          }
        }
      }
      container source {
        description
          "source MAC fields";
        container address {
          description
            "Source MAC address from packet";
          leaf input {
            description
              "Source MAC address from packet at input";
            tailf:cli-full-command;
            type empty;
          }
          leaf output {
            description
              "Source MAC address from packet at output";
            tailf:cli-full-command;
            type empty;
          }
        }
      }
    }
    leaf source-vlan-id {
      description
        "ID of the VLAN that the packet came from";
      tailf:cli-full-command;
      type empty;
    }
  }

  grouping flow-flow-common-grouping {
    container cts {
      description
        "Cisco Trusted Security fields";
      container destination {
        description
          "Cisco Trusted Security destination fields";
        leaf group-tag {
          description
            "destination group-tag";
          type empty;
        }
      }
      container source {
        description
          "Cisco Trusted Security source fields";
        leaf group-tag {
          description
            "source group-tag";
          type empty;
        }
      }
    }
    leaf direction {
      description
        "Direction the flow was monitored in";
      tailf:cli-full-command;
      type empty;
    }
    container observation {
      description
        "Flow observation metrics";
      leaf point {
        description
          "Observation point ID";
        type empty;
      }
    }
    leaf sampler {
      description
        "ID of the sampler";
      tailf:cli-full-command;
      type empty;
    }
  }

  grouping flow-interface-grouping {
    container input {
      description
        "The input interface";
      presence "true";
      leaf snmp {
        description
          "SNMP Index of the input interface";
        type empty;
      }
    }
    container output {
      description
        "The output interface";
      presence "true";
      leaf snmp {
        description
          "SNMP Index of the output interface";
        type empty;
      }
    }
  }

  grouping flow-ipv4-grouping {
    container destination {
      description
        "IPv4 destination address based fields";
      leaf address {
        description
          "IPv4 destination address";
        tailf:cli-full-command;
        type empty;
      }
      container mask {
        description
          "IPv4 address mask for the IPv4 destination address";
        presence "true";
        leaf minimum-mask {
          description
            "Provide a minimum mask for this field";
          type uint8 {
            range "1..32";
          }
        }
      }
      container prefix {
        description
          "IPv4 address prefix for the IPv4 destination address";
        presence "true";
        leaf minimum-mask {
          description
            "Provide a minimum mask for this field";
          type uint8 {
            range "1..32";
          }
        }
      }
    }
    leaf dscp {
      description
        "IPv4 DSCP (part of TOS)";
      tailf:cli-full-command;
      type empty;
    }
    container fragmentation {
      description
        "IPv4 fragmentation fields";
      leaf flags {
        description
          "IPv4 fragmentation flags";
        tailf:cli-full-command;
        type empty;
      }
      leaf offset {
        description
          "IPv4 fragmentation offset";
        tailf:cli-full-command;
        type empty;
      }
    }
    leaf header-length {
      description
        "IPv4 header length (IHL in 32 bit words)";
      tailf:cli-full-command;
      type empty;
    }
    leaf id {
      description
        "IPv4 ID";
      tailf:cli-full-command;
      type empty;
    }
    container length {
      description
        "IPv4 length fields";
      leaf header {
        description
          "Length of the IPv4 header in bytes";
        tailf:cli-full-command;
        type empty;
      }
      leaf payload {
        description
          "Length of the IPv4 payload in bytes";
        tailf:cli-full-command;
        type empty;
      }
      container total {
        description
          "Total length of the IPv4 header and payload in bytes";
        presence "true";
        leaf maximum {
          description
            "Maximum total length in bytes";
          tailf:cli-full-command;
          type empty;
        }
        leaf minimum {
          description
            "Minimum total length in bytes";
          tailf:cli-full-command;
          type empty;
        }
      }
    }
    container option {
      description
        "IPv4 option fields";
      leaf map {
        description
          "Bitmap of IPv4 options";
        tailf:cli-full-command;
        type empty;
      }
    }
    leaf precedence {
      description
        "IPv4 precedence (part of TOS)";
      tailf:cli-full-command;
      type empty;
    }
    leaf protocol {
      description
        "IPv4 protocol";
      tailf:cli-full-command;
      type empty;
    }
    container section {
      description
        "Part of the packet";
      container header {
        description
          "Raw data starting at the IPv4 header";
        leaf size {
          description
            "Specify the number of bytes to capture";
          type uint16 {
            range "1..1200";
          }
        }
      }
      container payload {
        description
          "Raw data starting at the IPv4 payload";
        leaf size {
          description
            "Specify the number of bytes to capture";
          type uint16 {
            range "1..1200";
          }
        }
      }
    }
    container source {
      description
        "IPv4 source address based fields";
      leaf address {
        description
          "IPv4 source address";
        tailf:cli-full-command;
        type empty;
      }
      container mask {
        description
          "IPv4 address mask for the IPv4 source address";
        presence "true";
        leaf minimum-mask {
          description
            "Provide a minimum mask for this field";
          type uint8 {
            range "1..32";
          }
        }
      }
      container prefix {
        description
          "IPv4 address prefix for the IPv4 source address";
        presence "true";
        leaf minimum-mask {
          description
            "Provide a minimum mask for this field";
          type uint8 {
            range "1..32";
          }
        }
      }
    }
    leaf tos {
      description
        "IPv4 type of service";
      tailf:cli-full-command;
      type empty;
    }
    container total-length {
      description
        "IPv4 total length";
      presence "true";
      leaf maximum {
        description
          "Largest value for IPv4 length seen in the flow";
        tailf:cli-full-command;
        type empty;
      }
      leaf minimum {
        description
          "Smallest value for IPv4 length seen in the flow";
        tailf:cli-full-command;
        type empty;
      }
    }
    container ttl {
      description
        "IPv4 TTL";
      presence "true";
      leaf maximum {
        description
          "Largest value seen for TTL in the flow";
        tailf:cli-full-command;
        type empty;
      }
      leaf minimum {
        description
          "Smallest value seen for TTL in the flow";
        tailf:cli-full-command;
        type empty;
      }
    }
    leaf version {
      description
        "IP version from IPv4 header";
      tailf:cli-full-command;
      type empty;
    }
  }

  grouping flow-ipv6-grouping {
    container destination {
      description
        "IPv6 destination address based fields";
      leaf address {
        description
          "IPv6 destination address";
        tailf:cli-full-command;
        type empty;
      }
      container mask {
        description
          "IPv6 address mask for the IPv6 destination address";
        presence "true";
        leaf minimum-mask {
          description
            "Provide a minimum mask for this field";
          type uint8 {
            range "1..128";
          }
        }
      }
      container prefix {
        description
          "IPv6 address prefix for the IPv6 destination address";
        presence "true";
        leaf minimum-mask {
          description
            "Provide a minimum mask for this field";
          type uint8 {
            range "1..128";
          }
        }
      }
    }
    leaf dscp {
      description
        "IPv6 DSCP (part of Traffic Class)";
      tailf:cli-full-command;
      type empty;
    }
    container extension {
      description
        "IPv6 extension header fields";
      leaf map {
        description
          "Bitmap of IPv6 extension headers";
        tailf:cli-full-command;
        type empty;
      }
    }
    leaf flow-label {
      description
        "IPv6 flow label";
      tailf:cli-full-command;
      type empty;
    }
    container fragmentation {
      description
        "IPv6 fragmentation fields";
      leaf flags {
        description
          "IPv6 fragmentation flags";
        tailf:cli-full-command;
        type empty;
      }
      leaf id {
        description
          "IPv6 fragmentation ID";
        tailf:cli-full-command;
        type empty;
      }
      leaf offset {
        description
          "IPv6 fragmentation offset";
        tailf:cli-full-command;
        type empty;
      }
    }
    container hop-limit {
      description
        "IPv6 hop limit";
      presence "true";
      leaf maximum {
        description
          "Largest value seen for hop-limit in the flow";
        tailf:cli-full-command;
        type empty;
      }
      leaf minimum {
        description
          "Smallest value seen for hop-limit in the flow";
        tailf:cli-full-command;
        type empty;
      }
    }
    container length {
      description
        "IPv6 length fields";
      leaf header {
        description
          "Length of the IPv6 header, not including any extension headers, in bytes";
        tailf:cli-full-command;
        type empty;
      }
      leaf payload {
        description
          "Length of the IPv6 payload, including any extension headers, in bytes";
        tailf:cli-full-command;
        type empty;
      }
      container total {
        description
          "Total length of the IPv6 header and payload in bytes";
        presence "true";
        leaf maximum {
          description
            "Maximum total length in bytes";
          tailf:cli-full-command;
          type empty;
        }
        leaf minimum {
          description
            "Minimum total length in bytes";
          tailf:cli-full-command;
          type empty;
        }
      }
    }
    leaf next-header {
      description
        "The value of the next-header field in the IPv6 header";
      tailf:cli-full-command;
      type empty;
    }
    leaf payload-length {
      description
        "Length of the IPv6 payload in bytes";
      tailf:cli-full-command;
      type empty;
    }
    leaf precedence {
      description
        "IPv6 precedence (part of Traffic Class)";
      tailf:cli-full-command;
      type empty;
    }
    leaf protocol {
      description
        "IPv6 payload protocol";
      tailf:cli-full-command;
      type empty;
    }
    container section {
      description
        "Part of the packet";
      container header {
        description
          "Raw data starting at the IPv6 header";
        leaf size {
          description
            "Specify the number of bytes to capture";
          type uint16 {
            range "1..1200";
          }
        }
      }
      container payload {
        description
          "Raw data starting at the IPv6 payload";
        leaf size {
          description
            "Specify the number of bytes to capture";
          type uint16 {
            range "1..1200";
          }
        }
      }
    }
    container source {
      description
        "IPv6 source address based fields";
      leaf address {
        description
          "IPv6 source address";
        tailf:cli-full-command;
        type empty;
      }
      container mask {
        description
          "IPv6 address mask for the IPv6 source address";
        presence "true";
        leaf minimum-mask {
          description
            "Provide a minimum mask for this field";
          type uint8 {
            range "1..128";
          }
        }
      }
      container prefix {
        description
          "IPv6 address prefix for the IPv6 source address";
        presence "true";
        leaf minimum-mask {
          description
            "Provide a minimum mask for this field";
          type uint8 {
            range "1..128";
          }
        }
      }
    }
    leaf traffic-class {
      description
        "IPv6 traffic class";
      tailf:cli-full-command;
      type empty;
    }
    leaf version {
      description
        "IP version from IPv6 header";
      tailf:cli-full-command;
      type empty;
    }
  }

  grouping flow-mpls-grouping {
    container label {
      description
        "MPLS label details";
      container one {
        description
          "MPLS label 1 information";
        tailf:alt-name "1";
        leaf details {
          description
            "MPLS label 1 details";
          tailf:cli-full-command;
          type empty;
        }
        leaf exp {
          description
            "MPLS EXP field from the last label that was pushed";
          tailf:cli-full-command;
          type empty;
        }
        leaf ttl {
          description
            "MPLS TTL field from the last label that was pushed";
          tailf:cli-full-command;
          type empty;
        }
        leaf type {
          description
            "MPLS label type of the last label that was pushed";
          tailf:cli-full-command;
          type empty;
        }
      }
      container two {
        description
          "MPLS label 2 information";
        tailf:alt-name "2";
        leaf details {
          description
            "MPLS label 2 details";
          tailf:cli-full-command;
          type empty;
        }
      }
      container three {
        description
          "MPLS label 3 information";
        tailf:alt-name "3";
        leaf details {
          description
            "MPLS label 3 details";
          tailf:cli-full-command;
          type empty;
        }
      }
      container four {
        description
          "MPLS label 4 information";
        tailf:alt-name "4";
        leaf details {
          description
            "MPLS label 4 details";
          tailf:cli-full-command;
          type empty;
        }
      }
      container five {
        description
          "MPLS label 5 information";
        tailf:alt-name "5";
        leaf details {
          description
            "MPLS label 5 details";
          tailf:cli-full-command;
          type empty;
        }
      }
      container six {
        description
          "MPLS label 6 information";
        tailf:alt-name "6";
        leaf details {
          description
            "MPLS label 6 details";
          tailf:cli-full-command;
          type empty;
        }
      }
    }
  }

  grouping flow-network-grouping {
    container delay {
      description
        "network delay metrics";
      leaf sample {
        description
          "The number of samples of roundtrip delay";
        tailf:cli-full-command;
        type empty;
      }
      leaf sum {
        description
          "The sum of roundtrip delay";
        tailf:cli-full-command;
        type empty;
      }
    }
  }

  grouping flow-pfr-grouping {
    container label {
      description
        "PfR label metrics";
      leaf identifier {
        description
          "pfr label id";
        tailf:cli-full-command;
        type empty;
      }
    }
    container one-way-delay {
      description
        "The packet transmission delay between specified nodes";
      leaf samples {
        description
          "Total number of one-way-delay samples";
        tailf:cli-full-command;
        type empty;
      }
      leaf sum {
        description
          "The packet transmission delay sum between specified nodes";
        tailf:cli-full-command;
        type empty;
      }
    }
    container service {
      description
        "PfR service metrics";
      tailf:cli-sequence-commands;
      tailf:cli-compact-syntax;
      leaf provider {
        description
          "PfR service provider metrics";
        type empty;
      }
      leaf tag {
        description
          "PfR service provider tag metrics";
        type empty;
      }
      leaf identifier {
        description
          "PfR service provider tag";
        type empty;
      }
    }
    container site {
      description
        "PfR site  metrics";
      container destination {
        description
          "PfR site destination metrics";
        container id {
          description
            "PfR site destination ID metrics";
          leaf ipv4 {
            description
              "site ID of the packet destination";
            tailf:cli-full-command;
            type empty;
          }
        }
        container prefix {
          description
            "PfR site prefix of the packet destination";
          leaf ipv4 {
            description
              "site prefix of the packet destination";
            tailf:cli-full-command;
            type empty;
          }
          container mask {
            description
              "PfR site prefix mask of the packet destination";
            leaf ipv4 {
              description
                "site prefix mask of the packet destination";
              tailf:cli-full-command;
              type empty;
            }
          }
        }
      }
      container source {
        description
          "PfR site source metrics";
        container id {
          description
            "PfR site source ID metrics";
          leaf ipv4 {
            description
              "site ID of the packet source";
            tailf:cli-full-command;
            type empty;
          }
        }
        container prefix {
          description
            "PfR site prefix of the packet source";
          leaf ipv4 {
            description
              "site prefix of the packet source";
            tailf:cli-full-command;
            type empty;
          }
          container mask {
            description
              "PfR site prefix mask of the packet source";
            leaf ipv4 {
              description
                "site prefix mask of the packet source";
              tailf:cli-full-command;
              type empty;
            }
          }
        }
      }
    }
  }

  grouping flow-policy-grouping {
    container performance-monitor {
      description
        "Performance-monitor policy related metrics";
      container classification {
        description
          "Classification metrics";
        leaf hierarchy {
          description
            "Performance-monitor class hierarchy";
          tailf:cli-full-command;
          type empty;
        }
      }
    }
    container qos {
      description
        "QoS policy related metrics";
      container classification {
        description
          "Classification metrics";
        leaf hierarchy {
          description
            "QoS class hierarchy";
          tailf:cli-full-command;
          type empty;
        }
      }
      container queue {
        description
          "Queue metrics";
        leaf drops {
          description
            "QoS queue drops";
          tailf:cli-full-command;
          when "../../../../../collect";
          type empty;
        }
        leaf index {
          description
            "QoS queue index";
          tailf:cli-full-command;
          type empty;
        }
      }
    }
  }

  grouping flow-routing-grouping {
    container destination {
      description
        "Destination routing attributes";
      container as {
        description
          "AS number of the destination network";
        presence "true";
        leaf as4-octet {
          tailf:alt-name "4-octet";
          description
            "4 octet AS number of the destination network";
          tailf:cli-full-command;
          type empty;
        }
        container peer {
          description
            "AS number of the peer network we will forward to";
          presence "true";
          leaf peer4-octet {
            tailf:alt-name "4-octet";
            description
              "4 octet AS number of the peer network we will forward to";
            tailf:cli-full-command;
            type empty;
          }
        }
      }
      leaf traffic-index {
        description
          "BGP destination traffic index";
        tailf:cli-full-command;
        type empty;
      }
    }
    container forwarding-status {
      description
        "Forwarding status of the packet";
      presence "true";
      leaf reason {
        description
          "Forwarding status reason of the packet";
        tailf:cli-full-command;
        type empty;
      }
    }
    leaf is-multicast {
      description
        "Indicates if this is multicast";
      tailf:cli-full-command;
      type empty;
    }
    container next-hop {
      description
        "Information regarding the next hop";
      container address {
        description
          "IP address of the next hop";
        container ipv4 {
          description
            "IPv4 address of the next hop";
          presence "true";
          leaf bgp {
            description
              "IPv4 address of the BGP next hop";
            tailf:cli-full-command;
            type empty;
          }
        }
        container ipv6 {
          description
            "IPv6 address of the next hop";
          presence "true";
          leaf bgp {
            description
              "IPv6 address of the BGP next hop";
            tailf:cli-full-command;
            type empty;
          }
        }
      }
    }
    container pw {
      description
        "Pseudowire fields";
      container destination {
        description
          "Pseudowire destination";
        leaf address {
          description
            "Pseudowire destination address";
          tailf:cli-full-command;
          type empty;
        }
      }
    }
    container source {
      description
        "Source routing attributes";
      container as {
        description
          "AS number of the original network";
        presence "true";
        leaf as4-octet {
          tailf:alt-name "4-octet";
          description
            "4 octet AS number of the original network";
          tailf:cli-full-command;
          type empty;
        }
        container peer {
          description
            "AS number of the peer network where the packet came from";
          presence "true";
          leaf peer4-octet {
            tailf:alt-name "4-octet";
            description
              "4 octet AS number of the peer network where the packet came from";
            tailf:cli-full-command;
            type empty;
          }
        }
      }
      leaf traffic-index {
        description
          "BGP source traffic index";
        tailf:cli-full-command;
        type empty;
      }
    }
    container vrf {
      description
        "VRF routing attributes";
      leaf input {
        description
          "VRF ID for incoming packet";
        tailf:cli-full-command;
        type empty;
      }
      leaf output {
        description
          "VRF ID for outgoing packet";
        tailf:cli-full-command;
        type empty;
      }
    }
  }

  grouping flow-services-grouping {
    container waas {
      description
        "WAAS (Wide Area Application Services) metrics";
      leaf passthrough-reason {
        description
          "WAAS passthrough reason";
        tailf:cli-full-command;
        when "../../../../collect";
        type empty;
      }
      container segment {
        description
          "WAAS optimization segment";
        presence "true";
        leaf account-on-resolution {
          description
            "Account on resolution";
          tailf:cli-full-command;
          type empty;
        }
      }
    }
  }

  grouping flow-transport-common-grouping {
    leaf destination-port {
      description
        "Transport destination port";
      tailf:cli-full-command;
      type empty;
    }
    container icmp {
      description
        "ICMP fields";
      container ipv4 {
        description
          "IPv4 ICMP fields";
        leaf code {
          description
            "IPv4 ICMP code";
          tailf:cli-full-command;
          type empty;
        }
        leaf type {
          description
            "IPv4 ICMP type";
          tailf:cli-full-command;
          type empty;
        }
      }
      container ipv6 {
        description
          "IPv6 ICMP fields";
        leaf code {
          description
            "IPv6 ICMP code";
          tailf:cli-full-command;
          type empty;
        }
        leaf type {
          description
            "IPv6 ICMP type";
          tailf:cli-full-command;
          type empty;
        }
      }
    }
    container igmp {
      description
        "IGMP fields";
      leaf type {
        description
          "IGMP type";
        tailf:cli-full-command;
        type empty;
      }
    }
    leaf source-port {
      description
        "Transport source port";
      tailf:cli-full-command;
      type empty;
    }
    container tcp {
      description
        "TCP fields";
      leaf acknowledgement-number {
        description
          "TCP acknowledgement number";
        tailf:cli-full-command;
        type empty;
      }
      leaf destination-port {
        description
          "TCP destination port";
        tailf:cli-full-command;
        type empty;
      }
      container flags {
        description
          "TCP flags";
        tailf:cli-compact-syntax;
        presence "true";
        leaf ack {
          description
            "TCP acknowledgement flag";
          type empty;
        }
        leaf cwr {
          description
            "TCP congestion window reduced flag";
          type empty;
        }
        leaf ece {
          description
            "TCP ECN echo flag";
          type empty;
        }
        leaf fin {
          description
            "TCP finish flag";
          type empty;
        }
        leaf psh {
          description
            "TCP push flag";
          type empty;
        }
        leaf rst {
          description
            "TCP reset flag";
          type empty;
        }
        leaf syn {
          description
            "TCP synchronise flag";
          type empty;
        }
        leaf urg {
          description
            "TCP urgent flag";
          type empty;
        }
      }
      container flow {
        description
          "TCP flow";
        when "../../../../collect";
        leaf count {
          description
            "Number of tcp flows";
          tailf:cli-full-command;
          type empty;
        }
      }
      leaf header-length {
        description
          "TCP header length (in 32 bit words)";
        tailf:cli-full-command;
        type empty;
      }
      leaf maximum-segment-size {
        description
          "The maximum size of TCP segment";
        tailf:cli-full-command;
        type empty;
      }
      container option {
        description
          "TCP option fields";
        container map {
          description
            "Bitmap of TCP options";
          presence "true";
          leaf long {
            description
              "Extended bitmap of TCP options";
            tailf:cli-full-command;
            type empty;
          }
        }
      }
      leaf sequence-number {
        description
          "TCP sequence number";
        tailf:cli-full-command;
        type empty;
      }
      leaf source-port {
        description
          "TCP source port";
        tailf:cli-full-command;
        type empty;
      }
      leaf urgent-pointer {
        description
          "TCP urgent pointer";
        tailf:cli-full-command;
        type empty;
      }
      container window-size {
        description
          "TCP window size";
        presence "true";
        container average {
          description
            "The average size of TCP window";
          presence "true";
          leaf sum {
            description
              "The sum of per flow TCP window average size";
            tailf:cli-full-command;
            type empty;
          }
        }
        leaf maximum {
          description
            "The maximum size of TCP window";
          tailf:cli-full-command;
          type empty;
        }
        leaf minimum {
          description
            "The minimum size of TCP window";
          tailf:cli-full-command;
          type empty;
        }
        leaf sum {
          description
            "The sum of TCP window size";
          tailf:cli-full-command;
          type empty;
        }
      }
    }
    container udp {
      description
        "UDP fields";
      leaf destination-port {
        description
          "UDP destination port";
        tailf:cli-full-command;
        type empty;
      }
      leaf message-length {
        description
          "UDP message length";
        tailf:cli-full-command;
        type empty;
      }
      leaf source-port {
        description
          "UDP source port";
        tailf:cli-full-command;
        type empty;
      }
    }
  }

  grouping flow-record-collect-grouping {
    container collect {
      description
        "Specify a non-key field";
      container application {
        description
          "Application fields";
        container dns {
          description
            "Domain Name Server lookup";
          leaf domain-name {
            description
              "Domain name";
            type empty;
          }
        }
        container http {
          description
            "World Wide Web traffic";
          leaf host {
            description
              "Host name of Origin Server containing resource";
            tailf:cli-full-command;
            type empty;
          }
          leaf referer {
            description
              "Address the resource request was obtained from";
            tailf:cli-full-command;
            type empty;
          }
          container uri {
            description
              "List of URIs and associated hit counts";
            leaf statistics {
              description
                "Collect URI statistics";
              tailf:cli-full-command;
              type empty;
            }
          }
          leaf url {
            description
              "Uniform Resource Locator path";
            tailf:cli-full-command;
            type empty;
          }
          leaf user-agent {
            description
              "Software used by agent sending the request";
            tailf:cli-full-command;
            type empty;
          }
        }
        container media {
          description
            "Media fields";
          container bytes {
            description
              "Media fields";
            container counter {
              description
                "A count of the number of bytes of media payload";
              presence "true";
              leaf long {
                description
                  "A count of the number of bytes of media payload (64 bit counter)";
                type empty;
              }
            }
            container rate {
              description
                "Byte rate for the media stream";
              presence "true";
              container per-flow {
                description
                  "Average media byte rate across flows";
                presence "true";
                leaf max {
                  description
                    "Maximum byte rate in the media stream";
                  tailf:cli-full-command;
                  type empty;
                }
                leaf min {
                  description
                    "Minumun byte rate in the media stream";
                  tailf:cli-full-command;
                  type empty;
                }
              }
            }
          }
          leaf event {
            description
              "Flags indicating media events";
            tailf:cli-full-command;
            type empty;
          }
          container packets {
            description
              "Media fields";
            container counter {
              description
                "A count of the number of packets with a media payload";
              presence "true";
              leaf long {
                description
                  "A count of the number of packets with a media payload (64 bit counter)";
                type empty;
              }
            }
            container rate {
              description
                "Packet rate for the media stream";
              presence "true";
              container variation {
                description
                  "Variation in packet rate from configured expected rate";
                presence "true";
                leaf max {
                  description
                    "Max variation in packet rate from configured expected rate";
                  tailf:cli-full-command;
                  type empty;
                }
                leaf min {
                  description
                    "Variation in packet rate from configured expected rate";
                  tailf:cli-full-command;
                  type empty;
                }
                leaf sum {
                  description
                    "The sum of media rate variation from the configured rate for the RTP stream";
                  tailf:cli-full-command;
                  type empty;
                }
              }
            }
          }
        }
        uses flow-name-grouping;
        container nntp {
          description
            "Network news transfer protocol";
          leaf group-name {
            description
              "NNTP Group name";
            type empty;
          }
        }
        container pop3 {
          description
            "Post Office Protocol 3";
          leaf server {
            description
              "POP3 Server Name";
            type empty;
          }
        }
        container rtmp {
          description
            "Real Time Messaging Protocol";
          leaf pageUrl {
            description
              "RTMP page url address";
            type empty;
          }
        }
        container rtsp {
          description
            "Real Time Streaming Protocol";
          leaf host {
            description
              "RTSP Host Name";
            type empty;
          }
        }
        container sip {
          description
            "Session Initiation Protocol";
          leaf destination {
            description
              "The destination domain of SIP transactions";
            tailf:cli-full-command;
            type empty;
          }
          leaf source {
            description
              "The source domain of SIP transactions";
            tailf:cli-full-command;
            type empty;
          }
        }
        container smtp {
          description
            "Simple Mail Transfer Protocol";
          leaf sender {
            description
              "SMTP Sender Mail Address";
            tailf:cli-full-command;
            type empty;
          }
          leaf server {
            description
              "SMTP Server Name";
            tailf:cli-full-command;
            type empty;
          }
        }
        container ssl {
          description
            "Secure Socket Layer Protocol";
          leaf common-name {
            description
              "Certificate Common Name (CN)";
            type empty;
          }
        }
        uses flow-vendor-version-grouping;
      }
      container connection {
        description
          "Connection fields";
        container client {
          description
            "Client side (flow initiator) related metrics";
          leaf all {
            description
              "All non-key client metrics";
            tailf:cli-full-command;
            type empty;
          }
          container counter {
            description
              "Client side counter metrics";
            container bytes {
              description
                "Number of bytes sent by the client";
              leaf long {
                description
                  "64 bits counter";
                tailf:cli-full-command;
                type empty;
              }
              container network {
                description
                  "Number of bytes sent by the client";
                leaf long {
                  description
                    "Total number of bytes transmitted by the client";
                  tailf:cli-full-command;
                  type empty;
                }
              }
              leaf retransmitted {
                description
                  "Number of bytes retransmitted by the client";
                tailf:cli-full-command;
                type empty;
              }
              container transport {
                description
                  "Number of bytes sent by the client";
                leaf long {
                  description
                    "64 bit counter";
                  tailf:cli-full-command;
                  type empty;
                }
              }
            }
            container packets {
              description
                "Number of packets sent by the client";
              leaf long {
                description
                  "64 bits counter";
                tailf:cli-full-command;
                type empty;
              }
              leaf retransmitted {
                description
                  "Number of packets retransmitted by the client";
                tailf:cli-full-command;
                type empty;
              }
            }
          }
          uses flow-client-ipv4-ipv6-transport-grouping;
        }
        container delay {
          description
            "Connection delay metrics";
          leaf all {
            description
              "All non-key client metrics";
            tailf:cli-full-command;
            type empty;
          }
          container application {
            description
              "Application time metrics";
            leaf max {
              description
                "Maximum application response time";
              tailf:cli-full-command;
              type empty;
            }
            leaf min {
              description
                "Minimum application response time";
              tailf:cli-full-command;
              type empty;
            }
            leaf sum {
              description
                "Total application response time";
              tailf:cli-full-command;
              type empty;
            }
          }
          container network {
            description
              "Network time metrics";
            container client-to-server {
              description
                "RTT between the client and the server";
              leaf max {
                description
                  "Maximum network time";
                tailf:cli-full-command;
                type empty;
              }
              leaf min {
                description
                  "Minimum network time";
                tailf:cli-full-command;
                type empty;
              }
              leaf num-samples {
                description
                  "The number of CSND samples";
                tailf:cli-full-command;
                type empty;
              }
              leaf sum {
                description
                  "Total network time";
                tailf:cli-full-command;
                type empty;
              }
            }
            container long-lived {
              description
                "Long-lived network delay metrics";
              container client-to-serve {
                description
                  "Long-lived network delay client-to-server metrics";
                leaf sum {
                  description
                    "Total network time";
                  type empty;
                }
              }
              container to-client {
                description
                  "Long-lived network delay to-client metrics";
                leaf sum {
                  description
                    "Total network time";
                  type empty;
                }
              }
              container to-serve {
                description
                  "Long-lived network delay to-server metrics";
                leaf sum {
                  description
                    "Total network time";
                  type empty;
                }
              }
            }
            container to-client {
              description
                "RTT from observation point to the client";
              leaf max {
                description
                  "Maximum network time";
                tailf:cli-full-command;
                type empty;
              }
              leaf min {
                description
                  "Minimum network time";
                tailf:cli-full-command;
                type empty;
              }
              leaf num-samples {
                description
                  "The number of CND samples";
                tailf:cli-full-command;
                type empty;
              }
              leaf sum {
                description
                  "Total network time";
                tailf:cli-full-command;
                type empty;
              }
            }
            container to-server {
              description
                "RTT from observation point to the server";
              leaf max {
                description
                  "Maximum network time";
                tailf:cli-full-command;
                type empty;
              }
              leaf min {
                description
                  "Minimum network time";
                tailf:cli-full-command;
                type empty;
              }
              leaf num-samples {
                description
                  "The number of SND samples";
                tailf:cli-full-command;
                type empty;
              }
              leaf sum {
                description
                  "Total network time";
                tailf:cli-full-command;
                type empty;
              }
            }
          }
          container response {
            description
              "Response time metrics";
            container client-to-server {
              description
                "Response time as seen by the client";
              leaf max {
                description
                  "Maximum response time";
                tailf:cli-full-command;
                type empty;
              }
              leaf min {
                description
                  "Minimum response time";
                tailf:cli-full-command;
                type empty;
              }
              leaf sum {
                description
                  "Total response time";
                tailf:cli-full-command;
                type empty;
              }
            }
            container to-server {
              description
                "Response time as seen from observation point";
              leaf histogram {
                description
                  "Histogram for response time";
                tailf:cli-full-command;
                type empty;
              }
              leaf max {
                description
                  "Maximum response time";
                tailf:cli-full-command;
                type empty;
              }
              leaf min {
                description
                  "Minimum response time";
                tailf:cli-full-command;
                type empty;
              }
              leaf sum {
                description
                  "Total response time";
                tailf:cli-full-command;
                type empty;
              }
            }
          }
        }
        uses flow-id-initiator-grouping;
        leaf new-connections {
          description
            "The number of connection initiations observed";
          tailf:cli-full-command;
          type empty;
        }
        container server {
          description
            "Server side (flow responder) related metrics";
          leaf all {
            description
              "All non-key server metrics";
            tailf:cli-full-command;
            type empty;
          }
          container counter {
            description
              "Server side counter metrics";
            container bytes {
              description
                "Number of bytes sent by the server";
              leaf long {
                description
                  "64 bits counter";
                tailf:cli-full-command;
                type empty;
              }
              container network {
                description
                  "Number of bytes sent by the server";
                leaf long {
                  description
                    "Total number of bytes transmitted by the server";
                  tailf:cli-full-command;
                  type empty;
                }
              }
              leaf retransmitted {
                description
                  "Number of bytes retransmitted by the server";
                tailf:cli-full-command;
                type empty;
              }
              container transport {
                description
                  "Number of bytes sent by the server";
                leaf long {
                  description
                    "64 bit counter";
                  tailf:cli-full-command;
                  type empty;
                }
              }
            }
            container packets {
              description
                "Number of packets sent by the server";
              leaf long {
                description
                  "64 bits counter";
                tailf:cli-full-command;
                type empty;
              }
              leaf retransmitted {
                description
                  "Number of packets retransmitted by the server";
                tailf:cli-full-command;
                type empty;
              }
            }
            leaf responses {
              description
                "Number of responses sent by the server";
              tailf:cli-full-command;
              type empty;
            }
          }
          uses flow-server-ipv4-ipv6-transport-grouping;
        }
        leaf sum-duration {
          description
            "The overall time in seconds for all connections";
          tailf:cli-full-command;
          type empty;
        }
        container transaction {
          description
            "Transaction related metrics";
          leaf all {
            description
              "All non-key transaction metrics";
            tailf:cli-full-command;
            type empty;
          }
          container counter {
            description
              "Transaction counter metrics";
            leaf complete {
              description
                "Number of completed transactions";
              tailf:cli-full-command;
              type empty;
            }
          }
          container duration {
            description
              "Transaction duration metrics";
            leaf max {
              description
                "Maximum transaction time";
              tailf:cli-full-command;
              type empty;
            }
            leaf min {
              description
                "Minimum transaction time";
              tailf:cli-full-command;
              type empty;
            }
            leaf sum {
              description
                "Total transaction time";
              tailf:cli-full-command;
              type empty;
            }
          }
        }
        uses flow-transaction-id-grouping;
      }
      container counter {
        description
          "Counter fields";
        container bytes {
          description
            "Total number of bytes";
          presence "true";
          leaf long {
            description
              "Total number of bytes (64 bit counter)";
            tailf:cli-full-command;
            type empty;
          }
          container rate {
            description
              "Byte rate for the flow";
            presence "true";
            container per-flow {
              description
                "Average byte rate for the flow";
              presence "true";
              leaf max {
                description
                  "Maximum byte rate among the aggregated flows";
                tailf:cli-full-command;
                type empty;
              }
              leaf min {
                description
                  "Minimum byte rate among the aggregated flows";
                tailf:cli-full-command;
                type empty;
              }
            }
          }
          container squared {
            description
              "Total of the square of the number of bytes";
            leaf long {
              description
                "Total of the square of the packet length in bytes (64 bit counter)";
              tailf:cli-full-command;
              type empty;
            }
          }
        }
        leaf flows {
          description
            "Total number of flows";
          tailf:cli-full-command;
          type empty;
        }
        container packets {
          description
            "Total number of packets";
          presence "true";
          leaf dropped {
            description
              "Dropped packets";
            type empty;
          }
          leaf long {
            description
              "Total number of packets (64 bit counter)";
            tailf:cli-full-command;
            type empty;
          }
          container rate {
            description
              "Packet rate for the flow";
            presence "true";
            container per-flow {
              description
                "Average packet rate for aggregated flows";
              presence "true";
              leaf max {
                description
                  "Maximum packet rate in the aggregated flows";
                tailf:cli-full-command;
                type empty;
              }
              leaf min {
                description
                  "Minimum packet rate in the aggregated flows";
                tailf:cli-full-command;
                type empty;
              }
            }
          }
        }
      }
      container datalink {
        description
          "Datalink (layer2) fields";
        uses flow-datalink-grouping;
      }
      container flow {
        description
          "Flow identifying fields";
        uses flow-flow-common-grouping;
        leaf end-reason {
          description
            "The reason for a flow ending";
          tailf:cli-full-command;
          type empty;
        }
      }
      container interface {
        description
          "Interface fields";
        uses flow-interface-grouping;
      }
      container ipv4 {
        description
          "IPv4 fields";
        uses flow-ipv4-grouping;
      }
      container ipv6 {
        description
          "IPv6 fields";
        uses flow-ipv6-grouping;
      }
      container metadata {
        description
          "Metadata fields";
        leaf clock-rate {
          description
            "Metadata clock-rate";
          tailf:cli-full-command;
          type empty;
        }
        leaf global-session-id {
          description
            "Metadata global-session-id";
          tailf:cli-full-command;
          type empty;
        }
        leaf multi-party-session-id {
          description
            "Metadata multi-party-session-id";
          tailf:cli-full-command;
          type empty;
        }
      }
      container monitor {
        description
          "monitor fields";
        leaf event {
          description
            "Flags indicating monitor events";
          tailf:cli-full-command;
          type empty;
        }
      }
      container mpls {
        description
          "MPLS fields";
        uses flow-mpls-grouping;
      }
      container network {
        description
          "network metrics";
        uses flow-network-grouping;
      }
      container pfr {
        description
          "PfR metrics";
        uses flow-pfr-grouping;
      }
      container policy {
        description
          "policy fields";
        uses flow-policy-grouping;
      }
      container routing {
        description
          "Routing attributes";
        uses flow-routing-grouping;
      }
      container services {
        description
          "Services fields";
        uses flow-services-grouping;
      }
      container timestamp {
        description
          "Timestamp fields";
        container absolute {
          description
            "Timestamps based on the epoch of 00:00 UTC 1st Jan 1970";
          leaf first {
            description
              "Absolute time the first packet was seen (milliseconds)";
            tailf:cli-full-command;
            type empty;
          }
          leaf last {
            description
              "Absolute time the most recent packet was seen (milliseconds)";
            tailf:cli-full-command;
            type empty;
          }
          container monitoring-interval {
            description
              "Monitoring interval timestamps";
            leaf end {
              description
                "Absolute end time of a monitoring interval (milliseconds)";
              tailf:cli-full-command;
              type empty;
            }
            leaf start {
              description
                "Absolute start time of a monitoring interval (milliseconds)";
              tailf:cli-full-command;
              type empty;
            }
          }
        }
        leaf interval {
          description
            "Epoch of a monitoring interval";
          tailf:cli-full-command;
          type empty;
        }
        container sys-uptime {
          description
            "Timestamps based on the sys-uptime";
          leaf first {
            description
              "Time the first packet was seen";
            tailf:cli-full-command;
            type empty;
          }
          leaf last {
            description
              "Time the most recent packet was seen";
            tailf:cli-full-command;
            type empty;
          }
        }
      }
      container transport {
        description
          "Transport layer fields";
        container bytes {
          description
            "Bytes fields";
          leaf expected {
            description
              "Transport bytes expected";
            tailf:cli-full-command;
            type empty;
          }
          container lost {
            description
              "Transport bytes lost";
            presence "true";
            leaf rate {
              description
                "Transport bytes lost rate";
              tailf:cli-full-command;
              type empty;
            }
          }
          leaf out-of-order {
            description
              "Total number of out-of-order bytes";
            tailf:cli-full-command;
            type empty;
          }
        }
        uses flow-transport-common-grouping;
        container event {
          description
            "Transport event fields";
          container packet-loss {
            description
              "Transport event packet-loss fields";
            container counter {
              description
                "Count of sets of packets that were lost";
              presence "true";
              leaf max {
                description
                  "Highest packet loss counter when multiple flows are aggregated";
                tailf:cli-full-command;
                type empty;
              }
              leaf min {
                description
                  "Lowest packet loss counter when multiple flows are aggregated";
                tailf:cli-full-command;
                type empty;
              }
            }
          }
        }
        container packets {
          description
            "Transport packet fields";
          container expected {
            description
              "Transport packets expected fields";
            leaf counter {
              description
                "Expected number of packets from sequencing information";
              tailf:cli-full-command;
              type empty;
            }
          }
          container lost {
            description
              "Transport packets lost fields";
            container counter {
              description
                "A count of the number of lost packets from sequencing information";
              presence "true";
              leaf max {
                description
                  "Highest lost packet count seen among the aggregated flows";
                tailf:cli-full-command;
                type empty;
              }
              leaf min {
                description
                  "Lowest lost packet count seen among the aggregated flows";
                tailf:cli-full-command;
                type empty;
              }
            }
            container rate {
              description
                "Packet loss rate from sequencing information";
              presence "true";
              leaf max {
                description
                  "Maximum packet loss rate in the aggregated flows";
                tailf:cli-full-command;
                type empty;
              }
              leaf min {
                description
                  "Minimum packet loss rate in the aggregated flows";
                tailf:cli-full-command;
                type empty;
              }
            }
          }
          leaf out-of-order {
            description
              "Total number of out-of-order bytes";
            tailf:cli-full-command;
            type empty;
          }
        }
        container round-trip-time {
          description
            "RTT calculation for flow";
          presence "true";
          leaf max {
            description
              "Highest RTT among all flows";
            tailf:cli-full-command;
            type empty;
          }
          leaf min {
            description
              "Lowest RTT among all flows";
            tailf:cli-full-command;
            type empty;
          }
          leaf samples {
            description
              "RTT samples";
            tailf:cli-full-command;
            type empty;
          }
          leaf sum {
            description
              "Sum RTT for all flows";
            tailf:cli-full-command;
            type empty;
          }
        }
        container rtp {
          description
            "RTP fields";
          container flow {
            description
              "RTP  flow";
            leaf count {
              description
                "Number of RTP flows";
              tailf:cli-full-command;
              type empty;
            }
          }
          container jitter {
            description
              "RTP jitter fields";
            leaf maximum {
              description
                "Maximum jitter for the RTP stream";
              tailf:cli-full-command;
              type empty;
            }
            container mean {
              description
                "Mean jitter for the RTP stream";
              presence "true";
              leaf sum {
                description
                  "The sum of jitter mean for the RTP stream";
                tailf:cli-full-command;
                type empty;
              }
            }
            leaf minimum {
              description
                "Minimum jitter for the RTP stream";
              tailf:cli-full-command;
              type empty;
            }
          }
          leaf payload-type {
            description
              "RTP payload type";
            tailf:cli-full-command;
            type empty;
          }
          leaf ssrc {
            description
              "RTP SSRC";
            tailf:cli-full-command;
            type empty;
          }
        }
      }
    }
  }

  grouping flow-record-match-grouping {
    container match {
      description
        "Specify a key field";
      container application {
        description
          "Application fields";
        uses flow-name-grouping;
        uses flow-vendor-version-grouping;
      }
      container connection {
        description
          "Connection fields";
        container client {
          description
            "Client side (flow initiator) related metrics";
          uses flow-client-ipv4-ipv6-transport-grouping;
        }
        uses flow-id-initiator-grouping;
        container server {
          description
            "Server side (flow responder) related metrics";
          uses flow-server-ipv4-ipv6-transport-grouping;
        }
        uses flow-transaction-id-grouping;
      }
      container datalink {
        description
          "Datalink (layer2) fields";
        uses flow-datalink-grouping;
      }
      container flow {
        description
          "Flow identifying fields";
        uses flow-flow-common-grouping;
      }
      container interface {
        description
          "Interface fields";
        uses flow-interface-grouping;
      }
      container ipv4 {
        description
          "IPv4 fields";
        uses flow-ipv4-grouping;
      }
      container ipv6 {
        description
          "IPv6 fields";
        uses flow-ipv6-grouping;
      }
      container metadata {
        description
          "Metadata fields";
        leaf global-session-id {
          description
            "Metadata global-session-id";
          tailf:cli-full-command;
          type empty;
        }
        leaf multi-party-session-id {
          description
            "Metadata multi-party-session-id";
          tailf:cli-full-command;
          type empty;
        }
      }
      container mpls {
        description
          "MPLS fields";
        uses flow-mpls-grouping;
      }
      container network {
        description
          "network metrics";
        uses flow-network-grouping;
      }
      container pfr {
        description
          "PfR metrics";
        uses flow-pfr-grouping;
      }
      container policy {
        description
          "policy fields";
        uses flow-policy-grouping;
      }
      container routing {
        description
          "Routing attributes";
        uses flow-routing-grouping;
      }
      container services {
        description
          "Services fields";
        uses flow-services-grouping;
      }
      container timestamp {
        description
          "Timestamp fields";
        container absolute {
          description
            "Timestamps based on the epoch of 00:00 UTC 1st Jan 1970";
          container monitoring-interval {
            description
              "Monitoring interval timestamps";
            leaf start {
              description
                "Absolute start time of a monitoring interval (milliseconds)";
              tailf:cli-full-command;
              type empty;
            }
          }
        }
      }
      container transport {
        description
          "Transport layer fields";
        container bytes {
          description
            "Bytes fields";
          leaf expected {
            description
              "Transport bytes expected";
            tailf:cli-full-command;
            type empty;
          }
          container lost {
            description
              "Transport bytes lost";
            presence "true";
            leaf rate {
              description
                "Transport bytes lost rate";
              tailf:cli-full-command;
              type empty;
            }
          }
        }
        container rtp {
          description
            "RTP fields";
          leaf ssrc {
            description
              "RTP SSRC";
            tailf:cli-full-command;
            type empty;
          }
        }
        uses flow-transport-common-grouping;
      }
    }
  }

  grouping flow-monitor-record-netflow-grouping {
    container as {
      description
        "AS aggregation schemes";
      presence "true";
      leaf peer {
        description
          "AS aggregation scheme with peer ASs";
        tailf:cli-full-command;
        type empty;
      }
    }
    container destination-prefix {
      description
        "Destination Prefix aggregation schemes";
      presence "true";
      leaf peer {
        description
          "Destination Prefix aggregation scheme with peer AS";
        tailf:cli-full-command;
        type empty;
      }
    }
    container original-input {
      description
        "Traditional IPv6 input NetFlow with ASs";
      presence "true";
      leaf peer {
        description
          "Traditional IPv6 input NetFlow with peer ASs";
        tailf:cli-full-command;
        type empty;
      }
    }
    container original-output {
      description
        "Traditional IPv6 output NetFlow with ASs";
      presence "true";
      leaf peer {
        description
          "Traditional IPv6 output NetFlow with peer ASs";
        tailf:cli-full-command;
        type empty;
      }
    }
    container prefix {
      description
        "Source and Destination Prefixes aggregation schemes";
      presence "true";
      leaf peer {
        description
          "Source and Destination Prefixes aggregation scheme with peer ASs";
        tailf:cli-full-command;
        type empty;
      }
    }
    leaf protocol-port {
      description
        "Protocol and Ports aggregation scheme";
      tailf:cli-full-command;
      type empty;
    }
    container source-prefix {
      description
        "Source AS and Prefix aggregation schemes";
      presence "true";
      leaf peer {
        description
          "Source AS and Prefix aggregation scheme with peer AS";
        tailf:cli-full-command;
        type empty;
      }
    }
  }

  grouping flow-monitor-grouping {
    container cache {
      description
        "Monitor cache entries";
      leaf entries {
        description
          "Number of cache entries";
        tailf:cli-full-command;
        type uint32 {
          range "16..2000000";
        }
      }
      container timeout {
        description
          "Cache timeout";
        leaf active {
          description
            "Active timeout";
          tailf:cli-full-command;
          type uint32 {
            range "1..604800";
          }
        }
        container event {
          description
            "Timeout event";
          leaf transaction-end {
            description
              "Transaction-end event";
            tailf:cli-full-command;
            type empty;
          }
        }
        leaf inactive {
          description
            "Inactive timeout";
          tailf:cli-full-command;
          type uint32 {
            range "1..604800";
          }
        }
        leaf synchronized {
          description
            "Synchronized timeout";
          tailf:cli-full-command;
          type uint16 {
            range "1..300";
          }
        }
        leaf update {
          description
            "Update timeout";
          tailf:cli-full-command;
          type uint32 {
            range "1..604800";
          }
        }
      }
      leaf type {
        description
          "Cache type";
        tailf:cli-full-command;
        type enumeration {
          enum "immediate";
          enum "normal";
          enum "permanent";
          enum "synchronized";
        }
      }
    }
    leaf description {
      description
        "Provide a description for this Flow Monitor";
      tailf:cli-multi-value;
      tailf:cli-full-command;
      type string;
    }
    list exporter {
      description
        "Add an Exporter to use to export records";
      tailf:cli-suppress-mode;
      key "name";
      leaf name {
        type string;
      }
    }
    container history {
      description
        "Monitor history intervals";
      tailf:cli-sequence-commands;
      tailf:cli-compact-syntax;
      leaf size {
        description
          "History size";
        type uint8 {
          range "0..60";
        }
      }
      leaf timeout {
        description
          "Specify timeout interval";
        tailf:cli-optional-in-sequence;
        type uint8 {
          range "1..30";
        }
      }
    }
    container record {
      description
        "Specify Flow Record to use to define Cache";
      leaf type {
        tailf:cli-drop-node-name;
        type union {
          type enumeration {
            enum "default-rtp";
            enum "default-tcp";
            enum "netflow-original";
          }
          type string;
        }
      }
      container netflow {
        description
          "Traditional NetFlow collection schemes";
        container ipv4 {
          description
            "Traditional IPv4 NetFlow collection schemes";
          uses flow-monitor-record-netflow-grouping;
          container as-tos {
            description
              "AS and TOS aggregation schemes";
            presence "true";
            leaf peer {
              description
                "AS and TOS aggregation scheme with peer ASs";
              tailf:cli-full-command;
              type empty;
            }
          }
          container bgp-nexthop-tos {
            description
              "BGP next-hop and TOS aggregation schemes";
            presence "true";
            leaf peer {
              description
                "BGP next-hop and TOS aggregation scheme with peer ASs";
              tailf:cli-full-command;
              type empty;
            }
          }
          container destination-prefix-tos {
            description
              "Destination Prefix and TOS  aggregation schemes";
            presence "true";
            leaf peer {
              description
                "Destination Prefix and TOS aggregation scheme with peer AS";
              tailf:cli-full-command;
              type empty;
            }
          }
          leaf prefix-port {
            description
              "Prefixes and Ports aggregation scheme";
            tailf:cli-full-command;
            type empty;
          }
          container prefix-tos {
            description
              "Prefixes and TOS aggregation schemes";
            presence "true";
            leaf peer {
              description
                "Prefixes and TOS aggregation scheme with peer ASs";
              tailf:cli-full-command;
              type empty;
            }
          }
          leaf protocol-port-tos {
            description
              "Protocol, Ports and TOS aggregation scheme";
            tailf:cli-full-command;
            type empty;
          }
          container source-prefix-tos {
            description
              "Source Prefix and TOS aggregation schemes";
            presence "true";
            leaf peer {
              description
                "Source Prefix and TOS aggregation scheme with peer AS";
              tailf:cli-full-command;
              type empty;
            }
          }
        }
        container ipv6 {
          description
            "Traditional IPv6 NetFlow collection schemes";
          uses flow-monitor-record-netflow-grouping;
          container bgp-nexthop {
            description
              "BGP next-hop aggregation schemes";
            presence "true";
            leaf peer {
              description
                "BGP next-hop aggregation scheme with peer ASs";
              tailf:cli-full-command;
              type empty;
            }
          }
        }
      }
    }
    container statistics {
      description
        "Collect statistics";
      container packet {
        description
          "Collect packet statistics";
        leaf protocol {
          description
            "Collect packet protocol distribution statistics";
          tailf:cli-full-command;
          type empty;
        }
        leaf size {
          description
            "Collect packet size distribution statistics";
          tailf:cli-full-command;
          type empty;
        }
      }
    }
  }

  grouping flow-default-monitor-grouping {
    container cache {
      description
        "Monitor cache entries";
      leaf entries {
        description
          "Maximum flow entries in the Flow Cache";
        tailf:cli-full-command;
        type empty;
      }
      container timeout {
        description
          "Configure flow cache timeout parameters";
        leaf active {
          description
            "Specify the active flow timeout";
          tailf:cli-full-command;
          type empty;
        }
        container event {
          description
            "Event-based export";
          leaf transaction-end {
            description
              "Export on transaction end event";
            tailf:cli-full-command;
            type empty;
          }
        }
        leaf inactive {
          description
            "Specify the inactive flow timeout";
          tailf:cli-full-command;
          type empty;
        }
        leaf synchronized {
          description
            "Specify the timeout for a synchronized Flow Cache";
          tailf:cli-full-command;
          type empty;
        }
        leaf update {
          description
            "Specify the update timeout for a permanent Flow Cache";
          tailf:cli-full-command;
          type empty;
        }
      }
      leaf type {
        description
          "Set the type of the Flow Cache";
        tailf:cli-full-command;
        type empty;
      }
    }
    leaf description {
      description
        "Provide a description for this Flow Monitor";
      tailf:cli-full-command;
      type empty;
    }
    leaf exporter {
      description
        "Add an Exporter to use to export records";
      tailf:cli-full-command;
      type empty;
    }
    leaf record {
      description
        "Specify Flow Record to use to define Cache";
      tailf:cli-full-command;
      type empty;
    }
    container statistics {
      description
        "Collect statistics";
      container packet {
        description
          "Collect packet statistics";
        leaf protocol {
          description
            "Collect packet protocol distribution statistics";
          tailf:cli-full-command;
          type empty;
        }
        leaf size {
          description
            "Collect packet size distribution statistics";
          tailf:cli-full-command;
          type empty;
        }
      }
    }
  }

  grouping flow-exporter-option-timeout-grouping {
    leaf timeout {
      description
        "Option resend time";
      type uint32 {
        range "1..86400";
      }
    }
  }

  grouping flow-exporter-grouping {
    leaf description {
      description
        "Provide a description for this Flow Exporter";
      tailf:cli-multi-value;
      tailf:cli-full-command;
      type string;
    }
    container destination {
      description
        "Export destination configuration";
      tailf:cli-sequence-commands;
      tailf:cli-compact-syntax;
      leaf ip {
        tailf:cli-drop-node-name;
        type inet:ip-address;
      }
      leaf vrf {
        description
          "Optional VRF label";
        tailf:cli-optional-in-sequence;
        type string;
      }
    }
    leaf dscp {
      description
        "Optional DSCP";
      tailf:cli-full-command;
      type uint8 {
        range "0..63";
      }
    }
    leaf export-protocol {
      description
        "Export protocol version";
      tailf:cli-full-command;
      type enumeration {
        enum "ipfix";
        enum "netflow-v5";
        enum "netflow-v9";
      }
    }
    container option {
      description
        "Select an option for exporting";
      container application-attributes {
        description
          "Application Attributes Table Option";
        presence "true";
        uses flow-exporter-option-timeout-grouping;
      }
      container application-table {
        description
          "Application Table Option";
        presence "true";
        uses flow-exporter-option-timeout-grouping;
      }
      container c3pl-class-table {
        description
          "C3PL class cce-id table";
        presence "true";
        uses flow-exporter-option-timeout-grouping;
      }
      container c3pl-policy-table {
        description
          "C3PL policy cce-id table";
        presence "true";
        uses flow-exporter-option-timeout-grouping;
      }
      container exporter-stats {
        description
          "Exporter Statistics Option";
        presence "true";
        uses flow-exporter-option-timeout-grouping;
      }
      container interface-table {
        description
          "Interface SNMP-index-to-name Table Option";
        presence "true";
        uses flow-exporter-option-timeout-grouping;
      }
      container metadata-version-table {
        description
          "Metadata Version Table Option";
        presence "true";
        uses flow-exporter-option-timeout-grouping;
      }
      container sampler-table {
        description
          "Export Sampler Option";
        presence "true";
        uses flow-exporter-option-timeout-grouping;
      }
      container sub-application-table {
        description
          "Sub Application Table Option";
        presence "true";
        uses flow-exporter-option-timeout-grouping;
      }
      container vrf-table {
        description
          "VRF ID-to-name Table Option";
        presence "true";
        uses flow-exporter-option-timeout-grouping;
      }
    }
    container output-features {
      presence "true";
    }
    container source {
      description
        "Originating interface";
      uses interface-grouping;
    }
    container template {
      description
        "Flow Exporter template configuration";
      container data {
        description
          "Flow Exporter data configuration";
        leaf timeout {
          description
            "Resend data based on a timeout";
          tailf:cli-full-command;
          type uint32 {
            range "1..86400";
          }
        }
      }
    }
    container transport {
      description
        "Transport protocol";
      leaf udp {
        description
          "UDP transport protocol";
        tailf:cli-full-command;
        type uint16;
      }
    }
    leaf ttl {
      description
        "Optional TTL or hop limit";
      tailf:cli-full-command;
      type uint8;
    }
  }

  grouping flow-default-exporter-grouping {
    leaf description {
      description
        "Provide a description for this Flow Exporter";
      tailf:cli-full-command;
      type empty;
    }
    leaf dscp {
      description
        "Optional DSCP";
      tailf:cli-full-command;
      type empty;
    }
    leaf export-protocol {
      description
        "Export protocol version";
      tailf:cli-full-command;
      type empty;
    }
    container option {
      description
        "Select an option for exporting";
      container application-attributes {
        description
          "Application Attributes Table Option";
        presence "true";
      }
      container c3pl-class-table {
        description
          "C3PL class cce-id table";
        presence "true";
      }
      container c3pl-policy-table {
        description
          "C3PL policy cce-id table";
        presence "true";
      }
      container exporter-stats {
        description
          "Exporter Statistics Option";
        presence "true";
      }
      container interface-table {
        description
          "Interface SNMP-index-to-name Table Option";
        presence "true";
      }
      container metadata-version-table {
        description
          "Metadata Version Table Option";
        presence "true";
      }
      container sampler-table {
        description
          "Export Sampler Option";
        presence "true";
      }
      container sub-application-table {
        description
          "Sub Application Table Option";
        presence "true";
      }
      container vrf-table {
        description
          "VRF ID-to-name Table Option";
        presence "true";
      }
    }
    container template {
      description
        "Flow Exporter template configuration";
      container data {
        description
          "Flow Exporter data configuration";
        leaf timeout {
          description
            "Resend data based on a timeout";
          tailf:cli-full-command;
          type empty;
        }
      }
    }
    leaf transport {
      description
        "Transport protocol";
      tailf:cli-full-command;
      type empty;
    }
    leaf ttl {
      description
        "Optional TTL or hop limit";
      tailf:cli-full-command;
      type empty;
    }
  }

  grouping pm-context-traffic-monitor-app-traffic-stats-grouping {
    leaf cache-size {
      description
        "Maximum flow entries in the Flow Cache";
      type uint32 {
        range "64..2000000";
      }
    }
    leaf class-replace {
      description
        "Replace traffic classification";
      type string;
    }
    leaf interval-timeout {
      description
        "The exporting interval timeout";
      type uint32 {
        range "1..604800";
      }
    }
  }

  grouping pm-context-traffic-monitor-ip-grouping {
    leaf ipv4 {
      description
        "Activate monitor for ipv4 traffic";
      type empty;
    }
    leaf ipv6 {
      description
        "Activate monitor for ipv6 traffic";
      type empty;
    }
  }

  grouping performance-monitor-context-grouping {
    container exporter {
      description
        "Create exporter";
      tailf:cli-sequence-commands {
        tailf:cli-reset-all-siblings;
      }
      tailf:cli-compact-syntax;
      leaf destination {
        description
          "Export destination configuration";
        type inet:ip-address;
      }
      leaf source {
        description
          "Originating interface";
        type string;
      }
      leaf port {
        description
          "port";
        tailf:cli-break-sequence-commands;
        type uint16;
      }
      leaf transport {
        description
          "transport";
        type enumeration {
          enum "udp";
        }
      }
      leaf vrf {
        description
          "vrf";
        type string;
      }
    }
    container traffic-monitor {
      description
        "Select traffic monitor";
      container all {
        description
          "All traffic monitors in this profile";
        when "../../profile = 'application-experience' and ../../profile = 'application-performance'";
        presence "true";
        leaf ipv4 {
          description
            "Activate monitor for ipv4 traffic";
          tailf:cli-full-command;
          type empty;
        }
        leaf ipv6 {
          description
            "Activate monitor for ipv6 traffic";
          tailf:cli-full-command;
          type empty;
        }
      }
      container application-response-time {
        description
          "Application response time (ART) metrics and counters for TCP traffic";
        when "../../profile = 'application-experience' and ../../profile = 'application-performance'";
        presence "true";
        uses pm-context-traffic-monitor-app-traffic-stats-grouping;
        leaf cache-type {
          description
            "The type of the Flow Cache";
          type enumeration {
            enum "normal";
            enum "synchronized";
          }
        }
        leaf class-and {
          description
            "Narrow down default traffic classification";
          type string;
        }
        uses pm-context-traffic-monitor-ip-grouping;
      }
      container application-traffic-stats {
        description
          "Application level counters for dns and dht protocol";
        when "../../profile = 'application-experience'";
        presence "true";
        uses pm-context-traffic-monitor-app-traffic-stats-grouping;
      }
      container conversation-traffic-stats {
        description
          "Conversation level counters for IP traffic";
        when "../../profile = 'application-experience'";
        presence "true";
        uses pm-context-traffic-monitor-app-traffic-stats-grouping;
        leaf cache-type {
          description
            "The type of the Flow Cache";
          type enumeration {
            enum "normal";
            enum "synchronized";
          }
        }
        uses pm-context-traffic-monitor-ip-grouping;
      }
      container media {
        description
          "Media metrics and counters for rtp and telepresence-media traffic";
        when "../../profile = 'application-experience' and ../../profile = 'application-performance'";
        presence "true";
        uses pm-context-traffic-monitor-app-traffic-stats-grouping;
        leaf class-and {
          description
            "Narrow down default traffic classification";
          type string;
        }
        leaf egress {
          description
            "Activate monitor on egress direction";
          type empty;
        }
        leaf ingress {
          description
            "Activate monitor on ingress direction";
          type empty;
        }
        uses pm-context-traffic-monitor-ip-grouping;
      }
      container url {
        description
          "URL information, application response time (ART) metrics and counters";
        when "../../profile = 'application-experience' and ../../profile = 'application-performance'";
        presence "true";
        leaf cache-size {
          description
            "Maximum flow entries in the Flow Cache";
          type uint32 {
            range "64..2000000";
          }
        }
        leaf class-and {
          description
            "Narrow down default traffic classification";
          type string;
        }
        leaf class-replace {
          description
            "Replace traffic classification";
          type string;
        }
        uses pm-context-traffic-monitor-ip-grouping;
        leaf sampling-rate {
          description
            "Sampling rate of flow sampler";
          type uint32 {
            range "1..32768";
          }
        }
      }
      container application-client-server-stats {
        description
          "Per interface, client, server and application statistics";
        presence "true";
        when "../../profile = 'application-performance' and ../../profile = 'application-statistics'";
        uses pm-context-traffic-monitor-app-traffic-stats-grouping;
        leaf cache-type {
          description
            "The type of the Flow Cache";
          type enumeration {
            enum "normal";
            enum "synchronized";
          }
        }
        uses pm-context-traffic-monitor-ip-grouping;
      }
      container application-stats {
        description
          "Per application and interface statistics";
        presence "true";
        when "../../profile = 'application-performance' and ../../profile = 'application-statistics'";
        uses pm-context-traffic-monitor-app-traffic-stats-grouping;
      }
    }
  }

  grouping performance-monitor-context-default-grouping {
    container exporter {
      description
        "Create exporter";
      tailf:cli-sequence-commands {
        tailf:cli-reset-all-siblings;
      }
      tailf:cli-compact-syntax;
      leaf destination {
        description
          "Export destination configuration";
        type inet:ip-address;
      }
      leaf source {
        description
          "Originating interface";
        type string;
      }
      leaf port {
        description
          "port";
        tailf:cli-break-sequence-commands;
        type uint16;
      }
      leaf transport {
        description
          "transport";
        type enumeration {
          enum "udp";
        }
      }
      leaf vrf {
        description
          "vrf";
        type string;
      }
    }
    container traffic-monitor {
      description
        "Select traffic monitor";
      container all {
        description
          "All traffic monitors in this profile";
        when "../../../profile = 'application-experience' and ../../../profile = 'application-performance'";
        presence "true";
        leaf ipv4 {
          description
            "Activate monitor for ipv4 traffic";
          tailf:cli-full-command;
          type empty;
        }
        leaf ipv6 {
          description
            "Activate monitor for ipv6 traffic";
          tailf:cli-full-command;
          type empty;
        }
      }
      container application-response-time {
        description
          "Application response time (ART) metrics and counters for TCP traffic";
        when "../../../profile = 'application-experience' and ../../../profile = 'application-performance'";
        presence "true";
        uses pm-context-traffic-monitor-app-traffic-stats-grouping;
        leaf cache-type {
          description
            "The type of the Flow Cache";
          type enumeration {
            enum "normal";
            enum "synchronized";
          }
        }
        leaf class-and {
          description
            "Narrow down default traffic classification";
          type string;
        }
        uses pm-context-traffic-monitor-ip-grouping;
      }
      container application-traffic-stats {
        description
          "Application level counters for dns and dht protocol";
        when "../../../profile = 'application-experience'";
        presence "true";
        uses pm-context-traffic-monitor-app-traffic-stats-grouping;
      }
      container conversation-traffic-stats {
        description
          "Conversation level counters for IP traffic";
        when "../../../profile = 'application-experience'";
        presence "true";
        uses pm-context-traffic-monitor-app-traffic-stats-grouping;
        leaf cache-type {
          description
            "The type of the Flow Cache";
          type enumeration {
            enum "normal";
            enum "synchronized";
          }
        }
        uses pm-context-traffic-monitor-ip-grouping;
      }
      container media {
        description
          "Media metrics and counters for rtp and telepresence-media traffic";
        when "../../../profile = 'application-experience' and ../../../profile = 'application-performance'";
        presence "true";
        uses pm-context-traffic-monitor-app-traffic-stats-grouping;
        leaf class-and {
          description
            "Narrow down default traffic classification";
          type string;
        }
        leaf egress {
          description
            "Activate monitor on egress direction";
          type empty;
        }
        leaf ingress {
          description
            "Activate monitor on ingress direction";
          type empty;
        }
        uses pm-context-traffic-monitor-ip-grouping;
      }
      container url {
        description
          "URL information, application response time (ART) metrics and counters";
        when "../../../profile = 'application-experience' and ../../../profile = 'application-performance'";
        presence "true";
        leaf cache-size {
          description
            "Maximum flow entries in the Flow Cache";
          type uint32 {
            range "64..2000000";
          }
        }
        leaf class-and {
          description
            "Narrow down default traffic classification";
          type string;
        }
        leaf class-replace {
          description
            "Replace traffic classification";
          type string;
        }
        uses pm-context-traffic-monitor-ip-grouping;
        leaf sampling-rate {
          description
            "Sampling rate of flow sampler";
          type uint32 {
            range "1..32768";
          }
        }
      }
      container application-client-server-stats {
        description
          "Per interface, client, server and application statistics";
        presence "true";
        when "../../../profile = 'application-performance' and ../../../profile = 'application-statistics'";
        uses pm-context-traffic-monitor-app-traffic-stats-grouping;
        leaf cache-type {
          description
            "The type of the Flow Cache";
          type enumeration {
            enum "normal";
            enum "synchronized";
          }
        }
        uses pm-context-traffic-monitor-ip-grouping;
      }
      container application-stats {
        description
          "Per application and interface statistics";
        presence "true";
        when "../../../profile = 'application-performance' and ../../../profile = 'application-statistics'";
        uses pm-context-traffic-monitor-app-traffic-stats-grouping;
      }
    }
  }

  grouping ip-nbar-attribute-custom-grouping {
    list custom {
      description
        "custom group value to be created for attribute";
      tailf:cli-suppress-mode;
      key "name";
      leaf name {
        type string;
      }
      leaf help {
        tailf:cli-drop-node-name;
        type string;
      }
    }
  }

  grouping crypto-map-common-grouping {
    leaf description {
      description
        "Description of the crypto map statement policy";
      tailf:cli-multi-value;
      type string;
    }
    container dialer {
      description
        "Dialer related commands";
      leaf pre-classify {
        description
          "Enable dialer list classification before initiating IKE";
        type empty;
      }
    }
    container match {
      description
        "Match values";
      leaf address {
        description
          "Match address of packets to encrypt";
        type ext-acl-type;
      }
    }
    container qos {
      description
        "Quality of Service related commands";
      leaf pre-classify {
        description
          "Enable QOS classification before packets are tunnel encapsulated";
        type empty;
      }
    }
    container reverse-route {
      description
        "Reverse Route Injection.";
      presence "true";
      choice remote-peer-static {
        case remote-peer-case {
          container remote-peer-conatiner {
            tailf:cli-drop-node-name;
            tailf:cli-sequence-commands;
            tailf:cli-compact-syntax;
            leaf remote-peer {
              description
                "Create route in route table for remote tunnel endpoint";
              type inet:ip-address;
            }
            leaf gateway {
              description
                "Force encrypted traffic via this preferred gateway";
              tailf:cli-break-sequence-commands;
              type empty;
            }
            leaf static {
              description
                "Create routes based on static ACLs permanently";
              type empty;
            }
          }
        }
        case static-case {
          leaf static {
            description
              "Create routes based on static ACLs permanently";
            type empty;
          }
        }
      }
    }
  }

  grouping crypto-map-common-set-security-association-grouping {
    leaf dfbit {
      description
        "Handling of encapsulated DF bit.";
      type enumeration {
        enum "clear";
        enum "copy";
        enum "set";
      }
    }
    container dummy {
      description
        "Enable transmitting dummy packets";
      leaf pps {
        description
          "Simulated traffic rate (in pps)";
        type uint8 {
          range "0..25";
        }
      }
      leaf seconds {
        description
          "Simulated traffic rate (in seconds)";
        type uint16 {
          range "1..3600";
        }
      }
    }
    leaf ecn {
      description
        "Handling of ECN bit";
      type enumeration {
        enum "discard";
        enum "propagate";
      }
    }
    container idle-time-container {
      tailf:cli-drop-node-name;
      tailf:cli-sequence-commands;
      tailf:cli-compact-syntax;
      leaf idle-time {
        description
          "Automatically delete IPSec SAs after a given idle period.";
        type uint32 {
          range "60..86400";
        }
      }
      leaf default {
        description
          "All SAs idle-out reset to default peer";
        tailf:cli-optional-in-sequence;
        type empty;
      }
    }
    container lifetime {
      description
        "security association lifetime";
      leaf days {
        description
          "Time-based key duration in days";
        type uint8 {
          range "1..30";
        }
      }
      leaf kilobytes {
        description
          "Volume-based key duration";
        type union {
          type uint64 {
            range "2560..4294967295";
          }
          type enumeration {
            enum "disable";
          }
        }
      }
      leaf seconds {
        description
          "Time-based key duration in seconds";
        type uint64 {
          range "120..2592000";
        }
      }
    }
    container replay {
      description
        "Set replay checking.";
      leaf disable {
        description
          "Disable replay checking";
        type empty;
      }
      leaf window-size {
        description
          "Set replay window size.";
        type enumeration {
          enum "1024";
          enum "128";
          enum "256";
          enum "512";
          enum "64";
        }
      }
    }
  }

  grouping crypto-map-common-set-grouping {
    leaf group {
      description
        "Set the san group parameters";
      type string;
    }
    leaf identity {
      description
        "Identity restriction";
      type string;
    }
    leaf ikev2-profile {
      description
        "Specify ikev2 Profile";
      type string;
    }
    leaf isakmp-profile {
      description
        "Specify isakmp Profile";
      type string;
    }
    container peer {
      description
        "Allowed Encryption/Decryption peer.";
      tailf:cli-sequence-commands;
      tailf:cli-compact-syntax;
      leaf address {
        tailf:cli-drop-node-name;
        type union {
          type inet:ipv4-address;
          type string;
          type inet:ipv6-address;
        }
      }
      leaf default {
        description
          "Reset to default peer in list in the event of a failure";
        tailf:cli-break-sequence-commands;
        type empty;
      }
      leaf dynamic {
        description
          "Resolve the peer address at the time of negotiation";
        type empty;
      }
    }
    container pfs {
      description
        "Specify pfs settings";
      presence "true";
      leaf group {
        tailf:cli-drop-node-name;
        type enumeration {
          enum "group1";
          enum "group14";
          enum "group15";
          enum "group16";
          enum "group19";
          enum "group2";
          enum "group20";
          enum "group21";
          enum "group24";
          enum "group5";
        }
      }
    }
    container reverse-route {
      description
        "Reverse Route Injection";
      leaf distance {
        description
          "Distance metric for this static route";
        type uint8;
      }
      leaf tag {
        description
          "Create route and tag it";
        type uint64 {
          range "1..4294967295";
        }
      }
    }
    leaf-list transform-set {
      description
        "Specify list of transform sets in priority order";
      tailf:cli-flat-list-syntax;
      type string;
    }
  }

  grouping crypto-dynamic-map-grouping {
    uses crypto-map-common-grouping;
    container set {
      description
        "Set values for encryption/decryption";
      uses crypto-map-common-set-grouping;
      container ip-in {
        tailf:cli-drop-node-name;
        container ip {
          description
            "Interface Internet Protocol config commands";
          tailf:cli-sequence-commands;
          tailf:cli-compact-syntax;
          leaf access-group {
            description
              "Specify access control for packets";
            type exp-acl-type;
          }
          leaf in {
            description
              "inbound packets";
            type empty;
          }
        }
      }
      container ip-out {
        tailf:cli-drop-node-name;
        container ip {
          description
            "Interface Internet Protocol config commands";
          tailf:cli-sequence-commands;
          tailf:cli-compact-syntax;
          leaf access-group {
            description
              "Specify access control for packets";
            type exp-acl-type;
          }
          leaf out {
            description
              "outbound packets";
            type empty;
          }
        }
      }
      container nat {
        description
          "Set NAT translation";
        leaf demux {
          description
            "Set NAT demultiplexing";
          type empty;
        }
      }
      container peer-container {
        tailf:cli-drop-node-name;
        tailf:cli-sequence-commands;
        tailf:cli-compact-syntax;
        leaf peer {
          description
            "Allowed Encryption/Decryption peer.";
          type host-v4v6-type;
        }
        leaf default {
          description
            "Reset to default peer in list in the event of a failure";
          tailf:cli-optional-in-sequence;
          type empty;
        }
      }
      container security-association {
        description
          "Security association parameters";
        uses crypto-map-common-set-security-association-grouping;
      }
    }
  }

  grouping crypto-dynamic-map-default-grouping {
    leaf description {
      description
        "Description of the crypto map statement policy";
      type empty;
    }
    container dialer {
      description
        "Dialer related commands";
      leaf pre-classify {
        description
          "Enable dialer list classification before initiating IKE";
        type empty;
      }
    }
    container match {
      description
        "Match values";
      leaf address {
        description
          "Match address of packets to encrypt";
        type empty;
      }
    }
    container qos {
      description
        "Quality of Service related commands";
      leaf pre-classify {
        description
          "Enable QOS classification before packets are tunnel encapsulated";
        type empty;
      }
    }
    container reverse-route {
      description
        "Reverse Route Injection.";
      presence "true";
    }
    container set {
      description
        "Set values for encryption/decryption";
      leaf group {
        description
          "Set the san group parameters";
        type empty;
      }
      leaf identity {
        description
          "Identity restriction";
        type empty;
      }
      leaf ikev2-profile {
        description
          "Specify ikev2 Profile";
        type string;
      }
      container ip {
        description
          "Interface Internet Protocol config commands";
        tailf:cli-sequence-commands;
        tailf:cli-compact-syntax;
        leaf access-group {
          description
            "Specify access control for packets";
          type exp-acl-type;
        }
        leaf direction {
          tailf:cli-drop-node-name;
          type enumeration {
            enum "in";
            enum "out";
          }
        }
      }
      leaf isakmp-profile {
        description
          "Specify isakmp Profile";
        type string;
      }
      container nat {
        description
          "Set NAT translation";
        leaf demux {
          description
            "Set NAT demultiplexing";
          type empty;
        }
      }
      container peer-container {
        tailf:cli-drop-node-name;
        tailf:cli-sequence-commands;
        tailf:cli-compact-syntax;
        leaf peer {
          description
            "Allowed Encryption/Decryption peer.";
          type host-v4v6-type;
        }
        leaf default {
          description
            "Reset to default peer in list in the event of a failure";
          tailf:cli-optional-in-sequence;
          type empty;
        }
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          tailf:cli-drop-node-name;
          tailf:cli-sequence-commands;
          tailf:cli-compact-syntax;
          leaf idle-time {
            description
              "Automatically delete IPSec SAs after a given idle period.";
            type empty;
          }
          leaf default {
            description
              "All SAs idle-out reset to default peer";
            tailf:cli-optional-in-sequence;
            type empty;
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      leaf transform-set {
        description
          "Specify list of transform sets in priority order";
        type empty;
      }
    }
  }

  grouping crypto-gkm-local-server-id-grouping {
    container range {
      description
        "Assign range of Key Server Sender IDs (unique in entire group)";
      tailf:cli-sequence-commands;
      tailf:cli-compact-syntax;
      leaf lowest {
        tailf:cli-drop-node-name;
        type uint8 {
          range "0..1";
        }
      }
      leaf hyphen {
        tailf:alt-name "-";
        type empty;
      }
      leaf highest {
        tailf:cli-drop-node-name;
        type uint8 {
          range "0..1";
        }
      }
    }
    leaf value {
      description
        "Assign Key Server Sender ID (unique in entire group)";
      type uint8 {
        range "0..1";
      }
    }
  }

  grouping crypto-gdoi-coop-ks-config-grouping {
    container local {
      description
        "Local key server configurations";
      presence "true";
      leaf priority {
        description
          "Set local server priority";
        type uint8;
      }
    }
    container peer {
      description
        "Peer server configurations";
      container address {
        description
          "Peer server address";
        leaf ipv4 {
          description
            "Set peer server ipv4 address";
          type inet:ipv4-address;
        }
      }
    }
    container protocol {
      description
        "Specify various protocol operational values";
      presence "true";
      leaf pdu {
        description
          "Maximum size of COOP messages";
        type uint32 {
          range "1..65000";
        }
      }
      leaf version {
        description
          "Set COOP ANN version";
        type enumeration {
          enum "base";
          enum "optimize";
        }
      }
    }
  }

  grouping crypto-gkm-sa-ipsec-grouping {
    container match {
      description
        "Match characteristics of packets to encrypt";
      container address {
        description
          "Match addresses of packets to encrypt";
        leaf ipv4 {
          description
            "Match ipv4 packets";
          type ext-acl-type;
        }
        leaf ipv6 {
          description
            "Match ipv6 packets";
          type string;
        }
      }
    }
    leaf profile {
      description
        "Configure an ipsec profile for the SA";
      type string;
    }
    container replay {
      description
        "Set replay method";
      container counter {
        description
          "Enable anti-replay check for single source traffic by using sequence number";
        presence "true";
        leaf window-size {
          description
            "Set replay window size.";
          type enumeration {
            enum "1024";
            enum "128";
            enum "256";
            enum "512";
            enum "64";
          }
        }
      }
      container time {
        description
          "Enable anti-replay check for any traffic by using time";
        presence "true";
        leaf window-size {
          description
            "Time based replay window size";
          type uint8 {
            range "1..100";
          }
        }
      }
    }
    container tag {
      description
        "Set inline tagging method";
      container cts {
        description
          "Cisco Trust Security";
        leaf sgt {
          description
            "Security Group Tag";
          type empty;
        }
      }
    }
  }

  grouping crypto-gkm-sa-ipsec-default-grouping {
    container match {
      description
        "Match characteristics of packets to encrypt";
      container address {
        description
          "Match addresses of packets to encrypt";
        presence "true";
      }
    }
    leaf profile {
      description
        "Configure an ipsec profile for the SA";
      type empty;
    }
    container replay {
      description
        "Set replay method";
      presence "true";
    }
    container tag {
      description
        "Set inline tagging method";
      presence "true";
    }
  }

  grouping crypto-gkm-local-server-grouping {
    container address {
      description
        "Configure server source address";
      leaf ipv4 {
        description
          "Set ipv4 address of local server";
        type inet:ipv4-address;
      }
    }
    container authorization {
      description
        "Configure authorization for the group";
      container address {
        description
          "Set authorization by address";
        leaf ipv4 {
          description
            "Set authorization by address";
          type union {
            type uint16 {
              range "1..99";
            }
            type string;
          }
        }
      }
      leaf identity {
        description
          "Set authorization by identity";
        type string;
      }
    }
    leaf gdoi {
      description
        "Enable GDOI (ISAKMP) Protocol for Registration & Rekey";
      tailf:cli-full-command;
      type empty;
    }
    leaf gikev2 {
      description
        "Enable G-IKEv2 (IKEv2) Protocol for Registration & Rekey";
      tailf:cli-full-command;
      type string;
    }
    container group {
      description
        "Configure parameters for the group (e.g. Suite-B)";
      container size {
        description
          "Set Group Size for Suite-B counter transforms (SID length)";
        leaf large {
          description
            "32-bit Sender ID (FIPS 140-2 Operating Mode)";
          tailf:cli-full-command;
          type empty;
        }
        leaf medium {
          description
            "24-bit Sender ID (Default)";
          tailf:cli-full-command;
          type empty;
        }
        leaf small {
          description
            "Interoperable with GDOI / G-IKEv2 Standard";
          tailf:cli-full-command;
          type enumeration {
            enum "12";
            enum "16";
            enum "8";
          }
        }
      }
    }
    container identifier {
      description
        "Enter Suite-B KSSID (Key Server Sender ID) config mode";
      tailf:cli-add-mode;
      tailf:cli-mode-name "gkm-local-server-id";
      container default {
        description
          "Set a command to its defaults";
        uses crypto-gkm-local-server-id-grouping;
      }
      uses crypto-gkm-local-server-id-grouping;
    }
    container redundancy {
      description
        "Enter cooperative key server configuration mode";
      tailf:cli-add-mode;
      tailf:cli-mode-name "gdoi-coop-ks-config";
      container default {
        description
          "Set a command to its defaults";
        uses crypto-gdoi-coop-ks-config-grouping;
      }
      uses crypto-gdoi-coop-ks-config-grouping;
    }
    container registration {
      description
        "Configure registration for the group";
      leaf interface {
        description
          "Identify an interface on which to respond to GKM registrations";
        type string;
      }
      container periodic {
        description
          "Define periodic registrations for the group";
        container crl {
          description
            "On every new CRL";
          leaf trustpoint {
            description
              "For a PKI trustpoint";
            type string;
          }
        }
      }
    }
    container rekey {
      description
        "Configure rekey policy for the group";
      leaf acknowledgement {
        description
          "Request group members to acknowledge rekeys";
        type enumeration {
          enum "any";
          enum "cisco";
          enum "interoperable";
        }
      }
      container address {
        description
          "Define the rekey packet format";
        leaf ipv4 {
          description
            "Match ipv4 packets";
          type ext-acl-type;
        }
      }
      container algorithm {
        description
          "Set the rekey encryption algorithm";
        leaf a3des-cbc {
          description
            "Triple DES in CBC mode";
          tailf:alt-name "3des-cbc";
          tailf:cli-full-command;
          type empty;
        }
        leaf aes-128 {
          description
            "128 bit AES";
          tailf:alt-name "aes 128";
          tailf:cli-full-command;
          type empty;
        }
        leaf aes-192 {
          description
            "192 bit AES";
          tailf:alt-name "aes 192";
          tailf:cli-full-command;
          type empty;
        }
        leaf aes-256 {
          description
            "256 bit AES";
          tailf:alt-name "aes 256";
          tailf:cli-full-command;
          type empty;
        }
        leaf des-cbc {
          description
            "DES in CBC mode";
          tailf:cli-full-command;
          type empty;
        }
      }
      container authentication {
        description
          "Identify the rekey authentication keypair";
        container mypubkey {
          description
            "Identify a keypair associated with this device";
          leaf rsa {
            description
              "Identify an RSA keypair";
            type string;
          }
        }
      }
      container lifetime {
        description
          "Define the rekey lifetime";
        leaf days {
          description
            "Time-based key duration in days";
          type uint8 {
            range "1..30";
          }
        }
        leaf seconds {
          description
            "Time-based key duration in seconds";
          type uint64 {
            range "300..2592000";
          }
        }
      }
      container retransmit {
        description
          "Define the rekey retransmission parameters";
        tailf:cli-sequence-commands;
        tailf:cli-compact-syntax;
        leaf seconds {
          tailf:cli-drop-node-name;
          type uint8 {
            range "10..60";
          }
        }
        choice number-periodic {
          case number-case {
            leaf number {
              description
                "Retransmit this many times";
              tailf:cli-full-command;
              type uint8;
            }
          }
          case periodic-case {
            leaf periodic {
              description
                "Periodically send retransmit rekeys";
              tailf:cli-full-command;
              type empty;
            }
          }
        }
      }
      container sig-hash {
        description
          "Set rekey signature-hash parameters";
        leaf algorithm {
          description
            "Set the rekey signature-hash algorithm";
          type enumeration {
            enum "sha";
            enum "sha256";
            enum "sha384";
            enum "sha512";
          }
        }
      }
      container transport {
        description
          "Specify the rekey distribution method";
        leaf unicast {
          description
            "specify unicast rekey distribution";
          tailf:cli-full-command;
          type empty;
        }
      }
    }
    container sa {
      description
        "Configure a security association";
      container d3p {
        description
          "Enable IP delivery delay detection protocol for all SAs within the group";
        container window {
          description
            "IP-D3P window size";
          leaf msec {
            description
              "IP-D3P window size in milliseconds";
            tailf:cli-full-command;
            type uint32 {
              range "1000..100000";
            }
          }
          leaf sec {
            description
              "IP-D3P window size in seconds";
            tailf:cli-full-command;
            type uint8;
          }
        }
      }
      list ipsec {
        description
          "Configure an IPsec SA";
        tailf:cli-mode-name "gkm-sa-ipsec";
        key "sequence";
        leaf sequence {
          type uint16;
        }
        container default {
          description
            "Set a command to its defaults";
          uses crypto-gkm-sa-ipsec-default-grouping;
        }
        uses crypto-gkm-sa-ipsec-grouping;
      }
      container pair-wise-keying {
        description
          "Enable KGS pair-wise-keying";
        leaf safety-limit {
          description
            "KGS safety limit";
          type uint8;
        }
      }
      leaf receive-only {
        description
          "Configure SA to work only in inbound direction";
        tailf:cli-full-command;
        type empty;
      }
    }
  }

  grouping crypto-gkm-local-server-default-grouping {
    container address {
      description
        "Configure server source address";
      presence "true";
    }
    container authorization {
      description
        "Configure authorization for the group";
      container address {
        description
          "Set authorization by address";
        leaf ipv4 {
          description
            "Set authorization by address";
          type empty;
        }
      }
      leaf identity {
        description
          "Set authorization by identity";
        type empty;
      }
    }
    leaf gdoi {
      description
        "Enable GDOI (ISAKMP) Protocol for Registration & Rekey";
      tailf:cli-full-command;
      type empty;
    }
    leaf gikev2 {
      description
        "Enable G-IKEv2 (IKEv2) Protocol for Registration & Rekey";
      tailf:cli-full-command;
      type empty;
    }
    container group {
      description
        "Configure parameters for the group (e.g. Suite-B)";
      container size {
        description
          "Set Group Size for Suite-B counter transforms (SID length)";
        presence "true";
      }
    }
    container identifier {
      description
        "Enter Suite-B KSSID (Key Server Sender ID) config mode";
      presence "true";
    }
    container redundancy {
      description
        "Enter cooperative key server configuration mode";
      presence "true";
    }
    container registration {
      description
        "Configure registration for the group";
      leaf interface {
        description
          "Identify an interface on which to respond to GKM registrations";
        type string;
      }
      container periodic {
        description
          "Define periodic registrations for the group";
        container crl {
          description
            "On every new CRL";
          leaf trustpoint {
            description
              "For a PKI trustpoint";
            type empty;
          }
        }
      }
    }
    container rekey {
      description
        "Configure rekey policy for the group";
      leaf acknowledgement {
        description
          "Request group members to acknowledge rekeys";
        type empty;
      }
      container address {
        description
          "Define the rekey packet format";
        presence "true";
      }
      container algorithm {
        description
          "Set the rekey encryption algorithm";
        presence "true";
      }
      container authentication {
        description
          "Identify the rekey authentication keypair";
        presence "true";
      }
      container lifetime {
        description
          "Define the rekey lifetime";
        leaf days {
          description
            "Time-based key duration in days";
          type empty;
        }
        leaf seconds {
          description
            "Time-based key duration in seconds";
          type empty;
        }
      }
      container retransmit {
        description
          "Define the rekey retransmission parameters";
        presence "true";
      }
      container sig-hash {
        description
          "Set rekey signature-hash parameters";
        leaf algorithm {
          description
            "Set the rekey signature-hash algorithm";
          type empty;
        }
      }
      container transport {
        description
          "Specify the rekey distribution method";
        leaf unicast {
          description
            "specify unicast rekey distribution";
          tailf:cli-full-command;
          type empty;
        }
      }
    }
    container sa {
      description
        "Configure a security association";
      container d3p {
        description
          "Enable IP delivery delay detection protocol for all SAs within the group";
        presence "true";
      }
      list ipsec {
        description
          "Configure an IPsec SA";
        tailf:cli-mode-name "gkm-sa-ipsec";
        key "sequence";
        leaf sequence {
          type uint16;
        }
      }
      container pair-wise-keying {
        description
          "Enable KGS pair-wise-keying";
        presence "true";
      }
      leaf receive-only {
        description
          "Configure SA to work only in inbound direction";
        tailf:cli-full-command;
        type empty;
      }
    }
  }

  grouping crypto-gdio-grouping {
    container client {
      description
        "Set the group client parameters";
      leaf bypass-policy {
        description
          "Allow group-key management traffic sent to this GM only";
        tailf:cli-full-command;
        type empty;
      }
      container protocol {
        description
          "Group Member Registration & Rekey Protocol";
        leaf gdoi {
          description
            "Use GDOI (ISAKMP) Protocol for Registration & Rekey";
          tailf:cli-full-command;
          type empty;
        }
        leaf gikev2 {
          description
            "Use G-IKEv2 Protocol for Registration & Rekey";
          tailf:cli-full-command;
          type string;
        }
      }
      container recovery-check {
        description
          "Specify GM recovery check parameters";
        leaf interval {
          description
            "Waiting period(sec) between consecutive recovery registrations";
          type uint16 {
            range "100..1000";
          }
        }
      }
      container registration {
        description
          "Set the group client management/register interface";
        leaf interface {
          description
            "Set the group client management/register interface";
          type string;
        }
      }
      container rekey {
        description
          "Set the group client acceptable rekey ciphers and hashs";
        container encryption {
          description
            "Set the group client acceptable rekey ciphers";
          leaf rekey-3des-cbc {
            tailf:alt-name "3des-cbc";
            type empty;
          }
          leaf aes-128 {
            tailf:alt-name "aes 128";
            description
              "128 bit AES";
            type empty;
          }
          leaf aes-192 {
            tailf:alt-name "aes 192";
            description
              "192 bit AES";
            type empty;
          }
          leaf aes-256 {
            tailf:alt-name "aes 256";
            description
              "256 bit AES";
            type empty;
          }
          leaf des-cbc {
            description
              "DES in CBC mode";
            type empty;
          }
        }
        container hash {
          description
            "Set the group client acceptable rekey hash";
          leaf sha {
            description
              "Secure Hash Standard";
            type empty;
          }
          leaf sha256 {
            description
              "Secure Hash Standard 2 (256 bit)";
            type empty;
          }
          leaf sha384 {
            description
              "Secure Hash Standard 2 (384 bit)";
            type empty;
          }
          leaf sha512 {
            description
              "Secure Hash Standard 2 (512 bit)";
            type empty;
          }
        }
      }
      container status {
        description
          "group-member status";
        container active-sa {
          description
            "TEK SA with positive remaining lifetime";
          leaf track {
            description
              "enable stub tracking object";
            type uint16 {
              range "1..1000";
            }
          }
        }
      }
      leaf-list transform-sets {
        description
          "Specify list of group client acceptable transform sets";
        type string;
      }
      leaf transport-encrypt-key {
        description
          "Enforce group or pair-wise keying";
        type enumeration {
          enum "group-key";
          enum "pair-wise-key";
        }
      }
    }
    container identity {
      description
        "Set the identity of the group";
      container address {
        description
          "Set the identity of the group as an address";
        leaf ipv4 {
          description
            "Set the identity of the group as an IPv4 address";
          type inet:ipv4-address;
        }
      }
      leaf number {
        description
          "Set the identity of the group as a number";
        type uint64;
      }
    }
    leaf passive {
      description
        "Set the group in passive mode";
      tailf:cli-full-command;
      type empty;
    }
    container server {
      description
        "Set the group server for of the group";
      container address {
        description
          "Identify the group server by address";
        leaf ipv4 {
          description
            "Set the IPv4 address of the group server";
          type inet:ipv4-address;
        }
      }
      container hostname {
        description
          "Identify the group server by hostname";
        leaf ipv4 {
          description
            "Set the IPv4 hostname of the group server";
          type string;
        }
      }
      container local {
        description
          "Configure GKM group server defined locally";
        tailf:cli-add-mode;
        tailf:cli-mode-name "gkm-local-server";
        uses crypto-gkm-local-server-grouping;
        container default {
          description
            "Set a command to its defaults";
          uses crypto-gkm-local-server-default-grouping;
        }
      }
    }
  }

  grouping crypto-gdio-default-grouping {
    container client {
      description
        "Set the group client parameters";
      leaf bypass-policy {
        description
          "Allow group-key management traffic sent to this GM only";
        tailf:cli-full-command;
        type empty;
      }
      container protocol {
        description
          "Group Member Registration & Rekey Protocol";
        presence "true";
      }
      container recovery-check {
        description
          "Specify GM recovery check parameters";
        presence "true";
      }
      container registration {
        description
          "Set the group client management/register interface";
        leaf interface {
          description
            "Set the group client management/register interface";
          type empty;
        }
      }
      container rekey {
        description
          "Set the group client acceptable rekey ciphers and hashs";
        container encryption {
          description
            "Set the group client acceptable rekey ciphers";
          presence "true";
        }
        container hash {
          description
            "Set the group client acceptable rekey hash";
          presence "true";
        }
      }
      container status {
        description
          "group-member status";
        container active-sa {
          description
            "TEK SA with positive remaining lifetime";
          presence "true";
        }
      }
      leaf transform-sets {
        description
          "Specify list of group client acceptable transform sets";
        type empty;
      }
      leaf transport-encrypt-key {
        description
          "Enforce group or pair-wise keying";
        type enumeration {
          enum "group-key";
          enum "pair-wise-key";
        }
      }
    }
    container identity {
      description
        "Set the identity of the group";
      presence "true";
    }
    leaf passive {
      description
        "Set the group in passive mode";
      tailf:cli-full-command;
      type empty;
    }
    container server {
      description
        "Set the group server for of the group";
      container address {
        description
          "Identify the group server by address";
        leaf ipv4 {
          description
            "Set the IPv4 address of the group server";
          type inet:ipv4-address;
        }
      }
      container hostname {
        description
          "Identify the group server by hostname";
        leaf ipv4 {
          description
            "Set the IPv4 hostname of the group server";
          type string;
        }
      }
      leaf local {
        description
          "Configure GKM group server defined locally";
        type empty;
      }
    }
  }

  grouping crypto-identity-grouping {
    leaf description {
      description
        "Description of the crypto identity";
      tailf:cli-multi-value;
      type string;
    }
    leaf dn {
      description
        "Distinguished name identifier";
      tailf:cli-multi-value;
      type string;
    }
    leaf fqdn {
      description
        "Fully qualified distinguished name identifier";
      tailf:cli-multi-value;
      type string;
    }
  }

  grouping crypto-identity-default-grouping {
    leaf description {
      description
        "Description of the crypto identity";
      type empty;
    }
    leaf dn {
      description
        "Distinguished name identifier";
      tailf:cli-multi-value;
      type string;
    }
    leaf fqdn {
      description
        "Fully qualified distinguished name identifier";
      tailf:cli-multi-value;
      type string;
    }
  }

  grouping crypto-ikev2-keyring-peer-grouping {
    container address {
      description
        "Specify IPv4/IPv6 address of peer";
      choice ipv4-ipv6 {
        case ipv4-case {
          container ipv4 {
            tailf:cli-drop-node-name;
            tailf:cli-sequence-commands;
            tailf:cli-compact-syntax;
            leaf ipv4-address {
              tailf:cli-drop-node-name;
              type inet:ipv4-address;
            }
            leaf ipv4-mask {
              tailf:cli-drop-node-name;
              tailf:cli-optional-in-sequence;
              type inet:ipv4-address;
            }
          }
        }
        case ipv6-case {
          leaf ipv6-prefix {
            tailf:cli-drop-node-name;
            type inet:ipv6-prefix;
          }
        }
      }
    }
    leaf description {
      description
        "Specify a description of this peer";
      tailf:cli-multi-value;
      type string;
    }
    leaf hostname {
      description
        "Hostname of peer";
      type string;
    }
    container identity {
      description
        "Specify IKE identity to use";
      leaf address {
        description
          "IP address";
        type union {
          type inet:ipv4-address;
          type inet:ipv6-address;
        }
      }
      container email {
        description
          "Use email address";
        leaf name {
          tailf:cli-drop-node-name;
          tailf:cli-full-command;
          type string;
        }
        leaf domain {
          description
            "email Domain Name";
          tailf:cli-full-command;
          type string;
        }
      }
      container fqdn {
        description
          "Use FQDN";
        leaf name {
          tailf:cli-drop-node-name;
          tailf:cli-full-command;
          type string;
        }
        leaf domain {
          description
            "email Domain Name";
          tailf:cli-full-command;
          type string;
        }
      }
      leaf key-id {
        description
          "proprietary types of identification (ID KEY ID)";
        type string;
      }
    }
    container pre-shared-key {
      description
        "specify the pre-shared key";
      tailf:cli-compact-syntax;
      leaf local {
        description
          "specify signing key";
        type empty;
      }
      leaf remote {
        description
          "specify verifying key";
        type empty;
      }
      choice encryption-hex {
        case encryption-case {
          leaf encryption {
            tailf:cli-drop-node-name;
            tailf:cli-incomplete-command;
            type enumeration {
              enum "0";
              enum "6";
            }
          }
          leaf key {
            tailf:cli-drop-node-name;
            tailf:cli-multi-value;
            type string;
          }
        }
        case hex-case {
          leaf hex {
            description
              "Key entered in hex string";
            tailf:cli-multi-value;
            type string;
          }
        }
      }
    }
  }

  grouping crypto-ikev2-profile-aaa-authorization-grouping {
    list list {
      description
        "AAA method list";
      tailf:cli-suppress-mode;
      key "name";
      leaf name {
        type string;
      }
      leaf username {
        tailf:cli-drop-node-name;
        tailf:cli-hide-in-submode;
        type string;
      }
      leaf local {
        description
          "Local AAA Authorization";
        tailf:cli-hide-in-submode;
        when "../username";
        type empty;
      }
      leaf name-mangler {
        description
          "Specify the name-mangler to derive AAA username";
        tailf:cli-hide-in-submode;
        type string;
      }
      container password {
        description
          "Specify the AAA password";
        tailf:cli-hide-in-submode;
        tailf:cli-flatten-container;
        tailf:cli-sequence-commands;
        tailf:cli-compact-syntax;
        leaf encryption {
          tailf:cli-drop-node-name;
          tailf:cli-incomplete-command;
          tailf:cli-optional-in-sequence;
          type enumeration {
            enum "0";
            enum "6";
          }
        }
        leaf key {
          tailf:cli-drop-node-name;
          tailf:cli-multi-value;
          type string;
        }
      }
    }
  }

  grouping crypto-ikev2-profile-authentication-grouping {
    leaf username {
      description
        "EAP username";
      tailf:cli-break-sequence-commands;
      tailf:cli-incomplete-command;
      type string;
    }
    container password {
      description
        "EAP password";
      tailf:cli-flatten-container;
      tailf:cli-sequence-commands;
      tailf:cli-compact-syntax;
      leaf encryption {
        tailf:cli-drop-node-name;
        tailf:cli-incomplete-command;
        tailf:cli-optional-in-sequence;
        type enumeration {
          enum "0";
          enum "6";
        }
      }
      leaf key {
        tailf:cli-drop-node-name;
        tailf:cli-multi-value;
        type string;
      }
    }
  }

  grouping crypto-ikev2-profile-authentication-key-grouping {
    container key {
      description
        "specify key";
      tailf:cli-sequence-commands;
      tailf:cli-compact-syntax;
      leaf encryption {
        tailf:cli-drop-node-name;
        tailf:cli-incomplete-command;
        tailf:cli-optional-in-sequence;
        type enumeration {
          enum "0";
          enum "6";
        }
      }
      leaf key {
        tailf:cli-drop-node-name;
        tailf:cli-multi-value;
        type string;
      }
    }
  }

  grouping crypto-ikev2-profile-grouping {
    container aaa {
      description
        "Specify AAA related configs";
      container accounting {
        description
          "AAA accounting";
        leaf anyconnect-eap {
          description
            "AAA list to use when IKEv2 remote auth method is AnyConnect EAP";
          tailf:cli-full-command;
          type string;
        }
        leaf cert {
          description
            "AAA list to use when IKEv2 remote auth method is certificate based";
          tailf:cli-full-command;
          type string;
        }
        leaf eap {
          description
            "AAA list to use when IKEv2 remote auth method is EAP";
          tailf:cli-full-command;
          type string;
        }
        leaf psk {
          description
            "AAA list to use when IKEv2 remote auth method is PSK";
          tailf:cli-full-command;
          type string;
        }
      }
      container authentication {
        description
          "AAA authentication";
        leaf anyconnect-eap {
          description
            "AAA AnyConnect EAP authentication";
          tailf:cli-full-command;
          type string;
        }
        leaf eap {
          description
            "AAA EAP authentication";
          tailf:cli-full-command;
          type string;
        }
      }
      container authorization {
        description
          "AAA authorization";
        container group {
          description
            "AAA group authorization";
          container anyconnect-eap {
            description
              "AAA list to use when IKEv2 remote auth method is anyconnect eap based";
            uses crypto-ikev2-profile-aaa-authorization-grouping;
          }
          container cert {
            description
              "AAA list to use when IKEv2 remote auth method is certificate based";
            uses crypto-ikev2-profile-aaa-authorization-grouping;
          }
          container eap {
            description
              "AAA list to use when IKEv2 remote auth method is EAP";
            uses crypto-ikev2-profile-aaa-authorization-grouping;
          }
          container psk {
            description
              "AAA list to use when IKEv2 remote auth method is PSK";
            uses crypto-ikev2-profile-aaa-authorization-grouping;
          }
          leaf override {
            description
              "Override user authorization with group authorization.By default, group authorization isoverridden with user authorization";
            tailf:cli-incomplete-command;
            type empty;
          }
        }
        container user {
          description
            "AAA user authorization";
          container anyconnect-eap {
            description
              "AAA list to use when IKEv2 remote auth method is anyconnect eap based";
            leaf cached {
              description
                "Use cached attributes from EAP authentication or AAA pre-shared key fetch";
              tailf:cli-full-command;
              type empty;
            }
            uses crypto-ikev2-profile-aaa-authorization-grouping;
          }
          container cert {
            description
              "AAA list to use when IKEv2 remote auth method is certificate based";
            uses crypto-ikev2-profile-aaa-authorization-grouping;
          }
          container eap {
            description
              "AAA list to use when IKEv2 remote auth method is EAP";
            leaf cached {
              description
                "Use cached attributes from EAP authentication or AAA pre-shared key fetch";
              tailf:cli-full-command;
              type empty;
            }
            uses crypto-ikev2-profile-aaa-authorization-grouping;
          }
          container psk {
            description
              "AAA list to use when IKEv2 remote auth method is PSK";
            leaf cached {
              description
                "Use cached attributes from EAP authentication or AAA pre-shared key fetch";
              tailf:cli-full-command;
              type empty;
            }
            uses crypto-ikev2-profile-aaa-authorization-grouping;
          }
        }
      }
    }
    container authentication {
      description
        "Set authentication method";
      container local {
        description
          "Set local authentication method";
        container eap {
          description
            "Extended Authentication Protocol";
          presence "true";
          container gtc {
            description
              "eap method gtc credentials";
            tailf:cli-sequence-commands;
            tailf:cli-compact-syntax;
            uses crypto-ikev2-profile-authentication-grouping;
          }
          container md5 {
            description
              "eap method md5 credentials";
            tailf:cli-sequence-commands;
            tailf:cli-compact-syntax;
            uses crypto-ikev2-profile-authentication-grouping;
          }
          container mschapv2 {
            description
              "eap method mschapv2 credentials";
            tailf:cli-sequence-commands;
            tailf:cli-compact-syntax;
            uses crypto-ikev2-profile-authentication-grouping;
          }
        }
        leaf ecdsa-sig {
          description
            "ECDSA Signature";
          tailf:cli-full-command;
          type empty;
        }
        container pre-share {
          description
            "Pre-Shared Key";
          presence "true";
          tailf:cli-sequence-commands;
          tailf:cli-compact-syntax;
          uses crypto-ikev2-profile-authentication-key-grouping;
        }
        leaf rsa-sig {
          description
            "Rivest-Shamir-Adleman Signature";
          tailf:cli-full-command;
          type empty;
        }
      }
      container remote {
        description
          "Set remote authentication method";
        container anyconnect-eap {
          description
            "AnyConnect EAP";
          container aggregate {
            description
              "use aggregate auth for anyconnect eap";
            presence "true";
            leaf cert-request {
              description
                "use double authentication during anyconnect eap";
              tailf:cli-full-command;
              type empty;
            }
          }
        }
        container eap {
          description
            "Extended Authentication Protocol";
          presence "true";
          leaf query-identity {
            description
              "query EAP identity from peer";
            tailf:cli-full-command;
            type empty;
          }
          leaf timeout {
            description
              "timeout";
            tailf:cli-full-command;
            type uint8 {
              range "45..180";
            }
          }
        }
        leaf ecdsa-sig {
          description
            "ECDSA Signature";
          tailf:cli-full-command;
          type empty;
        }
        container pre-share {
          description
            "Pre-Shared Key";
          presence "true";
          uses crypto-ikev2-profile-authentication-key-grouping;
        }
        leaf rsa-sig {
          description
            "Rivest-Shamir-Adleman Signature";
          tailf:cli-full-command;
          type empty;
        }
      }
    }
    container config-exchange {
      description
        "config-exchange options";
      leaf request {
        description
          "enable config-exchange request";
        tailf:cli-full-command;
        type empty;
      }
      leaf set {
        description
          "config-exchange set options";
        tailf:cli-full-command;
        type enumeration {
          enum "accept";
          enum "send";
        }
      }
    }
    leaf description {
      description
        "Specify a description of this profile";
      tailf:cli-multi-value;
      type string;
    }
    container dpd {
      description
        "Enable IKE liveness check for peers";
      tailf:cli-sequence-commands;
      tailf:cli-compact-syntax;
      leaf interval {
        tailf:cli-drop-node-name;
        type uint16 {
          range "10..3600";
        }
      }
      leaf retry {
        tailf:cli-drop-node-name;
        type uint8 {
          range "2..60";
        }
      }
      leaf query {
        tailf:cli-drop-node-name;
        type enumeration {
          enum "on-demand";
          enum "periodic";
        }
      }
    }
    container identity {
      description
        "Specify IKE identity to use";
      leaf address {
        description
          "address";
        tailf:cli-full-command;
        type inet:ip-address;
      }
      leaf dn {
        description
          "Distinguished Name";
        tailf:cli-full-command;
        type empty;
      }
      leaf email {
        description
          "Fully qualified email string";
        tailf:cli-full-command;
        type string;
      }
      leaf fqdn {
        description
          "Fully qualified domain name string";
        tailf:cli-full-command;
        type string;
      }
      leaf key-id {
        description
          "key-id opaque string - proprietary types of identification";
        tailf:cli-full-command;
        type string;
      }
    }
    container initial-contact {
      description
        "initial-contact processing options";
      leaf force {
        description
          "Enforces initial-contact based clean-up";
        tailf:cli-full-command;
        type empty;
      }
    }
    leaf ivrf {
      description
        "I-VRF of the profile";
      type string;
    }
    container keyring {
      description
        "Specify keyring to use";
      list aaa {
        description
          "AAA based keyring";
        tailf:cli-suppress-mode;
        key "name";
        leaf name {
          type string;
        }
        leaf name-mangler {
          description
            "Specify the name-mangler to derive username";
          tailf:cli-hide-in-submode;
          type string;
        }
        container password {
          description
            "Specify the AAA password";
          tailf:cli-hide-in-submode;
          tailf:cli-flatten-container;
          tailf:cli-sequence-commands;
          tailf:cli-compact-syntax;
          leaf encryption {
            tailf:cli-drop-node-name;
            tailf:cli-incomplete-command;
            tailf:cli-optional-in-sequence;
            type enumeration {
              enum "0";
              enum "6";
            }
          }
          leaf key {
            tailf:cli-drop-node-name;
            tailf:cli-multi-value;
            type string;
          }
        }
      }
      leaf local {
        description
          "Local keyring";
        type string;
      }
    }
    container lifetime {
      description
        "Set lifetime for ISAKMP security association";
      leaf seconds {
        tailf:cli-drop-node-name;
        tailf:cli-full-command;
        type uint32 {
          range "120..86400";
        }
      }
      leaf certificate {
        description
          "Enable certificate based lifetime";
        tailf:cli-full-command;
        type empty;
      }
    }
    container match {
      description
        "Match values of peer";
      container address {
        description
          "IP address";
        container local {
          description
            "Local address";
          leaf ip {
            tailf:cli-drop-node-name;
            tailf:cli-full-command;
            type inet:ip-address;
          }
          leaf interface {
            description
              "Specify an interface";
            tailf:cli-full-command;
            type string;
          }
        }
      }
      leaf certificate {
        description
          "Peer certificate attributes";
        type string;
      }
      container fvrf {
        description
          "fvrf of the profile";
        leaf name {
          tailf:cli-drop-node-name;
          tailf:cli-full-command;
          type string;
        }
        leaf any {
          description
            "Any fvrf";
          tailf:cli-full-command;
          type empty;
        }
      }
      container identity {
        description
          "IKE identity";
        container remote {
          description
            "Remote identity";
          container address {
            description
              "IP address(es)";
            choice ipv4-ipv6 {
              case ipv4-case {
                container ipv4 {
                  tailf:cli-drop-node-name;
                  tailf:cli-sequence-commands;
                  tailf:cli-compact-syntax;
                  leaf ipv4-address {
                    tailf:cli-drop-node-name;
                    type inet:ipv4-address;
                  }
                  leaf ipv4-mask {
                    tailf:cli-drop-node-name;
                    tailf:cli-optional-in-sequence;
                    type inet:ipv4-address;
                  }
                }
              }
              case ipv6-case {
                leaf ipv6-prefix {
                  tailf:cli-drop-node-name;
                  type inet:ipv6-prefix;
                }
              }
            }
          }
          leaf any {
            description
              "match any peer identity";
            tailf:cli-full-command;
            type empty;
          }
          container email {
            description
              "Fully qualified email string [Max. 255 char(s)]";
            leaf name {
              tailf:cli-drop-node-name;
              tailf:cli-full-command;
              type string;
            }
            leaf domain {
              description
                "match domain instead of exact";
              tailf:cli-full-command;
              type string;
            }
          }
          container fqdn {
            description
              "Fully qualified domain name string [Max. 255 char(s)]";
            leaf name {
              tailf:cli-drop-node-name;
              tailf:cli-full-command;
              type string;
            }
            leaf domain {
              description
                "match domain instead of exact";
              tailf:cli-full-command;
              type string;
            }
          }
          leaf key-id {
            description
              "key-id opaque string";
            type string;
          }
        }
      }
    }
    container nat {
      description
        "NAT-transparency";
      leaf keepalive {
        description
          "NAT keepalive interval";
        type uint16 {
          range "5..3600";
        }
      }
    }
    container pki {
      description
        "Specify certificate authorities to trust";
      tailf:cli-sequence-commands;
      tailf:cli-compact-syntax;
      leaf trustpoint {
        description
          "Cert authority trustpoint for RSA sig";
        type string;
      }
      leaf use {
        tailf:cli-drop-node-name;
        tailf:cli-optional-in-sequence;
        type enumeration {
          enum "sign";
          enum "verify";
        }
      }
    }
    container reconnect {
      description
        "Enable profile for auto re-connect";
      presence "true";
      leaf timeout {
        description
          "timeout value for session in reconnect state";
        type uint32 {
          range "600..86400";
        }
      }
    }
    container redirect {
      description
        "IKEv2 Redirect Mechanism for load-balancing";
      container gateway {
        description
          "Enables Redirect Mechanism on Gateway";
        leaf auth {
          description
            "Redirect at SA authentication";
          type empty;
        }
      }
    }
    leaf shutdown {
      description
        "shutdown the IKEv2 profile";
      tailf:cli-full-command;
      type empty;
    }
    container virtual-template {
      description
        "Specify the virtual-template for dynamic interface creation.";
      tailf:cli-sequence-commands;
      tailf:cli-compact-syntax;
      leaf number {
        tailf:cli-drop-node-name;
        type uint16 {
          range "1..4095";
        }
      }
      leaf mode {
        description
          "Enabling Tunnel Auto Mode";
        tailf:cli-optional-in-sequence;
        type enumeration {
          enum "auto";
        }
      }
    }
  }

  grouping crypto-ikev2-grouping {
    container authorization {
      description
        "IKEv2 authorization";
      leaf policy {
        description
          "IKEv2 authorization policy";
        type string;
      }
    }
    leaf certificate-cache {
      description
        "Cache for storing certs fetched from HTTP URLs";
      type uint16;
    }
    container client {
      description
        "IKEv2 client configuration";
      leaf flexvpn {
        description
          "Configure an IKEv2 FlexVPN client";
        type string;
      }
    }
    leaf cluster {
      description
        "Cluster load-balancer settings";
      type empty;
    }
    leaf cookie-challenge {
      description
        "Set Cookie-challenge watermark";
      type uint16;
    }
    container cts {
      description
        "Cisco Trust Security";
      leaf sgt {
        description
          "Security Group Tag";
        type empty;
      }
    }
    container diagnose {
      description
        "IKEV2 diagnose";
      leaf error {
        description
          "Start IKEv2 error trace debug";
        type uint16 {
          range "1..1000";
        }
      }
    }
    leaf disconnect-revoked-peers {
      description
        "Disconnect Crypto Session with Cert Revoked Peer";
      type empty;
    }
    container dpd-container {
      tailf:cli-drop-node-name;
      tailf:cli-sequence-commands;
      tailf:cli-compact-syntax;
      leaf dpd {
        description
          "Enable IKE liveness check for peers";
        type uint16 {
          range "10..3600";
        }
      }
      leaf retry-interval {
        tailf:cli-drop-node-name;
        type uint8 {
          range "2..60";
        }
      }
      leaf dpd-query {
        tailf:cli-drop-node-name;
        type enumeration {
          enum "on-demand";
          enum "periodic";
        }
      }
    }
    container fragmentation {
      description
        "Enable fragmentation of ikev2 packets";
      presence "true";
      leaf mtu {
        description
          "MTU size for fragmentation";
        type uint16 {
          range "68..1500";
        }
      }
    }
    container http-url {
      description
        "Enable http URL lookup";
      leaf cert {
        description
          "Enable certificate lookup based on HTTP-based URL";
        type empty;
      }
    }
    list keyring {
      description
        "Define IKEv2 Keyring";
      tailf:cli-mode-name "config-ikev2-keyring";
      key "name";
      leaf name {
        type string;
      }
      list peer {
        description
          "Configure a Peer and associated keys";
        tailf:cli-mode-name "config-ikev2-keyring-peer";
        key "name";
        leaf name {
          type string;
        }
        uses crypto-ikev2-keyring-peer-grouping;
      }
    }
    container limit {
      description
        "Limit the number of maximum and negotiating sa";
      container max-neg-sa {
        tailf:cli-drop-node-name;
        tailf:cli-sequence-commands;
        tailf:cli-compact-syntax;
        leaf max-in-negotation-sa {
          description
            "Limit the maximum number of negotiating SA";
          type uint32 {
            range "1..9999";
          }
        }
        leaf direction {
          tailf:cli-drop-node-name;
          tailf:cli-optional-in-sequence;
          type enumeration {
            enum "incoming";
            enum "outgoing";
          }
        }
      }
      leaf max-sa {
        description
          "Limit the maximum number of SA allowed";
        type uint32 {
          range "1..9999";
        }
      }
    }
    leaf name-mangler {
      description
        "Name mangler";
      type string;
    }
    container nat {
      description
        "NAT-transparency";
      leaf keepalive {
        description
          "Set NAT keepalive interval";
        type uint16 {
          range "5..3600";
        }
      }
    }
    list policy {
      description
        "Define IKEV2 policies";
      tailf:cli-mode-name "config-ikev2-policy";
      key "name";
      leaf name {
        type string;
      }
      container match {
        description
          "Match values of local fields";
        container address {
          description
            "Specify the address to match";
          leaf local {
            description
              "Local address";
            type inet:ip-address;
          }
        }
        container fvrf {
          description
            "Specify fvrf";
          leaf name {
            tailf:cli-drop-node-name;
            tailf:cli-full-command;
            type string;
          }
          leaf any {
            description
              "Any fvrf";
            tailf:cli-full-command;
            type empty;
          }
        }
      }
      leaf proposal {
        description
          "Specify Proposal";
        type string;
      }
    }
    list profile {
      description
        "Define IKEV2 profiles";
      tailf:cli-mode-name "config-ikev2-profile";
      key "name";
      leaf name {
        type string;
      }
      uses crypto-ikev2-profile-grouping;
    }
    list proposal {
      description
        "Define IKEV2 proposals";
      tailf:cli-mode-name "config-ikev2-proposal";
      key "name";
      leaf name {
        type string;
      }
      container encryption {
        description
          "Set encryption algorithm(s) for proposal";
        tailf:cli-compact-syntax;
        leaf en-3des {
          tailf:alt-name "3des";
          description
            "3DES";
          type empty;
        }
        leaf aes-cbc-128 {
          description
            "AES-CBC-128";
          type empty;
        }
        leaf aes-cbc-192 {
          description
            "AES-CBC-192";
          type empty;
        }
        leaf aes-cbc-256 {
          description
            "AES-CBC-256";
          type empty;
        }
        leaf aes-gcm-128 {
          description
            "Combined-mode,128 bit key,16 byte ICV(Authentication Tag)";
          type empty;
        }
        leaf aes-gcm-256 {
          description
            "Combined-mode,256 bit key,16 byte ICV(Authentication Tag)";
          type empty;
        }
        leaf des {
          description
            "DES";
          type empty;
        }
      }
      container group {
        description
          "Set the Diffie-Hellman group(s)";
        tailf:cli-compact-syntax;
        leaf one {
          tailf:alt-name "1";
          description
            "DH 768 MODP";
          type empty;
        }
        leaf fourteen {
          tailf:alt-name "14";
          description
            "DH 2048 MODP";
          type empty;
        }
        leaf fifteen {
          tailf:alt-name "15";
          description
            "DH 3072 MODP";
          type empty;
        }
        leaf sixteen {
          tailf:alt-name "16";
          description
            "DH 4096 MODP";
          type empty;
        }
        leaf nineteen {
          tailf:alt-name "19";
          description
            "DH 256 ECP";
          type empty;
        }
        leaf two {
          tailf:alt-name "2";
          description
            "DH 1024 MODP";
          type empty;
        }
        leaf twenty {
          tailf:alt-name "20";
          description
            "DH 384 ECP";
          type empty;
        }
        leaf twenty-one {
          tailf:alt-name "21";
          description
            "DH 521 ECP";
          type empty;
        }
        leaf twenty-four {
          tailf:alt-name "24";
          description
            "DH 2048 (256 subgroup) MODP";
          type empty;
        }
        leaf five {
          tailf:alt-name "5";
          description
            "DH 1536 MODP";
          type empty;
        }
      }
      container integrity {
        description
          "Set integrity hash algorithm(s) for proposal";
        tailf:cli-compact-syntax;
        leaf md5 {
          description
            "Message Digest 5";
          type empty;
        }
        leaf sha1 {
          description
            "Secure Hash Standard";
          type empty;
        }
        leaf sha256 {
          description
            "Secure Hash Standard 2 (256 bit)";
          type empty;
        }
        leaf sha384 {
          description
            "Secure Hash Standard 2 (384 bit)";
          type empty;
        }
        leaf sha512 {
          description
            "Secure Hash Standard 2 (512 bit)";
          type empty;
        }
      }
      container prf {
        description
          "Set prf algorithm(s) for proposal";
        tailf:cli-compact-syntax;
        leaf md5 {
          description
            "Message Digest 5";
          type empty;
        }
        leaf sha1 {
          description
            "Secure Hash Standard";
          type empty;
        }
        leaf sha256 {
          description
            "Secure Hash Standard 2 (256 bit)";
          type empty;
        }
        leaf sha384 {
          description
            "Secure Hash Standard 2 (384 bit)";
          type empty;
        }
        leaf sha512 {
          description
            "Secure Hash Standard 2 (512 bit)";
          type empty;
        }
      }
    }
    container reconnect {
      description
        "Cluster Reconnect";
      tailf:cli-sequence-commands;
      tailf:cli-compact-syntax;
      leaf key {
        description
          "Cluster Reconnect key";
        type uint8 {
          range "1..2";
        }
      }
      choice value-active {
        case value-case {
          leaf value {
            tailf:cli-drop-node-name;
            type string {
              length "1..128";
            }
          }
        }
        case active-case {
          leaf active {
            description
              "Current active cluster reconnect key";
            type string {
              length "1..128";
            }
          }
        }
      }
    }
    container redirect {
      description
        "IKEv2 Redirect Mechanism for load-balancing";
      container client {
        description
          "Enables Redirect Mechanism on Client";
        presence "true";
        leaf max-redirects {
          description
            "Redirect loop detection";
          type uint8;
        }
      }
      leaf gateway {
        description
          "Enables Redirect Mechanism on Gateway";
        type enumeration {
          enum "auth";
          enum "init";
        }
      }
    }
    leaf window {
      description
        "IKEV2 window size";
      type uint8;
    }
  }

  grouping crypto-ipsec-profile-grouping {
    leaf description {
      description
        "Description of the crypto map statement policy";
      tailf:cli-multi-value;
      type string;
    }
    container dialer {
      description
        "Dialer related commands";
      leaf pre-classify {
        description
          "Enable dialer list classification before initiating IKE";
        type empty;
      }
    }
    container redundancy {
      description
        "Configure HA for this ipsec profile";
      tailf:cli-sequence-commands;
      tailf:cli-compact-syntax;
      leaf name {
        tailf:cli-drop-node-name;
        type string;
      }
      leaf stateful {
        description
          "enable stateful failover";
        type empty;
      }
    }
    leaf responder-only {
      description
        "Do not initiate SAs from this device";
      type empty;
    }
    container set {
      description
        "Set values for encryption/decryption";
      uses crypto-map-common-set-grouping;
      leaf mixed-mode {
        description
          "Turn on IPSec mixed-mode";
        type empty;
      }
      container security-association {
        description
          "Security association parameters";
        uses crypto-map-common-set-security-association-grouping;
        leaf level {
          description
            "specify a security association granularity level for identities";
          type enumeration {
            enum "per-host";
          }
        }
      }
      container security-policy {
        description
          "Maximum number of Security Policy entries that can be negotiated with the peer";
        leaf limit {
          description
            "limit  0 - 50000";
          type uint32 {
            range "0..50000";
          }
        }
      }
    }
  }

  grouping crypto-ipsec-profile-default-grouping {
    leaf description {
      description
        "Description of the crypto map statement policy";
      type empty;
    }
    container dialer {
      description
        "Dialer related commands";
      leaf pre-classify {
        description
          "Enable dialer list classification before initiating IKE";
        type empty;
      }
    }
    leaf redundancy {
      description
        "Configure HA for this ipsec profile";
      type empty;
    }
    leaf responder-only {
      description
        "Do not initiate SAs from this device";
      type empty;
    }
    container set {
      description
        "Set values for encryption/decryption";
      leaf group {
        description
          "Set the san group parameters";
        type empty;
      }
      leaf identity {
        description
          "Identity restriction";
        type empty;
      }
      leaf ikev2-profile {
        description
          "Specify ikev2 Profile";
        type string;
      }
      leaf isakmp-profile {
        description
          "Specify isakmp Profile";
        type empty;
      }
      leaf mixed-mode {
        description
          "Turn on IPSec mixed-mode";
        type empty;
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          tailf:cli-drop-node-name;
          tailf:cli-sequence-commands;
          tailf:cli-compact-syntax;
          leaf idle-time {
            description
              "Automatically delete IPSec SAs after a given idle period.";
            type empty;
          }
          leaf default {
            description
              "All SAs idle-out reset to default peer";
            tailf:cli-optional-in-sequence;
            type empty;
          }
        }
        leaf level {
          description
            "specify a security association granularity level for identities";
          type enumeration {
            enum "per-host";
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      container security-policy {
        description
          "Maximum number of Security Policy entries that can be negotiated with the peer";
        leaf limit {
          description
            "limit  0 - 50000";
          type uint32 {
            range "0..50000";
          }
        }
      }
      leaf transform-set {
        description
          "Specify list of transform sets in priority order";
        type empty;
      }
    }
  }

  grouping crypto-ipsec-grouping {
    leaf df-bit {
      description
        "Handling of encapsulated DF bit.";
      type enumeration {
        enum "clear";
        enum "copy";
        enum "set";
      }
    }
    leaf fragmentation {
      description
        "Handling of fragmentation of near-MTU sized packets";
      type enumeration {
        enum "after-encryption";
        enum "before-encryption";
      }
    }
    leaf ipv4-deny {
      description
        "Configure global ipv4 deny policy.";
      type enumeration {
        enum "clear";
        enum "drop";
        enum "jump";
      }
    }
    leaf nat-transparency {
      description
        "IPsec NAT transparency model";
      type enumeration {
        enum "spi-matching";
        enum "udp-encapsulation";
      }
    }
    container optional {
      description
        "Enable optional encryption for IPSec";
      presence "true";
      leaf retry {
        description
          "Configure length of IPSec retry interval";
        type uint32 {
          range "60..86400";
        }
      }
    }
    list profile {
      description
        "Configure an ipsec policy profile";
      tailf:cli-mode-name "ipsec-profile";
      key "name";
      leaf name {
        type string;
      }
      container default {
        description
          "Set a command to its defaults";
        uses crypto-ipsec-profile-default-grouping;
      }
      uses crypto-ipsec-profile-grouping;
    }
    container security-association {
      description
        "Security association parameters";
      container dummy {
        description
          "Enable transmitting dummy packets";
        leaf pps {
          description
            "Simulated traffic rate (in pps)";
          type uint8 {
            range "0..25";
          }
        }
        leaf seconds {
          description
            "Simulated traffic rate (in seconds)";
          type uint16 {
            range "1..3600";
          }
        }
      }
      leaf ecn {
        description
          "Handling of ECN bit";
        type enumeration {
          enum "discard";
          enum "propagate";
        }
      }
      leaf idle-time {
        description
          "Automatically delete IPSec SAs after a given idle period.";
        type uint32 {
          range "60..86400";
        }
      }
      container lifetime {
        description
          "security association lifetime";
        leaf days {
          description
            "Time-based key duration in days";
          type uint8 {
            range "1..30";
          }
        }
        leaf kilobytes {
          description
            "Volume-based key duration";
          type union {
            type uint64 {
              range "2560..4294967295";
            }
            type enumeration {
              enum "disable";
            }
          }
        }
        leaf seconds {
          description
            "Time-based key duration in seconds";
          type uint64 {
            range "120..2592000";
          }
        }
      }
      container replay {
        description
          "Set replay checking.";
        leaf disable {
          description
            "Disable replay checking";
          type empty;
        }
        leaf window-size {
          description
            "Set replay window size.";
          type enumeration {
            enum "1024";
            enum "128";
            enum "256";
            enum "512";
            enum "64";
          }
        }
      }
    }
    list transform-set {
      description
        "Define transform and settings";
      tailf:cli-mode-name "cfg-crypto-trans";
      key "tag";
      leaf tag {
        type string;
      }
      leaf ah-hmac {
        tailf:cli-drop-node-name;
        tailf:cli-hide-in-submode;
        type enumeration {
          enum "ah-md5-hmac";
          enum "ah-sha-hmac";
          enum "ah-sha256-hmac";
          enum "ah-sha384-hmac";
          enum "ah-sha512-hmac";
        }
      }
      leaf comp-lzs {
        description
          "IP Compression using the LZS compression algorithm";
        tailf:cli-hide-in-submode;
        type empty;
      }
      leaf esp {
        tailf:cli-drop-node-name;
        tailf:cli-hide-in-submode;
        type enumeration {
          enum "esp-3des";
          enum "esp-aes";
          enum "esp-des";
          enum "esp-gcm";
          enum "esp-gmac";
          enum "esp-null";
          enum "esp-seal";
        }
      }
      leaf key-bit {
        tailf:cli-drop-node-name;
        tailf:cli-hide-in-submode;
        when "../esp = 'esp-aes'";
        type enumeration {
          enum "128";
          enum "192";
          enum "256";
        }
      }
      leaf esp-hmac {
        tailf:cli-drop-node-name;
        tailf:cli-hide-in-submode;
        type enumeration {
          enum "esp-md5-hmac";
          enum "esp-sha-hmac";
          enum "esp-sha256-hmac";
          enum "esp-sha384-hmac";
          enum "esp-sha512-hmac";
        }
      }
      container default {
        description
          "Set a command to its defaults";
        leaf mode {
          description
            "encapsulation mode (transport/tunnel)";
          type empty;
        }
      }
      container mode {
        description
          "encapsulation mode (transport/tunnel)";
        container transport {
          description
            "transport (payload encapsulation) mode";
          presence "true";
          leaf require {
            description
              "Accept only the configured encapsulation mode.";
            type empty;
          }
        }
        leaf tunnel {
          description
            "tunnel (datagram encapsulation) mode";
          type empty;
        }
      }
    }
  }

  grouping crypto-isakmp-policy-grouping {
    leaf authentication {
      description
        "Set authentication method for protection suite";
      type enumeration {
        enum "pre-share";
        enum "rsa-encr";
        enum "rsa-sig";
      }
    }
    container encryption {
      description
        "Set encryption algorithm for protection suite";
      leaf a3des {
        tailf:alt-name "3des";
        type empty;
      }
      container aes {
        description
          "AES - Advanced Encryption Standard.";
        presence "true";
        leaf key {
          tailf:cli-drop-node-name;
          type enumeration {
            enum "128";
            enum "192";
            enum "256";
          }
        }
      }
      leaf des {
        description
          "DES - Data Encryption Standard (56 bit keys).";
        type empty;
      }
    }
    leaf group {
      description
        "Set the Diffie-Hellman group";
      type enumeration {
        enum "1";
        enum "14";
        enum "15";
        enum "16";
        enum "19";
        enum "2";
        enum "20";
        enum "21";
        enum "24";
        enum "5";
      }
    }
    leaf hash {
      description
        "Set hash algorithm for protection suite";
      type enumeration {
        enum "md5";
        enum "sha";
        enum "sha256";
        enum "sha384";
        enum "sha512";
      }
    }
  }

  grouping crypto-isakmp-profile-grouping {
    leaf accounting {
      description
        "Enable AAA Accounting for IPSec Sessions";
      type string;
    }
    container ca {
      description
        "Specify certificate authorities to trust";
      leaf trust-point {
        description
          "Cert authority trustpoint for RSA sig";
        type string;
      }
    }
    container client {
      description
        "Specify client configuration settings";
      container authentication {
        description
          "Use Extended Authentication";
        leaf list {
          description
            "AAA authentication list to use";
          type string;
        }
      }
      container configuration {
        description
          "Specify client configuration settings";
        leaf address {
          description
            "Specify client network address configuration";
          type enumeration {
            enum "initiate";
            enum "respond";
          }
        }
        leaf group {
          description
            "Specify group profile attributes for client";
          type string;
        }
      }
      container pki {
        description
          "Use username in the crypto certificate for authorization";
        container authorization {
          description
            "User authorization parameters";
          leaf list {
            description
              "AAA user authorization list";
            type string;
          }
        }
      }
    }
    leaf description {
      description
        "Specify a description of this profile";
      tailf:cli-multi-value;
      type string;
    }
    container initiate {
      description
        "Initiator property";
      container mode {
        description
          "Phase 1 negotiation mode to use";
        presence "true";
        leaf aggressive {
          description
            "Start agressive mode negotiation";
          type empty;
        }
      }
    }
    container isakmp {
      description
        "ISAKMP Authorization command";
      container authorization {
        description
          "Authorization parameters.";
        leaf list {
          description
            "AAA authorization list to use";
          type string;
        }
      }
    }
    container keepalive {
      description
        "Set a keepalive interval for use with IOS peers";
      tailf:cli-sequence-commands;
      tailf:cli-compact-syntax;
      leaf number {
        tailf:cli-drop-node-name;
        type uint16 {
          range "10..3600";
        }
      }
      leaf retry {
        description
          "Retry interval if keepalive fails";
        type uint8 {
          range "2..60";
        }
      }
    }
    leaf keyring {
      description
        "Specify keyring to use";
      type union {
        type string;
        type enumeration {
          enum "default";
        }
      }
    }
    leaf local-address {
      description
        "Interface to use for local address for this isakmp profile";
      type string;
    }
    container match {
      description
        "Match values of peer";
      leaf certificate {
        description
          "Peer certificate attributes";
        type string;
      }
      container identity {
        description
          "Peer identity";
        container ipv4-address {
          tailf:cli-drop-node-name;
          tailf:cli-sequence-commands;
          tailf:cli-compact-syntax;
          leaf address {
            description
              "IP Address(es)";
            type inet:ipv4-address;
          }
          leaf mask {
            tailf:cli-drop-node-name;
            tailf:cli-break-sequence-commands;
            type inet:ipv4-address;
          }
          leaf vrf {
            tailf:cli-drop-node-name;
            type string;
          }
        }
        container address {
          description
            "IP Address(es)";
          tailf:cli-sequence-commands;
          tailf:cli-compact-syntax;
          leaf ipv6 {
            description
              "IPv6 Address(es)";
            type inet:ipv6-prefix;
          }
          leaf vrf {
            tailf:cli-drop-node-name;
            tailf:cli-optional-in-sequence;
            type string;
          }
        }
        leaf group {
          description
            "Group name";
          type string;
        }
        container host {
          description
            "match a hostname/domain";
          container domain-name {
            tailf:cli-drop-node-name;
            tailf:cli-sequence-commands;
            tailf:cli-compact-syntax;
            leaf name {
              tailf:cli-drop-node-name;
              type string;
            }
            leaf vrf {
              tailf:cli-drop-node-name;
              tailf:cli-optional-in-sequence;
              type string;
            }
          }
          container domain-match {
            tailf:cli-drop-node-name;
            tailf:cli-sequence-commands;
            tailf:cli-compact-syntax;
            leaf domain {
              description
                "match domain instead of exact";
              type string;
            }
            leaf vrf {
              tailf:cli-drop-node-name;
              tailf:cli-optional-in-sequence;
              type string;
            }
          }
        }
        container user-fqdn {
          description
            "match a hostname/domain";
          container domain-name {
            tailf:cli-drop-node-name;
            tailf:cli-sequence-commands;
            tailf:cli-compact-syntax;
            leaf name {
              tailf:cli-drop-node-name;
              type string;
            }
            leaf vrf {
              tailf:cli-drop-node-name;
              tailf:cli-optional-in-sequence;
              type string;
            }
          }
          container domain-match {
            tailf:cli-drop-node-name;
            tailf:cli-sequence-commands;
            tailf:cli-compact-syntax;
            leaf domain {
              description
                "match domain instead of exact";
              type string;
            }
            leaf vrf {
              tailf:cli-drop-node-name;
              tailf:cli-optional-in-sequence;
              type string;
            }
          }
        }
      }
    }
    leaf qos-group {
      description
        "Apply a Qos policy class map for this profile";
      type uint16 {
        range "1..1023";
      }
    }
    container self-identity {
      description
        "Specify Identity to use";
      container address {
        description
          "Use IPv4 address";
        presence "true";
        leaf ipv6 {
          description
            "Use IPv6 address";
          type empty;
        }
      }
      container fqdn {
        description
          "Use FQDN";
        presence "true";
        leaf id {
          tailf:cli-drop-node-name;
          type string;
        }
      }
      leaf user-fqdn {
        description
          "Use user FQDN";
        type string;
      }
    }
    leaf virtual-template {
      description
        "Specify the virtual-template for dynamic interface creation.";
      type uint16 {
        range "1..4095";
      }
    }
    leaf vrf {
      description
        "Specify the VRF it is related to";
      type string;
    }
  }

  grouping crypto-isakmp-profile-default-grouping {
    leaf accounting {
      description
        "Enable AAA Accounting for IPSec Sessions";
      type empty;
    }
    container ca {
      description
        "Specify certificate authorities to trust";
      leaf trust-point {
        description
          "Cert authority trustpoint for RSA sig";
        type string;
      }
    }
    container client {
      description
        "Specify client configuration settings";
      container authentication {
        description
          "Use Extended Authentication";
        leaf list {
          description
            "AAA authentication list to use";
          type empty;
        }
      }
      container configuration {
        description
          "Specify client configuration settings";
        leaf address {
          description
            "Specify client network address configuration";
          type enumeration {
            enum "initiate";
            enum "respond";
          }
        }
        leaf group {
          description
            "Specify group profile attributes for client";
          type string;
        }
      }
      container pki {
        description
          "Use username in the crypto certificate for authorization";
        container authorization {
          description
            "User authorization parameters";
          presence "true";
        }
      }
    }
    leaf description {
      description
        "Specify a description of this profile";
      tailf:cli-multi-value;
      type string;
    }
    container initiate {
      description
        "Initiator property";
      container mode {
        description
          "Phase 1 negotiation mode to use";
        presence "true";
      }
    }
    container isakmp {
      description
        "ISAKMP Authorization command";
      container authorization {
        description
          "Authorization parameters.";
        leaf list {
          description
            "AAA authorization list to use";
          type empty;
        }
      }
    }
    container keepalive {
      description
        "Set a keepalive interval for use with IOS peers";
      presence "true";
    }
    leaf keyring {
      description
        "Specify keyring to use";
      type union {
        type string;
        type enumeration {
          enum "default";
        }
      }
    }
    leaf local-address {
      description
        "Interface to use for local address for this isakmp profile";
      type empty;
    }
    container match {
      description
        "Match values of peer";
      leaf certificate {
        description
          "Peer certificate attributes";
        type string;
      }
      container identity {
        description
          "Peer identity";
        container ipv4-address {
          tailf:cli-drop-node-name;
          tailf:cli-sequence-commands;
          tailf:cli-compact-syntax;
          leaf address {
            description
              "IP Address(es)";
            type inet:ipv4-address;
          }
          leaf mask {
            tailf:cli-drop-node-name;
            tailf:cli-break-sequence-commands;
            type inet:ipv4-address;
          }
          leaf vrf {
            tailf:cli-drop-node-name;
            type string;
          }
        }
        container address {
          description
            "IP Address(es)";
          tailf:cli-sequence-commands;
          tailf:cli-compact-syntax;
          leaf ipv6 {
            description
              "IPv6 Address(es)";
            type inet:ipv6-prefix;
          }
          leaf vrf {
            tailf:cli-drop-node-name;
            tailf:cli-optional-in-sequence;
            type string;
          }
        }
        leaf group {
          description
            "Group name";
          type string;
        }
        container host {
          description
            "match a hostname/domain";
          container domain-name {
            tailf:cli-drop-node-name;
            tailf:cli-sequence-commands;
            tailf:cli-compact-syntax;
            leaf name {
              tailf:cli-drop-node-name;
              type string;
            }
            leaf vrf {
              tailf:cli-drop-node-name;
              tailf:cli-optional-in-sequence;
              type string;
            }
          }
          container domain-match {
            tailf:cli-drop-node-name;
            tailf:cli-sequence-commands;
            tailf:cli-compact-syntax;
            leaf domain {
              description
                "match domain instead of exact";
              type string;
            }
            leaf vrf {
              tailf:cli-drop-node-name;
              tailf:cli-optional-in-sequence;
              type string;
            }
          }
        }
        container user-fqdn {
          description
            "match a hostname/domain";
          container domain-name {
            tailf:cli-drop-node-name;
            tailf:cli-sequence-commands;
            tailf:cli-compact-syntax;
            leaf name {
              tailf:cli-drop-node-name;
              type string;
            }
            leaf vrf {
              tailf:cli-drop-node-name;
              tailf:cli-optional-in-sequence;
              type string;
            }
          }
          container domain-match {
            tailf:cli-drop-node-name;
            tailf:cli-sequence-commands;
            tailf:cli-compact-syntax;
            leaf domain {
              description
                "match domain instead of exact";
              type string;
            }
            leaf vrf {
              tailf:cli-drop-node-name;
              tailf:cli-optional-in-sequence;
              type string;
            }
          }
        }
      }
    }
    leaf qos-group {
      description
        "Apply a Qos policy class map for this profile";
      type empty;
    }
    container self-identity {
      description
        "Specify Identity to use";
      presence "true";
    }
    leaf virtual-template {
      description
        "Specify the virtual-template for dynamic interface creation.";
      type empty;
    }
    leaf vrf {
      description
        "Specify the VRF it is related to";
      type empty;
    }
  }

  grouping crypto-isakmp-client-configuration-group-grouping {
    leaf access-restrict {
      description
        "Restrict clients in this group to an interface";
      type string;
    }
    leaf acl {
      description
        "Specify split tunneling inclusion access-list number";
      type union {
        type uint16 {
          range "100..199";
        }
        type string {
          pattern "[a-zA-Z].*";
        }
      }
    }
    container auto-update {
      description
        "Configure auto-upgrade";
      tailf:cli-sequence-commands;
      tailf:cli-compact-syntax;
      leaf client {
        description
          "Configure client";
        type string;
      }
      leaf url {
        description
          "Configure URL to download from";
        type string;
      }
      leaf rev {
        description
          "Use comma delimited list of revision strings only";
        type string;
      }
    }
    leaf backup-gateway {
      description
        "Specify backup gateway";
      type string;
    }
    leaf banner {
      description
        "Specify mode config banner";
      tailf:cli-multi-value;
      type string;
    }
    leaf browser-proxy {
      description
        "Configure browser-proxy";
      type string;
    }
    container configuration {
      description
        "Push configuration to the client";
      leaf url {
        description
          "URL for the client to fetch configuration";
        type enumeration {
          enum "bootflash:";
          enum "cns:";
          enum "flash:";
          enum "ftp:";
          enum "http:";
          enum "https:";
          enum "null:";
          enum "nvram:";
          enum "pram:";
          enum "rcp:";
          enum "scp:";
          enum "system:";
          enum "tar:";
          enum "tftp:";
          enum "tmpsys:";
        }
      }
      leaf version {
        description
          "version of the configuration available at the URL";
        type uint32 {
          range "1..32767";
        }
      }
    }
    container crypto {
      description
        "Client group crypto aaa attribute list";
      container aaa {
        description
          "AAA directive";
        container attribute {
          description
            "AAA attribute directive";
          leaf list {
            description
              "AAA attribute list";
            type string;
          }
        }
      }
    }
    container dhcp {
      description
        "Configure DHCP parameters";
      leaf giaddr {
        description
          "Specify giaddr for dhcp scope";
        type inet:ipv4-address;
      }
      leaf server {
        description
          "Specify dhcp server";
        type union {
          type inet:ipv4-address;
          type string;
        }
      }
      leaf timeout {
        description
          "Configure DHCP response timeout in seconds";
        type uint8 {
          range "4..30";
        }
      }
    }
    container dns {
      description
        "Specify DNS Addresses";
      tailf:cli-sequence-commands;
      tailf:cli-compact-syntax;
      leaf primary {
        tailf:cli-drop-node-name;
        type inet:ipv4-address;
      }
      leaf secondary {
        tailf:cli-drop-node-name;
        type inet:ipv4-address;
      }
    }
    leaf domain {
      description
        "Set default domain name to send to client";
      type string;
    }
    container firewall {
      description
        "Enforce group firewall feature";
      leaf are-u-there {
        description
          "firewall attribute, are-u-there";
        type empty;
      }
      leaf policy {
        description
          "Specify firewall policy";
        type string;
      }
    }
    leaf group-lock {
      description
        "Enforce group lock feature";
      type empty;
    }
    leaf include-local-lan {
      description
        "Enable Local LAN Access with no split tunnel";
      type empty;
    }
    container key {
      description
        "pre-shared key/IKE password";
      tailf:cli-sequence-commands;
      tailf:cli-compact-syntax;
      leaf encryption {
        tailf:cli-drop-node-name;
        tailf:cli-incomplete-command;
        tailf:cli-optional-in-sequence;
        type enumeration {
          enum "0";
          enum "6";
        }
      }
      leaf key {
        tailf:cli-drop-node-name;
        tailf:cli-multi-value;
        type string;
      }
    }
    leaf max-logins {
      description
        "Set maximum simultaneous logins for users in this group";
      type uint8 {
        range "1..10";
      }
    }
    leaf max-users {
      description
        "Set maximum number of users for this group";
      type uint32 {
        range "1..5000";
      }
    }
    leaf netmask {
      description
        "netmask used by the client for local connectivity";
      type inet:ipv4-address;
    }
    leaf pfs {
      description
        "The client should propose PFS";
      type empty;
    }
    leaf pool {
      description
        "Set name of address pool";
      type string;
    }
    leaf save-password {
      description
        "Allows remote client to save XAUTH password";
      type empty;
    }
    leaf smartcard-removal-disconnect {
      description
        "Enables smartcard-removal-disconnect";
      type empty;
    }
    leaf split-dns {
      description
        "DNS name to append for resolution";
      type string;
    }
    container wins {
      description
        "Specify WINS Addresses";
      tailf:cli-sequence-commands;
      tailf:cli-compact-syntax;
      leaf primary {
        tailf:cli-drop-node-name;
        type inet:ipv4-address;
      }
      leaf secondary {
        tailf:cli-drop-node-name;
        type inet:ipv4-address;
      }
    }
  }

  grouping crypto-isakmp-peer-grouping {
    leaf description {
      description
        "IKE peer specific description";
      tailf:cli-multi-value;
      type string {
        length "1..80";
      }
    }
    container set {
      description
        "set peer policy attributes";
      container aggressive-mode {
        description
          "aggressive mode attributes";
        container client-endpoint {
          description
            "specify a tunnel-client-endpoint attribute";
          leaf fqdn {
            description
              "Use the fqdn as tunnel-client-endpoint";
            tailf:cli-full-command;
            type string;
          }
          leaf ipv4-address {
            description
              "Use the IP address as tunnel-client-endpoint";
            tailf:cli-full-command;
            type inet:ipv4-address;
          }
          leaf ipv6-address {
            description
              "Use the IPv6 address as tunnel-client-endpoint";
            tailf:cli-full-command;
            type inet:ipv6-address;
          }
          leaf user-fqdn {
            description
              "Use the user-fqdn as tunnel-client-endpoint";
            tailf:cli-full-command;
            type string;
          }
        }
        container password {
          description
            "specify a tunnel-password attribute";
          tailf:cli-sequence-commands;
          tailf:cli-compact-syntax;
          leaf encryption {
            tailf:cli-drop-node-name;
            tailf:cli-incomplete-command;
            tailf:cli-optional-in-sequence;
            type enumeration {
              enum "0";
              enum "6";
            }
          }
          leaf key {
            tailf:cli-drop-node-name;
            tailf:cli-multi-value;
            type string;
          }
        }
      }
    }
  }

  grouping crypto-isakmp-grouping {
    leaf aggressive-mode {
      description
        "Disable ISAKMP aggressive mode";
      type enumeration {
        enum "disable";
      }
    }
    container client {
      description
        "Set client configuration policy";
      container configuration {
        description
          "Set client configuration policy";
        container address-pool {
          description
            "Set network address for client";
          leaf local {
            description
              "Set a local address pool for clients";
            type string;
          }
        }
        leaf browser-proxy {
          description
            "Set browser proxy attributes for client";
          type string;
        }
        list group {
          description
            "Set group profile attributes for client";
          tailf:cli-mode-name "config-isakmp-group";
          key "name";
          leaf name {
            type string;
          }
          uses crypto-isakmp-client-configuration-group-grouping;
        }
      }
      list firewall {
        description
          "Define client firewall";
        tailf:cli-mode-name "config-ikmp-client-fw";
        key "policy-name";
        leaf policy-name {
          type string;
        }
        leaf optional {
          description
            "firewall policy is optional";
          tailf:cli-hide-in-submode;
          type enumeration {
            enum "cisco-integrated-client-firewall";
            enum "cisco-security-agent";
            enum "zonelabs-zonealarm";
            enum "zonelabs-zonealarmpro";
          }
        }
        leaf required {
          description
            "firewall policy is mandatory";
          tailf:cli-hide-in-submode;
          type enumeration {
            enum "cisco-integrated-client-firewall";
            enum "cisco-security-agent";
            enum "zonelabs-zonealarm";
            enum "zonelabs-zonealarmpro";
          }
        }
        container policy {
          description
            "Define Cisco firewall Policy";
          container central-policy-push {
            description
              "Define Cisco Protection Policy";
            when "../../optional = 'cisco-integrated-client-firewall' or ../../required = 'cisco-integrated-client-firewall' or ../../optional = 'zonelabs-zonealarm' or ../../required = 'zonelabs-zonealarm' or ../../optional = 'zonelabs-zonealarmpro' or ../../required = 'zonelabs-zonealarmpro'";
            container access-list {
              description
                "Specify access list";
              tailf:cli-sequence-commands;
              tailf:cli-compact-syntax;
              leaf direction {
                tailf:cli-drop-node-name;
                type enumeration {
                  enum "in";
                  enum "out";
                }
              }
              leaf acl {
                tailf:cli-drop-node-name;
                type union {
                  type uint16 {
                    range "100..199";
                  }
                  type string {
                    pattern "[a-zA-Z].*";
                  }
                }
              }
            }
          }
          leaf check-presence {
            description
              "Define firewall are-you-there policy";
            when "../../optional = 'cisco-security-agent' or ../../required = 'cisco-security-agent' or ../../optional = 'zonelabs-zonealarm' or ../../required = 'zonelabs-zonealarm' or ../../optional = 'zonelabs-zonealarmpro' or ../../required = 'zonelabs-zonealarmpro'";
            type empty;
          }
        }
      }
    }
    container default {
      description
        "ISAKMP default policy";
      leaf policy {
        description
          "Enable default policies for ISAKMP protection suite";
        type empty;
      }
    }
    leaf disconnect-revoked-peers {
      description
        "Disconnect Crypto Session with Revoked Peer";
      type empty;
    }
    leaf enable {
      description
        "Enable ISAKMP";
      type empty;
    }
    leaf fragmentation {
      description
        "IKE Fragmentation enabled if required";
      type empty;
    }
    leaf identity {
      description
        "Set the identity which ISAKMP will use";
      type enumeration {
        enum "address";
        enum "dn";
        enum "hostname";
      }
    }
    leaf invalid-spi-recovery {
      description
        "Initiate IKE and send Invalid SPI Notify";
      type empty;
    }
    container keepalive {
      description
        "Set a keepalive interval for use with IOS peers";
      tailf:cli-sequence-commands;
      tailf:cli-compact-syntax;
      leaf number {
        tailf:cli-drop-node-name;
        type uint16 {
          range "10..3600";
        }
      }
      leaf retry-number {
        tailf:cli-drop-node-name;
        tailf:cli-break-sequence-commands;
        type uint8 {
          range "2..60";
        }
      }
      leaf send {
        tailf:cli-drop-node-name;
        type enumeration {
          enum "on-demand";
          enum "periodic";
        }
      }
    }
    container key {
      description
        "Set pre-shared key for remote peer";
      container key-address {
        tailf:cli-drop-node-name;
        tailf:cli-sequence-commands;
        tailf:cli-compact-syntax;
        leaf encryption {
          tailf:cli-drop-node-name;
          tailf:cli-incomplete-command;
          tailf:cli-optional-in-sequence;
          type enumeration {
            enum "0";
            enum "6";
          }
        }
        leaf key {
          tailf:cli-drop-node-name;
          type string;
        }
        choice ipv4-ipv6 {
          case ipv4 {
            container addr4-container {
              tailf:cli-drop-node-name;
              tailf:cli-flatten-container;
              tailf:cli-sequence-commands;
              tailf:cli-compact-syntax;
              leaf address {
                description
                  "define shared key with IP address";
                type inet:ipv4-address;
              }
              leaf mask {
                tailf:cli-drop-node-name;
                tailf:cli-break-sequence-commands;
                type inet:ipv4-address;
              }
              leaf no-xauth {
                description
                  "Bypasses XAuth for this peer";
                type empty;
              }
            }
          }
          case ipv6 {
            container addr6-container {
              tailf:cli-drop-node-name;
              tailf:cli-flatten-container;
              container address {
                description
                  "define shared key with IP address";
                tailf:cli-sequence-commands;
                tailf:cli-compact-syntax;
                leaf ipv6 {
                  description
                    "define shared key with IPv6 address";
                  type inet:ipv6-prefix;
                }
                leaf no-xauth {
                  description
                    "Bypasses XAuth for this peer";
                  tailf:cli-break-sequence-commands;
                  type empty;
                }
              }
            }
          }
        }
      }
      container key-host {
        tailf:cli-drop-node-name;
        tailf:cli-sequence-commands;
        tailf:cli-compact-syntax;
        leaf encryption {
          tailf:cli-drop-node-name;
          tailf:cli-incomplete-command;
          tailf:cli-optional-in-sequence;
          type enumeration {
            enum "0";
            enum "6";
          }
        }
        leaf key {
          tailf:cli-drop-node-name;
          type string;
        }
        container host-container {
          tailf:cli-drop-node-name;
          tailf:cli-flatten-container;
          tailf:cli-sequence-commands;
          tailf:cli-compact-syntax;
          leaf hostname {
            description
              "define shared key with hostname";
            type string;
          }
          leaf no-xauth {
            description
              "Bypasses XAuth for this peer";
            tailf:cli-break-sequence-commands;
            type empty;
          }
        }
      }
    }
    container nat {
      description
        "Set a nat  keepalive interval for use with IOS peers";
      leaf keepalive {
        description
          "Set a nat keepalive interval for use with IOS peers";
        type uint16 {
          range "5..3600";
        }
      }
    }
    container peer {
      description
        "Set Peer Policy";
      container ipv4-addr {
        tailf:cli-drop-node-name;
        list address {
          description
            "define peer policy for IP address";
          tailf:cli-mode-name "config-isakmp-peer";
          key "ipv4";
          leaf ipv4 {
            type inet:ipv4-address;
          }
          leaf vrf {
            description
              "specify front door vrf of the peer";
            tailf:cli-hide-in-submode;
            type string;
          }
          uses crypto-isakmp-peer-grouping;
        }
      }
      container ipv6-addr {
        tailf:cli-drop-node-name;
        list address {
          description
            "define peer policy for IP address";
          tailf:cli-mode-name "config-isakmp-peer";
          key "ipv6";
          leaf ipv6 {
            description
              "define peer policy for IPv6 address";
            tailf:cli-expose-key-name;
            type inet:ipv6-address;
          }
          leaf vrf {
            description
              "specify front door vrf of the peer";
            tailf:cli-hide-in-submode;
            type string;
          }
          uses crypto-isakmp-peer-grouping;
        }
      }
      list hostname {
        description
          "hostname  define peer policy for hostname";
        tailf:cli-mode-name "config-isakmp-peer";
        key "name";
        leaf name {
          type string;
        }
        leaf vrf {
          description
            "specify front door vrf of the peer";
          tailf:cli-hide-in-submode;
          type string;
        }
        uses crypto-isakmp-peer-grouping;
      }
    }
    list policy {
      description
        "Set policy for an ISAKMP protection suite";
      tailf:cli-mode-name "config-isakmp";
      key "number";
      leaf number {
        type uint32 {
          range "1..10000";
        }
      }
      container default {
        description
          "Set a command to its defaults";
        uses crypto-isakmp-policy-grouping;
        leaf lifetime {
          description
            "Set lifetime for ISAKMP security association";
          type empty;
        }
      }
      uses crypto-isakmp-policy-grouping;
      leaf lifetime {
        description
          "Set lifetime for ISAKMP security association";
        type uint32 {
          range "60..86400";
        }
      }
    }
    list profile {
      description
        "Define ISAKMP Profiles";
      tailf:cli-mode-name "conf-isa-prof";
      key "name";
      leaf name {
        type string;
      }
      container default {
        description
          "Set a command to its defaults";
        uses crypto-isakmp-profile-default-grouping;
      }
      uses crypto-isakmp-profile-grouping;
    }
    container xauth {
      description
        "Set Extended Authentication values";
      leaf timeout {
        description
          "Set Extended Authentication timeout";
        type uint8 {
          range "5..90";
        }
      }
    }
  }

  grouping crypto-key-decrypt-rc-rsa-np-grouping {
    leaf name {
      description
        "Name of keypair to decrypt.";
      type string;
    }
    leaf passphrase {
      description
        "decryption key.";
      tailf:cli-multi-value;
      type string;
    }
  }

  grouping crypto-key-decrypt-rc-rsa-grouping {
    container ec {
      description
        "EC keys";
      presence "true";
      uses crypto-key-decrypt-rc-rsa-np-grouping;
    }
    container rsa {
      description
        "RSA keys";
      presence "true";
      uses crypto-key-decrypt-rc-rsa-np-grouping;
    }
  }

  grouping crypto-key-encrypt-rc-rsa-np-grouping {
    leaf name {
      description
        "Name of keypair to encrypt.";
      type string;
    }
    leaf passphrase {
      description
        "encryption key.";
      tailf:cli-multi-value;
      type string;
    }
  }

  grouping crypto-key-encrypt-rc-rsa-grouping {
    container ec {
      description
        "EC keys";
      presence "true";
      uses crypto-key-encrypt-rc-rsa-np-grouping;
    }
    container rsa {
      description
        "RSA keys";
      presence "true";
      uses crypto-key-encrypt-rc-rsa-np-grouping;
    }
  }

  grouping crypto-key-url-file-ex-grouping {
    leaf file {
      tailf:cli-drop-node-name;
      type enumeration {
        enum "bootflash:";
        enum "flash:";
        enum "ftp:";
        enum "http:";
        enum "https:";
        enum "null:";
        enum "nvram:";
        enum "pram:";
        enum "rcp:";
        enum "scp:";
        enum "system:";
        enum "tftp:";
        enum "tmpsys:";
      }
    }
  }

  grouping crypto-key-url-file-im-grouping {
    leaf file {
      tailf:cli-drop-node-name;
      type enumeration {
        enum "bootflash:";
        enum "cns:";
        enum "flash:";
        enum "ftp:";
        enum "http:";
        enum "https:";
        enum "null:";
        enum "nvram:";
        enum "pram:";
        enum "rcp:";
        enum "scp:";
        enum "system:";
        enum "tar:";
        enum "tftp:";
        enum "tmpsys:";
      }
    }
  }

  grouping crypto-key-export-pem-grouping {
    container pem {
      description
        "File type to export";
      tailf:cli-flatten-container;
      choice terminal-url {
        case terminal-case {
          container terminal {
            description
              "Export via the terminal (cut-and-paste)";
            choice des-3des {
              case pk-3des-case {
                leaf pk-3des {
                  tailf:alt-name "3des";
                  description
                    "Encrypt the private key with 3DES";
                  tailf:cli-multi-value;
                  tailf:cli-optional-in-sequence;
                  tailf:cli-full-command;
                  type string;
                }
              }
              case des-case {
                leaf des {
                  description
                    "Encrypt the private key with DES";
                  tailf:cli-multi-value;
                  tailf:cli-full-command;
                  type string;
                }
              }
            }
          }
        }
        case url-case {
          container url {
            description
              "Export via the file systems";
            tailf:cli-sequence-commands;
            tailf:cli-compact-syntax;
            uses crypto-key-url-file-ex-grouping;
            choice des-3des {
              case url-3des-case {
                leaf url-3des {
                  tailf:alt-name "3des";
                  description
                    "Encrypt the private key with 3DES";
                  tailf:cli-multi-value;
                  tailf:cli-optional-in-sequence;
                  tailf:cli-full-command;
                  type string;
                }
              }
              case des-case {
                leaf des {
                  description
                    "Encrypt the private key with DES";
                  tailf:cli-multi-value;
                  tailf:cli-full-command;
                  type string;
                }
              }
            }
          }
        }
      }
    }
  }

  grouping crypto-key-pubkey-key-grouping {
    leaf address {
      description
        "Assign an address to the key";
      type inet:ipv4-address;
    }
    container key-string {
      description
        "Key data";
      tailf:cli-add-mode;
      tailf:cli-mode-name "config-pubkey";
      leaf hex-data {
        tailf:cli-drop-node-name;
        tailf:cli-multi-value;
        tailf:cli-full-command;
        type string;
      }
      leaf quit {
        description
          "Exit data entry mode";
        tailf:cli-full-command;
        type empty;
      }
    }
    leaf serial-number {
      description
        "Serial number of the device";
      type string;
    }
  }

  grouping crypto-key-pubkey-key-default-grouping {
    leaf address {
      description
        "Assign an address to the key";
      type empty;
    }
    container key-string {
      description
        "Key data";
      presence "true";
    }
    leaf serial-number {
      description
        "Serial number of the device";
      type empty;
    }
  }

  grouping crypto-key-pubkey-chain-grouping {
    list addressed-key {
      description
        "Public key associated with an address";
      tailf:cli-mode-name "config-pubkey-key";
      key "ip";
      leaf ip {
        type inet:ipv4-address;
      }
      leaf use {
        tailf:cli-drop-node-name;
        tailf:cli-hide-in-submode;
        type enumeration {
          enum "encryption";
          enum "signature";
        }
      }
      uses crypto-key-pubkey-key-grouping;
      container default {
        description
          "Set a command to its defaults";
        uses crypto-key-pubkey-key-default-grouping;
      }
    }
    list named-key {
      description
        "Public key associated with a name";
      tailf:cli-mode-name "config-pubkey-key";
      key "name";
      leaf name {
        type string;
      }
      leaf use {
        tailf:cli-drop-node-name;
        tailf:cli-hide-in-submode;
        type enumeration {
          enum "encryption";
          enum "signature";
        }
      }
      uses crypto-key-pubkey-key-grouping;
      container default {
        description
          "Set a command to its defaults";
        uses crypto-key-pubkey-key-default-grouping;
      }
    }
  }

  grouping crypto-key-pubkey-chain-default-grouping {
    list addressed-key {
      description
        "Public key associated with an address";
      tailf:cli-suppress-mode;
      key "ip";
      leaf ip {
        type inet:ipv4-address;
      }
      leaf use {
        tailf:cli-drop-node-name;
        tailf:cli-hide-in-submode;
        type enumeration {
          enum "encryption";
          enum "signature";
        }
      }
    }
    list named-key {
      description
        "Public key associated with a name";
      tailf:cli-suppress-mode;
      key "name";
      leaf name {
        type string;
      }
      leaf use {
        tailf:cli-drop-node-name;
        tailf:cli-hide-in-submode;
        type enumeration {
          enum "encryption";
          enum "signature";
        }
      }
    }
  }

  grouping crypto-key-grouping {
    container decrypt {
      description
        "Decrypt a keypair.";
      uses crypto-key-decrypt-rc-rsa-grouping;
      container write {
        description
          "Will write the configuration to startup-config.";
        uses crypto-key-decrypt-rc-rsa-grouping;
      }
    }
    container encrypt {
      description
        "Encrypt a keypair.";
      uses crypto-key-encrypt-rc-rsa-grouping;
      container write {
        description
          "Will write the configuration to startup-config.";
        uses crypto-key-encrypt-rc-rsa-grouping;
      }
    }
    container export {
      description
        "Export keys";
      list ec {
        description
          "Export EC keys";
        tailf:cli-suppress-mode;
        key "label";
        leaf label {
          type string;
        }
        uses crypto-key-export-pem-grouping;
      }
      list rsa {
        description
          "Export RSRA keys";
        tailf:cli-suppress-mode;
        key "label";
        leaf label {
          type string;
        }
        uses crypto-key-export-pem-grouping;
      }
    }
    container generate {
      description
        "Generate new keys";
      container ec {
        description
          "Generate EC keys for ECDSA";
        tailf:cli-sequence-commands;
        tailf:cli-compact-syntax;
        leaf keysize {
          description
            "Number of bits";
          type enumeration {
            enum "256";
            enum "384";
          }
        }
        leaf exportable {
          description
            "Allow key to be exported";
          tailf:cli-break-sequence-commands;
          type empty;
        }
        leaf label {
          description
            "Provide a label";
          tailf:cli-full-command;
          type string;
        }
      }
      container rsa {
        description
          "Generate RSA keys";
        tailf:cli-compact-syntax;
        presence "true";
        leaf encryption {
          description
            "Generate a general purpose RSA key pair for signing and encryption";
          type empty;
        }
        leaf exportable {
          description
            "Allow the key to be exported";
          type empty;
        }
        leaf general-keys {
          description
            "Generate a general purpose RSA key pair for signing and encryption";
          type empty;
        }
        leaf label {
          description
            "Provide a label";
          type string;
        }
        leaf modulus {
          description
            "Provide number of modulus bits on the command line";
          type uint16 {
            range "360..4096";
          }
        }
        leaf on {
          description
            "create key on specified device.";
          type string;
        }
        leaf redundancy {
          description
            "Allow the key to be synced to high-availability peer";
          type empty;
        }
        leaf signature {
          description
            "Generate a general purpose RSA key pair for signing and encryption";
          type empty;
        }
        leaf storage {
          description
            "Store key on specified device";
          type string;
        }
        leaf usage-keys {
          description
            "Generate separate RSA key pairs for signing and encryption";
          type empty;
        }
      }
    }
    container import {
      description
        "Import keys";
      list ec {
        description
          "Import EC keys";
        tailf:cli-suppress-mode;
        key "name";
        leaf name {
          type string;
        }
        leaf exportable {
          description
            "Allow key to be exported";
          tailf:cli-hide-in-submode;
          type empty;
        }
        choice terminal-url {
          case terminal-case {
            leaf terminal {
              description
                "Import via the terminal (cut-and-paste)";
              tailf:cli-multi-value;
              tailf:cli-full-command;
              type string;
            }
          }
          case url-case {
            container url {
              description
                "Export via the file systems";
              tailf:cli-flatten-container;
              tailf:cli-sequence-commands;
              tailf:cli-compact-syntax;
              uses crypto-key-url-file-im-grouping;
              leaf key {
                tailf:cli-drop-node-name;
                tailf:cli-multi-value;
                tailf:cli-optional-in-sequence;
                type string;
              }
            }
          }
        }
      }
      list rsa {
        description
          "Import RSA keys";
        tailf:cli-suppress-mode;
        tailf:cli-compact-syntax;
        key "label";
        leaf label {
          type string;
        }
        leaf encryption {
          description
            "Encryption key";
          type empty;
        }
        leaf exportable {
          description
            "Allow the key to be exported";
          type empty;
        }
        leaf general-purpose {
          description
            "General Purpose key";
          type empty;
        }
        leaf on {
          description
            "Make this an on-token key";
          type string;
        }
        leaf pem {
          description
            "File type to import";
          type empty;
        }
        leaf redundancy {
          description
            "Sync this key to the standby";
          type empty;
        }
        leaf signature {
          description
            "Signature key";
          type empty;
        }
        leaf storage {
          description
            "Store key on specified device";
          type string;
        }
        leaf usage-keys {
          description
            "Usage key pairs";
          type empty;
        }
        choice terminal-url {
          case terminal-case {
            leaf terminal {
              description
                "Import via the terminal (cut-and-paste)";
              tailf:cli-multi-value;
              tailf:cli-full-command;
              type string;
            }
          }
          case url-case {
            container url {
              description
                "Export via the file systems";
              tailf:cli-flatten-container;
              tailf:cli-sequence-commands;
              tailf:cli-compact-syntax;
              uses crypto-key-url-file-im-grouping;
              leaf key {
                tailf:cli-drop-node-name;
                tailf:cli-multi-value;
                tailf:cli-optional-in-sequence;
                type string;
              }
            }
          }
        }
      }
    }
    container move {
      description
        "Move keys";
      container rsa {
        description
          "Move RSA keys";
        tailf:cli-flatten-container;
        tailf:cli-sequence-commands;
        tailf:cli-compact-syntax;
        leaf label {
          tailf:cli-drop-node-name;
          type string;
        }
        leaf non-exportable {
          description
            "Do Not allow the key to be exported";
          tailf:cli-break-sequence-commands;
          type empty;
        }
        leaf on {
          description
            "Make this an on-token key";
          type string;
        }
        leaf redundancy {
          description
            "Sync this key to the standby";
          type empty;
        }
        leaf storage {
          description
            "Store key on specified device";
          type string;
        }
      }
    }
    container pubkey-chain {
      description
        "Peer public key chain management";
      container rsa {
        description
          "Peer RSA public key chain management";
        tailf:cli-add-mode;
        tailf:cli-mode-name "config-pubkey-chain";
        uses crypto-key-pubkey-chain-grouping;
        container default {
          description
            "Set a command to its defaults";
          uses crypto-key-pubkey-chain-default-grouping;
        }
      }
    }
    leaf storage {
      description
        "default storage location for keypairs";
      type string;
    }
    container zeroize {
      description
        "Remove keys";
      container ec {
        description
          "Remove EC keys";
        presence "true";
        leaf label {
          tailf:cli-drop-node-name;
          type string;
        }
      }
      container pubkey-chain {
        description
          "Remove peer's cached public key";
        presence "true";
        leaf index {
          tailf:cli-drop-node-name;
          type uint16;
        }
      }
      container rsa {
        description
          "Remove RSA keys";
        presence "true";
        leaf label {
          tailf:cli-drop-node-name;
          type string;
        }
      }
    }
  }

  grouping crypto-keyring-key-grouping {
    leaf key {
      description
        "specify the key";
      type empty;
    }
    leaf encryption {
      tailf:cli-drop-node-name;
      tailf:cli-break-sequence-commands;
      type enumeration {
        enum "0";
        enum "6";
      }
    }
    leaf unencryt-key {
      tailf:cli-drop-node-name;
      tailf:cli-multi-value;
      type string;
    }
  }

  grouping crypto-keyring-grouping {
    leaf description {
      description
        "Specify a description about this keyring";
      tailf:cli-multi-value;
      type string;
    }
    leaf local-address {
      description
        "Limit the keyring usage to a local address";
      type string;
    }
    container pre-shared-key {
      description
        "Pre-Shared Key";
      container ipv4-addr {
        tailf:cli-drop-node-name;
        tailf:cli-sequence-commands;
        tailf:cli-compact-syntax;
        leaf address {
          description
            "pre shared key by address";
          type inet:ipv4-address;
        }
        leaf mask {
          description
            "pre shared key by address";
          tailf:cli-drop-node-name;
          tailf:cli-optional-in-sequence;
          type inet:ipv4-address;
        }
        uses crypto-keyring-key-grouping;
      }
      container address {
        description
          "pre shared key by address";
        tailf:cli-sequence-commands;
        tailf:cli-compact-syntax;
        leaf ipv6 {
          description
            "define shared key with IPv6 address";
          type inet:ipv6-prefix;
        }
        uses crypto-keyring-key-grouping;
      }
      container hostname {
        description
          "hostname  define peer policy for hostname";
        tailf:cli-sequence-commands;
        tailf:cli-compact-syntax;
        leaf name {
          tailf:cli-drop-node-name;
          type string;
        }
        uses crypto-keyring-key-grouping;
      }
    }
    container rsa-pubkey {
      description
        "Peer RSA public key chain management";
      container addr {
        tailf:cli-drop-node-name;
        tailf:cli-sequence-commands;
        tailf:cli-compact-syntax;
        leaf address {
          description
            "Public key associated with an address";
          type inet:ipv4-address;
        }
        leaf way {
          tailf:cli-drop-node-name;
          tailf:cli-optional-in-sequence;
          type enumeration {
            enum "encryption";
            enum "signature";
          }
        }
      }
      container hostname {
        tailf:cli-drop-node-name;
        tailf:cli-sequence-commands;
        tailf:cli-compact-syntax;
        leaf name {
          description
            "Public key associated with a hostname";
          type string;
        }
        leaf way {
          tailf:cli-drop-node-name;
          tailf:cli-optional-in-sequence;
          type enumeration {
            enum "encryption";
            enum "signature";
          }
        }
      }
    }
  }

  grouping crypto-map-grouping {
    uses crypto-map-common-grouping;
    container set {
      description
        "Set values for encryption/decryption";
      uses crypto-map-common-set-grouping;
      container security-association {
        description
          "Security association parameters";
        uses crypto-map-common-set-security-association-grouping;
        leaf level {
          description
            "specify a security association granularity level for identities";
          type enumeration {
            enum "per-host";
          }
        }
      }
    }
  }

  grouping crypto-map-default-grouping {
    leaf description {
      description
        "Description of the crypto map statement policy";
      type empty;
    }
    container dialer {
      description
        "Dialer related commands";
      leaf pre-classify {
        description
          "Enable dialer list classification before initiating IKE";
        type empty;
      }
    }
    container match {
      description
        "Match values";
      leaf address {
        description
          "Match address of packets to encrypt";
        type empty;
      }
    }
    container qos {
      description
        "Quality of Service related commands";
      leaf pre-classify {
        description
          "Enable QOS classification before packets are tunnel encapsulated";
        type empty;
      }
    }
    container reverse-route {
      description
        "Reverse Route Injection.";
      presence "true";
    }
    container set {
      description
        "Set values for encryption/decryption";
      leaf group {
        description
          "Set the san group parameters";
        type empty;
      }
      leaf identity {
        description
          "Identity restriction";
        type empty;
      }
      leaf ikev2-profile {
        description
          "Specify ikev2 Profile";
        type string;
      }
      leaf isakmp-profile {
        description
          "Specify isakmp Profile";
        type empty;
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          tailf:cli-drop-node-name;
          tailf:cli-sequence-commands;
          tailf:cli-compact-syntax;
          leaf idle-time {
            description
              "Automatically delete IPSec SAs after a given idle period.";
            type empty;
          }
          leaf default {
            description
              "All SAs idle-out reset to default peer";
            tailf:cli-optional-in-sequence;
            type empty;
          }
        }
        leaf level {
          description
            "specify a security association granularity level for identities";
          type enumeration {
            enum "per-host";
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      leaf transform-set {
        description
          "Specify list of transform sets in priority order";
        type empty;
      }
    }
  }

  grouping crypto-map-gdoi-mapping {
    leaf activate {
      description
        "Activate the crypto map to work in fail-close mode";
      type empty;
    }
    container match {
      description
        "Match address of packets for fail-close";
      leaf address {
        description
          "Match address of packets for fail-close.";
        type ext-acl-type;
      }
    }
  }

  grouping crypto-map-gdoi-default-mapping {
    leaf activate {
      description
        "Activate the crypto map to work in fail-close mode";
      type empty;
    }
    container match {
      description
        "Match address of packets for fail-close";
      leaf address {
        description
          "Match address of packets for fail-close.";
        type empty;
      }
    }
  }

  grouping time-grouping {
    container time {
      tailf:cli-sequence-commands;
      tailf:cli-compact-syntax;
      choice date-month {
        case date1 {
          leaf date1 {
            tailf:cli-drop-node-name;
            type uint8 {
              range "1..31";
            }
          }
        }
        case month1 {
          leaf month1 {
            tailf:cli-drop-node-name;
            type string;
          }
        }
      }
      choice month-date {
        case date2 {
          leaf date2 {
            tailf:cli-drop-node-name;
            when "../month1";
            type uint8 {
              range "1..31";
            }
          }
        }
        case month2 {
          leaf month2 {
            tailf:cli-drop-node-name;
            when "../date1";
            type string;
          }
        }
      }
      leaf year {
        tailf:cli-drop-node-name;
        type uint16 {
          range "1993..2035";
        }
      }
      leaf clock {
        tailf:cli-drop-node-name;
        tailf:cli-break-sequence-commands;
        type string;
      }
      leaf utc {
        description
          "Time is in UTC (not local Time Zone)";
        tailf:cli-full-command;
        type empty;
      }
    }
  }

  grouping compare-time-grouping {
    container eq {
      description
        "Equal";
      uses time-grouping;
    }
    container ge {
      description
        "Greater than or equal";
      uses time-grouping;
    }
    container lt {
      description
        "Less Than";
      uses time-grouping;
    }
    container ne {
      description
        "Not Equal";
      uses time-grouping;
    }
  }

  grouping compare-string-grouping {
    leaf co {
      description
        "Contains";
      tailf:cli-multi-value;
      type string;
    }
    leaf eq {
      description
        "Equal";
      tailf:cli-multi-value;
      type string;
    }
    leaf nc {
      description
        "Does not contain";
      tailf:cli-multi-value;
      type string;
    }
    leaf ne {
      description
        "Not Equal";
      tailf:cli-multi-value;
      type string;
    }
  }

  grouping crypto-pki-certificate-map-grouping {
    container alt-subject-name {
      description
        "Alternate subject name";
      uses compare-string-grouping;
    }
    container expires-on {
      description
        "Expiration date/time";
      uses compare-time-grouping;
    }
    container issuer-name {
      description
        "Certificate issuer name";
      uses compare-string-grouping;
    }
    container name {
      description
        "Any subject name field";
      uses compare-string-grouping;
    }
    container serial-number {
      description
        "Certificate serial number (hexidecimal)";
      uses compare-string-grouping;
    }
    container subject-name {
      description
        "Certificate subject name";
      uses compare-string-grouping;
    }
    container unstructured-subject-name {
      description
        "Unstructured subject name";
      uses compare-string-grouping;
    }
    container valid-start {
      description
        "Valid after date/time";
      uses compare-time-grouping;
    }
  }

  grouping crypto-pki-profile-enrollment-auth-grouping {
    leaf command {
      description
        "command to authenticate or enroll";
      tailf:cli-multi-value;
      type string;
    }
    leaf terminal {
      description
        "authenticate or enroll using terminal";
      type empty;
    }
    container url {
      description
        "url to authenticate/enroll";
      tailf:cli-sequence-commands;
      tailf:cli-compact-syntax;
      leaf name {
        tailf:cli-drop-node-name;
        type string;
      }
      leaf vrf {
        description
          "VRF to use for certificate enrollment ";
        tailf:cli-optional-in-sequence;
        type string;
      }
    }
  }

  grouping crypto-pki-profile-enrollment-grouping {
    container authentication {
      description
        "Retrieve CA certificate(s)";
      uses crypto-pki-profile-enrollment-auth-grouping;
    }
    container enrollment {
      description
        "Enroll router with a CA";
      uses crypto-pki-profile-enrollment-auth-grouping;
      leaf credential {
        description
          "Use existing router cert for new enrollment";
        type string;
      }
    }
    leaf method-est {
      description
        "Use EST for this profile";
      type empty;
    }
    list parameter {
      description
        "Define a parameter value or prompt";
      tailf:cli-suppress-mode;
      key "number";
      leaf number {
        type uint8 {
          range "1..8";
        }
      }
      choice prompt-value {
        case prompt-case {
          leaf prompt {
            description
              "Define a parameter prompt";
            tailf:cli-hide-in-submode;
            tailf:cli-multi-value;
            type string;
          }
        }
        case value-case {
          leaf value {
            description
              "Define a parameter value";
            tailf:cli-hide-in-submode;
            tailf:cli-multi-value;
            type string;
          }
        }
      }
    }
    container reenrollment {
      description
        "Re-enroll router with a CA";
      uses crypto-pki-profile-enrollment-auth-grouping;
    }
    leaf source-interface {
      description
        "Interface used as source address";
      type string;
    }
  }

  grouping hour-minute-grouping {
    leaf hours {
      tailf:cli-drop-node-name;
      type uint8 {
        range "0..23";
      }
    }
    leaf minutes {
      tailf:cli-drop-node-name;
      type uint8 {
        range "0..59";
      }
    }
  }

  grouping username-password-grouping {
    leaf username {
      description
        "Provide the username for authentication";
      type string;
    }
    leaf password {
      description
        "Provide the password for authentication";
      type string;
    }
  }

  grouping utd-engine-standard-grouping {
    container logging {
      description
        "Provide config options for logging the alerts";
      container server {
        description
          "Log the alerts to a server";
        tailf:cli-sequence-commands;
        tailf:cli-compact-syntax;
        leaf name {
          tailf:cli-drop-node-name;
          type string;
        }
        leaf level {
          description
            "Provide the log level";
          tailf:cli-break-sequence-commands;
          tailf:cli-full-command;
          type syslog-level-type;
        }
        leaf syslog {
          description
            "Log the alerts to IOS syslogs";
          type empty;
        }
      }
      container syslog {
        description
          "Log the alerts to IOS syslogs";
        presence "true";
        leaf level {
          description
            "Provide the log level";
          tailf:cli-full-command;
          type syslog-level-type;
        }
      }
    }
    leaf policy {
      description
        "Provide the policy option (default=balanced)";
      type enumeration {
        enum "balanced";
        enum "connectivity";
        enum "security";
      }
    }
    container signature {
      description
        "Provide config options for the signatures";
      container update {
        description
          "Provide config options for the signature updates";
        container occur-at {
          description
            "Specify update occurence by calendar time";
          container daily {
            description
              "Option for daily update";
            tailf:cli-sequence-commands;
            tailf:cli-compact-syntax;
            uses hour-minute-grouping;
          }
          container monthly {
            description
              "Option for monthly update";
            tailf:cli-sequence-commands;
            tailf:cli-compact-syntax;
            leaf days {
              tailf:cli-drop-node-name;
              type string;
            }
            uses hour-minute-grouping;
          }
          container weekly {
            description
              "Option for weekly update";
            tailf:cli-sequence-commands;
            tailf:cli-compact-syntax;
            leaf days {
              tailf:cli-drop-node-name;
              type string;
            }
            uses hour-minute-grouping;
          }
        }
        container server {
          description
            "Provide config options for the signature update server";
          container cisco {
            description
              "Use Cisco site to provide updates";
            tailf:cli-sequence-commands;
            tailf:cli-compact-syntax;
            uses username-password-grouping;
          }
          container url {
            description
              "Enter the complete URL for the path to the update server";
            choice url-uname-passwd {
              case all-case {
                container all {
                  tailf:cli-drop-node-name;
                  tailf:cli-sequence-commands;
                  tailf:cli-compact-syntax;
                  leaf name {
                    tailf:cli-drop-node-name;
                    type string;
                  }
                  uses username-password-grouping;
                }
              }
              case name-only {
                leaf name {
                  tailf:cli-drop-node-name;
                  type string;
                }
              }
            }
          }
        }
      }
    }
    leaf threat {
      description
        "Provide the threat detection/protection option (default=detection)";
      tailf:cli-full-command;
      type enumeration {
        enum "detection";
        enum "protection";
      }
    }
    leaf whitelist {
      description
        "Enable whitelisting under the utd engine";
      tailf:cli-full-command;
      type empty;
    }
  }

  grouping pseudowire-grouping {
    // pseudowire-class * / encapsulation
    leaf encapsulation {
      description
        "Data encapsulation method";
      type enumeration {
        enum "l2tpv2";
        enum "l2tpv3";
        enum "mpls";
        enum "udp";
      }
    }
    //pseudowire-class * / ip
    container ip {
      description
        "Specify IP parameters";
      when "../encapsulation = 'l2tpv2' or ../encapsulation = 'l2tpv3'";
      container dfbit {
        description
          "DF bit options for tunnel";
        leaf set {
          description
            "Set the DF bit in the tunnel header";
          tailf:cli-full-command;
          type empty;
        }
      }
      container local {
        description
          "Specify local information";
        container interface {
          description
            "Source interface for pseudowire";
          uses interface-grouping;
        }
      }
      container pmtu {
        description
          "Enable Path MTU for tunnel";
        presence "true";
        leaf max {
          description
            "Maximum Path MTU for session";
          type uint16 {
            range "68..65535";
          }
        }
      }
      leaf protocol {
        description
          "Specific IP protocol number to use";
        when "../../encapsulation = 'l2tpv3'";
        type enumeration {
          enum "l2tp";
          enum "uti";
        }
      }
      container tos {
        description
          "Specify ToS options for IP tunnel header";
        leaf reflect {
          description
            "Reflect IP payload ToS on tunnel";
          tailf:cli-full-command;
          type empty;
        }
        leaf value {
          description
            "IP ToS value";
          type uint8;
        }
      }
      leaf ttl {
        description
          "Specify TTL value for IP tunnel header";
        type uint8;
      }
    }
    //pseudowire-class * / control-word
    leaf control-word {
      description
        "Include control-word in pseudowire packets";
      tailf:cli-show-no;
      tailf:cli-full-command;
      when "../encapsulation = 'mpls'";
      type empty;
    }
    //pseudowire-class * / interworking
    leaf interworking {
      description
        "Interworking options for pseudowire";
      type enumeration {
        enum "ethernet";
        enum "ip";
        enum "vlan";
      }
    }
    //pseudowire-class * / load-balance
    container load-balance {
      description
        "Loadbalancing for pseudowire";
      when "../encapsulation = 'mpls'";
      container flow {
        description
          "Enable flow based load balancing for pseudowire";
        presence "true";
        leaf ethernet {
          description
            "Ethernet pseudowire flow classification";
          tailf:cli-full-command;
          type enumeration {
            enum "dst-mac";
            enum "src-dst-mac";
            enum "src-mac";
          }
        }
      }
    }
    //pseudowire-class * / monitor
    container monitor {
      description
        "Active monitoring of xconnect peer";
      when "../encapsulation = 'mpls'";
      container peer {
        description
          "Active monitoring of xconnect peer";
        container bfd {
          description
            "BFD active monitoring for the xconnect peer";
          presence "true";
          container local {
            description
              "Specify local endpoint information to map to a BFD session";
            container interface {
              description
                "Source interface for pseudowire";
              uses interface-grouping;
            }
          }
        }
      }
    }
    //pseudowire-class * / preferred-path
    container preferred-path {
      description
        "Preferred path";
      container interface {
        description
          "Output Interface";
        tailf:cli-sequence-commands;
        tailf:cli-compact-syntax;
        choice Tunnel-Tunnel-tp {
          case Tunnel-case {
            leaf Tunnel {
              description
                "Tunnel interface";
              tailf:cli-allow-join-with-value {
                tailf:cli-display-joined;
              }
              type uint64 {
                range "0..2147483647";
              }
            }
          }
          case Tunnel-tp-case {
            leaf Tunnel-tp {
              description
                "MPLS Transport Profile interface";
              tailf:cli-allow-join-with-value {
                tailf:cli-display-joined;
              }
              type uint16;
            }
          }
        }
        leaf disable-fallback {
          description
            "disable fall back to alternative route";
          tailf:cli-optional-in-sequence;
          type empty;
        }
      }
      container peer-container {
        tailf:cli-drop-node-name;
        tailf:cli-sequence-commands;
        tailf:cli-compact-syntax;
        leaf peer {
          description
            "Peer Address";
          type union {
            type string;
            type inet:ipv4-address;
          }
        }
        leaf disable-fallback {
          description
            "disable fall back to alternative route";
          tailf:cli-optional-in-sequence;
          type empty;
        }
      }
    }
    //pseudowire-class * / protocol
    container protocol-mpls {
      tailf:cli-drop-node-name;
      when "../encapsulation = 'mpls'";
      leaf protocol {
        description
          "Signaling protocol to use";
        type enumeration {
          enum "ldp";
          enum "none";
        }
      }
    }
    container protocol-l2tpv2 {
      tailf:cli-drop-node-name;
      when "../encapsulation = 'l2tpv2'";
      leaf protocol {
        description
          "Signaling protocol to use";
        type enumeration {
          enum "l2tpv2";
          enum "none";
        }
      }
    }
    container protocol-l2tpv3 {
      tailf:cli-drop-node-name;
      when "../encapsulation = 'l2tpv3'";
      leaf protocol {
        description
          "Signaling protocol to use";
        type enumeration {
          enum "l2tpv3";
          enum "l2tpv3ietf";
          enum "none";
        }
      }
    }
    //pseudowire-class * / sequencing
    leaf sequencing {
      description
        "Sequencing options for pseudowire";
      when "../encapsulation = 'mpls' or ../encapsulation = 'l2tpv3'";
      type enumeration {
        enum "both";
        enum "receive";
        enum "resync";
        enum "transmit";
      }
    }
    //pseudowire-class * / status
    container status {
      description
        "Pseudowire status capabilities";
      presence "true";
      container admin-down {
        description
          "Admin down of Attachment Circuit";
        when "../../encapsulation = 'l2tpv2' or ../../encapsulation = 'l2tpv3'";
        leaf disconnect {
          description
            "Disconnect the session";
          type empty;
        }
      }
      container control-plane {
        description
          "control plane status events";
        leaf route-watch {
          description
            "listen on the control plane to route-watch events";
          type empty;
        }
      }
      leaf decoupled {
        description
          "Reflect standby status of the attachment circuit as up on the pseudowire";
        type empty;
      }
      container peer {
        description
          "peer status configuration";
        container topology {
          description
            "change status behaviour based on peer topology";
          leaf dual-homed {
            description
              "Our peer(s) are participating in a redundant solution with some form of redundancyprotocol running between the peer routers, Only one of the remote peers will advertise astatus of UP at a time. The other will advertise standby. Change our configuration so wecan send a status of UP on both active and redundant pseudowires";
            type empty;
          }
        }
      }
      container redundancy {
        description
          "Xconnect redundancy configuration";
        leaf master {
          description
            "Put the xconnect redundancy group on this node in master mode";
          type empty;
        }
      }
    }
    //pseudowire-class * / switching
    container switching {
      description
        "Switching TLV on/off for pseudowire";
      when "../encapsulation = 'mpls'";
      leaf tlv {
        description
          "Switching TLV on/off for pseudowire";
        type empty;
      }
    }
  }

  grouping track-timer-grouping {
    leaf seconds {
      tailf:cli-drop-node-name;
      tailf:cli-full-command;
      type uint32 {
        range "1..3000";
      }
    }
    leaf ms {
      description
        "Specify polling interval in milliseconds";
      tailf:cli-full-command;
      type uint32 {
        range "500..5000";
      }
    }
  }

  grouping track-grouping {
    container delay {
      description
        "Tracking delay";
      tailf:cli-compact-syntax;
      leaf down {
        description
          "Delay down change notification";
        type uint32 {
          range "0..180";
        }
      }
      leaf up {
        description
          "Delay up change notification";
        type uint32 {
          range "0..180";
        }
      }
    }
    leaf default-state {
      description
        "default object state";
      type enumeration {
        enum "down";
        enum "up";
      }
    }
    list object {
      description
        "Add a tracked object to list";
      tailf:cli-suppress-mode;
      tailf:cli-sequence-commands;
      tailf:cli-compact-syntax;
      key "number";
      leaf number {
        type uint32 {
          range "1..1000";
        }
      }
      leaf not {
        description
          "Negate the state of object";
        tailf:cli-optional-in-sequence;
        type empty;
      }
    }
  }

  grouping default-track-grouping {
    container delay {
      description
        "Tracking delay";
      presence "true";
    }
    leaf default-state {
      description
        "default object state";
      type enumeration {
        enum "down";
        enum "up";
      }
    }
  }

  grouping ip-wccp-group-address-grouping {
    leaf group-address {
      description
        "Set the multicast group";
      type inet:ipv4-address;
    }
    leaf group-list {
      description
        "Set the access-list used to permit group membership";
      type exp-acl-type;
    }
    leaf mode {
      description
        "Set the service mode";
      type enumeration {
        enum "closed";
        enum "open";
      }
    }
    container password {
      description
        "Set the authentication password";
      tailf:cli-compact-syntax;
      tailf:cli-flatten-container;
      leaf encryption {
        tailf:cli-drop-node-name;
        type enumeration {
          enum "0";
          enum "7";
        }
      }
      leaf clear-key {
        tailf:cli-drop-node-name;
        tailf:cli-full-command;
        type string;
      }
    }
    leaf redirect-list {
      description
        "Set the access-list used to permit redirection";
      type exp-acl-type;
    }
    leaf snmp-disabled {
      description
        "Disable SNMP for WCCP GRE Tunnel";
      type empty;
    }
  }

  grouping ip-wccp-grouping {
    list wccp-list {
      tailf:cli-drop-node-name;
      tailf:cli-suppress-mode;
      tailf:cli-compact-syntax;
      key "id";
      leaf id {
        type uint8 {
          range "0..254";
        }
      }
      uses ip-wccp-group-address-grouping;
    }
    leaf source-interface {
      description
        "Set source interface for Router ID";
      type string;
    }
    container web-cache {
      description
        "Standard web caching service";
      tailf:cli-compact-syntax;
      uses ip-wccp-group-address-grouping;
    }
  }

  grouping ip-msdp-grouping {
    container peer {
      description
        "Configure an MSDP peer";
      tailf:cli-compact-syntax;
      tailf:cli-sequence-commands;
      leaf addr {
        tailf:cli-drop-node-name;
        type union {
          type string;
          type inet:ipv4-address;
        }
      }
      leaf connect-source {
        description
          "Configure source address used for MSDP connection";
        tailf:cli-break-sequence-commands;
        type string;
      }
      leaf remote-as {
        description
          "Configured AS number";
        type uint16;
      }
    }
    leaf cache-rejected-sa {
      description
        "Store rejected SAs from all peers";
      tailf:cli-full-command;
      type uint32 {
        range "1..32766";
      }
    }
    leaf cache-sa-state {
      description
        "Configure this system to cache SA state";
      tailf:cli-full-command;
      type empty;
    }
    container default-peer {
      description
        "Default MSDP peer to accept SA messages from";
      tailf:cli-compact-syntax;
      tailf:cli-sequence-commands;
      leaf name-addr {
        tailf:cli-drop-node-name;
        type union {
          type string;
          type inet:ipv4-address;
        }
      }
      leaf prefix-list {
        description
          "Prefix list";
        tailf:cli-optional-in-sequence;
        type string;
      }
    }
    container description {
      description
        "Peer specific description";
      tailf:cli-compact-syntax;
      tailf:cli-sequence-commands;
      leaf name-addr {
        tailf:cli-drop-node-name;
        type union {
          type string;
          type inet:ipv4-address;
        }
      }
      leaf description {
        tailf:cli-drop-node-name;
        tailf:cli-multi-value;
        type string;
      }
    }
    container filter-sa-request {
      description
        "Filter SA-Requests from peer";
      tailf:cli-compact-syntax;
      tailf:cli-sequence-commands;
      leaf name-addr {
        tailf:cli-drop-node-name;
        type union {
          type string;
          type inet:ipv4-address;
        }
      }
      leaf list {
        description
          "Access-list";
        tailf:cli-optional-in-sequence;
        type std-acl-type;
      }
    }
    container keepalive {
      description
        "Configure keepalive parameters for a peer";
      tailf:cli-compact-syntax;
      tailf:cli-sequence-commands;
      leaf name-addr {
        tailf:cli-drop-node-name;
        type union {
          type string;
          type inet:ipv4-address;
        }
      }
      leaf keepalive {
        tailf:cli-drop-node-name;
        description
          "Send keepalive period in seconds";
        type uint8 {
          range "1..60";
        }
      }
      leaf max-wait {
        tailf:cli-drop-node-name;
        description
          "Maximum time in seconds to wait for a message";
        type uint8 {
          range "1..75";
        }
      }
    }
    container mesh-group {
      description
        "Configure an MSDP mesh-group";
      tailf:cli-compact-syntax;
      tailf:cli-sequence-commands;
      leaf name {
        tailf:cli-drop-node-name;
        type string;
      }
      leaf addr {
        tailf:cli-drop-node-name;
        type union {
          type string;
          type inet:ipv4-address;
        }
      }
    }
    leaf originator-id {
      description
        "Configure MSDP Originator ID";
      tailf:cli-full-command;
      type string;
    }
    container password {
      description
        "Configure an MSDP password";
      container peer {
        description
          "MSDP peer on which the password is to be set";
        tailf:cli-compact-syntax;
        tailf:cli-sequence-commands;
        leaf addr {
          tailf:cli-drop-node-name;
          type union {
            type string;
            type inet:ipv4-address;
          }
        }
        leaf encryption {
          tailf:cli-drop-node-name;
          tailf:cli-break-sequence-commands;
          type uint8;
        }
        leaf password {
          tailf:cli-drop-node-name;
          tailf:cli-multi-value;
          type string;
        }
      }
    }
    container redistribute {
      description
        "Inject multicast route entries into MSDP";
      tailf:cli-compact-syntax;
      leaf list {
        description
          "Access-list";
        type ext-acl-type;
      }
      leaf asn {
        description
          "AS access-list";
        type uint16;
      }
      leaf route-map {
        description
          "Route-map";
        type string;
      }
    }
    leaf rpf {
      description
        "MSDP rpf";
      type enumeration {
        enum "rfc3618";
      }
    }
    container sa-filter {
      description
        "Filter SA messages from peer";
      container in {
        description
          "Enable incoming SA filtering";
        tailf:cli-sequence-commands;
        tailf:cli-compact-syntax;
        leaf addr {
          tailf:cli-drop-node-name;
          type union {
            type string;
            type inet:ipv4-address;
          }
        }
        leaf list {
          description
            "Access list";
          tailf:cli-break-sequence-commands;
          type ext-acl-type;
        }
        leaf route-map {
          description
            "Route map";
          type string;
        }
        leaf rp-list {
          description
            "Access-list for originating RP";
          tailf:cli-full-command;
          type union {
            type uint16 {
              range "1..99";
            }
            type string;
          }
        }
        leaf rp-route-map {
          description
            "Route map for originating RP";
          tailf:cli-full-command;
          type string;
        }
      }
      container out {
        description
          "Enable outgoing SA filtering";
        tailf:cli-sequence-commands;
        tailf:cli-compact-syntax;
        leaf addr {
          tailf:cli-drop-node-name;
          type union {
            type string;
            type inet:ipv4-address;
          }
        }
        leaf list {
          description
            "Access list";
          tailf:cli-break-sequence-commands;
          type ext-acl-type;
        }
        leaf route-map {
          description
            "Route map";
          type string;
        }
        leaf rp-list {
          description
            "Access-list for originating RP";
          tailf:cli-full-command;
          type union {
            type uint16 {
              range "1..99";
            }
            type string;
          }
        }
        leaf rp-route-map {
          description
            "Route map for originating RP";
          tailf:cli-full-command;
          type string;
        }
      }
    }
    container sa-limit {
      description
        "Configure SA limit for a peer";
      tailf:cli-compact-syntax;
      tailf:cli-sequence-commands;
      leaf name-addr {
        tailf:cli-drop-node-name;
        type union {
          type string;
          type inet:ipv4-address;
        }
      }
      leaf limit {
        tailf:cli-drop-node-name;
        description
          "Limit of SAs";
        type uint32 {
          range "1..2147483646";
        }
      }
    }
    container shutdown {
      description
        "Administratively shutdown MSDP peer";
      leaf name-addr {
        tailf:cli-drop-node-name;
        type union {
          type string;
          type inet:ipv4-address;
        }
      }
    }
    leaf timer {
      description
        "MSDP timer";
      tailf:cli-full-command;
      type uint8 {
        range "1..60";
      }
    }
    container ttl-threshold {
      description
        "Configure TTL Threshold for MSDP Peer";
      tailf:cli-compact-syntax;
      tailf:cli-sequence-commands;
      leaf name-addr {
        tailf:cli-drop-node-name;
        type union {
          type string;
          type inet:ipv4-address;
        }
      }
      leaf threshold {
        tailf:cli-drop-node-name;
        description
          "TTL Threshold Value";
        type uint8;
      }
    }
  }

  grouping mcfg-srmpls-mapserver-sidmap {
    container address-family {
      container ipv4 {
        tailf:cli-add-mode;
        tailf:cli-mode-name "config-srmpls-mapserver-sidmap-af";
        tailf:cli-exit-command "exit-address-family";
        presence "true";
        container mcfg-srmpls-mapserver-sidmap-af {
          tailf:cli-drop-node-name;
          uses srcfg-srmpls-conn-af;
        }
      }
    }
  }

  grouping srcfg-srmpls-attr-af {
    leaf explicit-null {
      type empty;
    }
    leaf sr-label-preferred {
      type empty;
    }
  }

  grouping sr-range {
    leaf range-start {
      tailf:cli-drop-node-name;
      type uint32 {
        range "0..1048575";
      }
    }
    leaf range {
      description
        "Range value";
      type uint32 {
        range "1..1048575";
      }
    }
  }

  grouping srcfg-srmpls-conn-af {
    list prefixes {
      tailf:cli-drop-node-name;
      tailf:cli-suppress-mode;
      key "ipprefix";
      leaf ipprefix {
        tailf:cli-drop-node-name;
        type ios:ipv4-prefix;
      }
      container index {
        tailf:cli-compact-syntax;
        tailf:cli-sequence-commands {
          tailf:cli-reset-siblings;
        }
        uses sr-range;
      }
      container absolute {
        tailf:cli-compact-syntax;
        tailf:cli-sequence-commands {
          tailf:cli-reset-siblings;
        }
        uses sr-range;
      }
    }
  }

  grouping router-lisp-ip-route-import-map-cache-grouping {
    leaf route-map {
      description
        "Route map for route selection filtering";
      type string;
    }
  }

  grouping router-lisp-ip-route-import-database-grouping {
    leaf route-map {
      description
        "Route map for route selection filtering";
      tailf:cli-incomplete-command;
      type string;
    }
    leaf locator-set {
      description
        "Locator set to use with created database mapping entries";
      tailf:cli-full-command;
      type string;
    }
  }

  grouping router-lisp-ddt-authoritative-grouping {
    container delegate {
      description
        "DDT delegation to a child DDT node or map-server";
      tailf:cli-sequence-commands;
      tailf:cli-compact-syntax;
      choice instance-id-eid-prefix-choice {
        case eid-prefix-case {
          leaf eid-prefix {
            tailf:cli-drop-node-name;
            type union {
              type inet:ipv4-prefix;
              type inet:ipv6-prefix;
            }
          }
        }
        case instance-id-case {
          leaf instance-id {
            description
              "EID instance-ID";
            type string;
          }
        }
      }
      leaf to {
        description
          "DDT delegation to a child DDT node or map-server";
        type empty;
      }
      leaf ip-address {
        tailf:cli-drop-node-name;
        description
          "IPv4/6 Child or map-server node locator address";
        type union {
          type inet:ipv4-address;
          type inet:ipv6-address;
        }
      }
      leaf map-server {
        description
          "Delegation points to a map-server";
        tailf:cli-optional-in-sequence;
        type empty;
      }
    }
    leaf map-server-peer {
      description
        "Peer map-servers that are authoritative for the same EID prefixes";
      type union {
        type inet:ipv4-address;
        type inet:ipv6-address;
      }
    }
  }

  grouping router-lisp-ip-grouping {
    leaf alt-vrf {
      description
        "Activate LISP-ALT functionality in VRF";
      status deprecated;
      tailf:cli-full-command;
      type string;
    }
    container database-mapping {
      description
        "Address family specific local EID prefixes database configuration";
      container limit {
        description
          "Configures the maximum size of local EID prefixes database";
        tailf:cli-sequence-commands;
        tailf:cli-compact-syntax;
        leaf dynamic {
          description
            "Configures the maximum size of dynamic local EID prefixes database";
          type uint32;
        }
        leaf warning-threshold {
          description
            "Send warning message to syslog when the database-mapping dynamic sizereaches this percentage of the limit";
          tailf:cli-optional-in-sequence;
          type uint8;
        }
      }
    }
    container distance {
      description
        "Administrative distance for RIB route installation";
      leaf alt {
        description
          "LISP routes installed in the ALT table";
        tailf:cli-full-command;
        type uint8;
      }
      leaf dyn-eid {
        description
          "LISP installed routes of type dynamic-EID";
        tailf:cli-full-command;
        type uint8;
      }
      leaf site-registrations {
        description
          "LISP installed routes of type site-registrations";
        tailf:cli-full-command;
        type uint8;
      }
    }
    container itr {
      description
        "Configures a LISP Ingress Tunnel Router (ITR)";
      list map-resolver {
        description
          "Configures map-resolver address for sending Map-Requests";
        tailf:cli-suppress-mode;
        key "ip-addr";
        leaf ip-addr {
          type union {
            type inet:ipv4-address;
            type inet:ipv6-address;
          }
        }
      }
    }
    container itr-enable {
      tailf:cli-drop-node-name;
      leaf itr {
        description
          "Configures a LISP Ingress Tunnel Router (ITR)";
        type empty;
      }
    }
    container etr {
      description
        "Configures a LISP Egress Tunnel Router (ETR)";
      list map-server {
        description
          "Configures map server for ETR registration";
        tailf:cli-suppress-mode;
        key "ip-addr";
        leaf ip-addr {
          type union {
            type inet:ipv4-address;
            type inet:ipv6-address;
          }
        }
        container key {
          description
            "Authentication key used with map server";
          tailf:cli-compact-syntax;
          leaf key-0 {
            tailf:alt-name "0";
            description
              "The UNENCRYPTED (cleartext) password";
            type string;
          }
          leaf key-6 {
            tailf:alt-name "6";
            description
              "The ENCRYPTED password";
            type string;
          }
          leaf key-7 {
            tailf:alt-name "7";
            description
              "The HIDDEN password";
            type string;
          }
          leaf pwd {
            description
              "The UNENCRYPTED (cleartext) password";
            tailf:cli-drop-node-name;
            type string;
          }
        }
        leaf proxy-reply {
          description
            "Request Map-Server to send Map-Replies on behalf of site";
          tailf:cli-full-command;
          type empty;
        }
      }
    }
    container etr-enable {
      tailf:cli-drop-node-name;
      leaf etr {
        description
          "Configures a LISP Egress Tunnel Router (ETR)";
        type empty;
      }
    }
    container locator {
      description
        "Locator related configuration";
      tailf:display-when "../../../lisp or ../../../lisp-list";
      container reachability {
        description
          "Configuration realted to locator reachability";
        leaf exclude-default {
          description
            "If a remote RLOC is reached via the default route, treat it as unreachable";
          type empty;
        }
      }
    }
    container map-cache {
      description
        "Address family specific map cache configuration";
      leaf site-registration {
        description
          "Install map cache to map request for site registrations";
        type empty;
      }
    }
    container map-cache-limit {
      description
        "Configures maximum size of map-cache";
      tailf:cli-sequence-commands;
      tailf:cli-compact-syntax;
      leaf max-map-cache-entries {
        tailf:cli-drop-node-name;
        type uint32 {
          range "0..100000";
        }
      }
      leaf reserve-list {
        description
          "EID-prefixes guaranteed to be stored in map-cache";
        tailf:cli-break-sequence-commands;
        tailf:cli-full-command;
        type string;
      }
      leaf warning-threshold {
        description
          "Send warning message to syslog when the map-cache size reaches this percentage of the limit";
        type uint8 {
          range "0..100";
        }
      }
    }
    container map-cache-persistent {
      description
        "Dump map-cache onto flash, making it persistent across reboots";
      leaf interval {
        description
          "Interval in minutes of how often the map-cache is saved";
        type uint16 {
          range "1..1440";
        }
      }
    }
    leaf map-request-source {
      description
        "Configures inner header source address in Map-Request message";
      type inet:ipv4-address;
    }
    container map-resolver {
      description
        "Configures a LISP Map Resolver (MR)";
      tailf:display-when "../../../lisp or ../../../lisp-list";
      presence "true";
      container map-request {
        description
          "Map-Request processing options";
        container validate {
          description
            "Validation options";
          container source {
            description
              "Influence which source RLOCs map requests are accepted from";
            tailf:cli-compact-syntax;
            leaf list {
              description
                "Define allowed prefixes using an ip[v6] prefix list";
              type empty;
            }
            leaf registered {
              description
                "...from RLOCs that register EID-prefixes in the same IID on a co-located MapServer";
              type empty;
            }
            leaf ipv4 {
              description
                "IPv4 prefixes";
              tailf:display-when "../list";
              type string;
            }
            leaf ipv6 {
              description
                "IPv6 prefixes";
              tailf:display-when "../list";
              type string;
            }
          }
        }
      }
    }
    container map-server {
      description
        "Configures a LISP Map Server (MS)";
      tailf:display-when "../../../lisp or ../../../lisp-list";
      presence "true";
      container map-register {
        description
          "Map-Register processing options";
        container validate {
          description
            "Validation options";
          container source {
            description
              "RLOC Source IP address";
            leaf allowed-locator {
              description
                "Against sites' allowed-locators policy";
              type empty;
            }
          }
        }
      }
    }
    container path-mtu-discovery {
      description
        "Path MTU discovery";
      tailf:cli-compact-syntax;
      presence "true";
      leaf max {
        description
          "Upper bound on the path MTU accepted";
        tailf:cli-full-command;
        type uint16 {
          range "68..65535";
        }
      }
      leaf min {
        description
          "Lower bound on the path MTU accepted";
        type uint16 {
          range "68..65535";
        }
      }
    }
    leaf proxy-etr {
      description
        "Configures a LISP Proxy Engress Tunnel Router (PETR)";
      tailf:cli-full-command;
      type empty;
    }
    leaf-list proxy-itr {
      description
        "Configures a LISP Proxy Ingress Tunnel Router (PITR)";
      tailf:cli-list-syntax;
      type union {
        type inet:ipv4-address;
        type inet:ipv6-address;
      }
    }
    container route-export {
      description
        "Export routes into RIB from LISP";
      leaf site-registrations {
        description
          "Export LISP site registrations to RIB";
        tailf:cli-full-command;
        type empty;
      }
      leaf away-eids {
        description
          "Export LISP away EIDs to RIB";
        tailf:cli-full-command;
        type empty;
      }
    }
    container route-import {
      description
        "Import RIB routes by a routing protocol into LISP";
      tailf:display-when "../../../../eid-table";
      container database {
        description
          "Use RIB routes to define local EID database entries";
        list bgp {
          description
            "Border Gateway Protocol (BGP)";
          tailf:cli-suppress-mode;
          tailf:cli-compact-syntax;
          key "id";
          leaf id {
            type bgp-as-number-type;
          }
          uses router-lisp-ip-route-import-database-grouping;
        }
        container connected {
          description
            "Connected";
          tailf:cli-compact-syntax;
          uses router-lisp-ip-route-import-database-grouping;
        }
        list eigrp {
          description
            "Enhanced Interior Gateway Routing Protocol (EIGRP)";
          tailf:cli-suppress-mode;
          tailf:cli-compact-syntax;
          key "id";
          leaf id {
            type uint16;
          }
          uses router-lisp-ip-route-import-database-grouping;
        }
        list isis {
          description
            "ISO IS-IS";
          tailf:cli-suppress-mode;
          tailf:cli-compact-syntax;
          key "id";
          leaf id {
            type string;
          }
          uses router-lisp-ip-route-import-database-grouping;
        }
        container maximum-prefix {
          description
            "Maximum number of prefixes to pick up from the RIB";
          tailf:cli-compact-syntax;
          tailf:cli-sequence-commands;
          leaf number {
            tailf:cli-drop-node-name;
            type int32;
          }
          choice threshold-warning {
            case warning-only-case {
              leaf warning-only {
                description
                  "Only give a warning message and do not limit entries";
                tailf:cli-optional-in-sequence;
                type empty;
              }
            }
            case threshold-case {
              leaf threshold {
                tailf:cli-drop-node-name;
                tailf:cli-optional-in-sequence;
                type uint8 {
                  range "1..100";
                }
              }
            }
            case threshold-warning-case {
              leaf threshold1 {
                tailf:cli-drop-node-name;
                tailf:cli-optional-in-sequence;
                type uint8 {
                  range "1..100";
                }
              }
              leaf warning-only1 {
                tailf:alt-name "warning-only";
                description
                  "Only give a warning message and do not limit entries";
                tailf:cli-optional-in-sequence;
                type empty;
              }
            }
          }
        }
        list ospf {
          description
            "Open Shortest Path First (OSPF)";
          tailf:cli-suppress-mode;
          tailf:cli-compact-syntax;
          key "id";
          leaf id {
            type uint16;
          }
          uses router-lisp-ip-route-import-database-grouping;
        }
        list ospfv3 {
          description
            "OSPFv3";
          tailf:cli-suppress-mode;
          tailf:cli-compact-syntax;
          key "id";
          leaf id {
            type uint16;
          }
          uses router-lisp-ip-route-import-database-grouping;
        }
        container rip {
          description
            "Routing Information Protocol (RIP)";
          tailf:cli-compact-syntax;
          uses router-lisp-ip-route-import-database-grouping;
        }
        container static {
          description
            "Static routes";
          tailf:cli-compact-syntax;
          uses router-lisp-ip-route-import-database-grouping;
        }
      }
      container map-cache {
        description
          "Use RIB routes to define EID address space in map-cache";
        list bgp {
          description
            "Border Gateway Protocol (BGP)";
          tailf:cli-suppress-mode;
          key "id";
          leaf id {
            type bgp-as-number-type;
          }
          uses router-lisp-ip-route-import-map-cache-grouping;
        }
        container connected {
          description
            "Connected";
          presence "true";
          tailf:cli-compact-syntax;
          uses router-lisp-ip-route-import-map-cache-grouping;
        }
        list eigrp {
          description
            "Enhanced Interior Gateway Routing Protocol (EIGRP)";
          tailf:cli-suppress-mode;
          key "id";
          leaf id {
            type uint16;
          }
          uses router-lisp-ip-route-import-map-cache-grouping;
        }
        list isis {
          description
            "ISO IS-IS";
          tailf:cli-suppress-mode;
          key "id";
          leaf id {
            type string;
          }
          uses router-lisp-ip-route-import-map-cache-grouping;
        }
        container maximum-prefix {
          description
            "Maximum number of prefixes to pick up from the RIB";
          tailf:cli-compact-syntax;
          tailf:cli-sequence-commands;
          leaf number {
            tailf:cli-drop-node-name;
            type int32;
          }
          choice threshold-warning {
            case warning-only-case {
              leaf warning-only {
                description
                  "Only give a warning message and do not limit entries";
                tailf:cli-optional-in-sequence;
                type empty;
              }
            }
            case threshold-case {
              leaf threshold {
                tailf:cli-drop-node-name;
                tailf:cli-optional-in-sequence;
                type uint8 {
                  range "1..100";
                }
              }
            }
            case threshold-warning-case {
              leaf threshold1 {
                tailf:cli-drop-node-name;
                tailf:cli-optional-in-sequence;
                type uint8 {
                  range "1..100";
                }
              }
              leaf warning-only1 {
                tailf:alt-name "warning-only";
                description
                  "Only give a warning message and do not limit entries";
                tailf:cli-optional-in-sequence;
                type empty;
              }
            }
          }
        }
        list ospf {
          description
            "Open Shortest Path First (OSPF)";
          tailf:cli-suppress-mode;
          key "id";
          leaf id {
            type uint16;
          }
          uses router-lisp-ip-route-import-map-cache-grouping;
        }
        list ospfv3 {
          description
            "OSPFv3";
          tailf:cli-suppress-mode;
          key "id";
          leaf id {
            type uint16;
          }
          uses router-lisp-ip-route-import-map-cache-grouping;
        }
        container rip {
          description
            "Routing Information Protocol (RIP)";
          presence "true";
          tailf:cli-compact-syntax;
          uses router-lisp-ip-route-import-map-cache-grouping;
        }
        container static {
          description
            "Static routes";
          presence "true";
          tailf:cli-compact-syntax;
          uses router-lisp-ip-route-import-map-cache-grouping;
        }
      }
    }
    leaf sgt {
      description
        "Enable security group tag propagation in LISP encapsulated traffic";
      tailf:cli-full-command;
      type empty;
    }
    container site-registration {
      description
        "Site registrations configuration for a given instance-id";
      tailf:cli-sequence-commands;
      tailf:cli-compact-syntax;
      leaf limit {
        description
          "Maximum number of site registrations for a given instance-id";
        type uint32;
      }
      leaf warning-threshold {
        description
          "Warning threshold to issue system logging";
        tailf:cli-optional-in-sequence;
        type uint8 {
          range "1..100";
        }
      }
    }
    container solicit-map-request {
      description
        "Configure Solicit-Map-Request handling";
      leaf ignore {
        description
          "Ignore SMR bit in incoming Map-Requests";
        tailf:cli-full-command;
        type empty;
      }
      leaf max-per-entry {
        description
          "Maximum number of SMRs for addresses under a map-cache entry";
        tailf:cli-full-command;
        type uint8 {
          range "1..100";
        }
      }
      leaf suppression-time {
        description
          "How long to suppress repeated SMRs for the same address";
        tailf:cli-full-command;
        type uint16 {
          range "1..600";
        }
      }
    }
    list use-petr {
      description
        "Encapsulate to Proxy ETR when matching forward-native entry";
      tailf:cli-suppress-mode;
      tailf:cli-sequence-commands;
      tailf:cli-compact-syntax;
      key "locator-address";
      leaf locator-address {
        type union {
          type inet:ipv4-address;
          type inet:ipv6-address;
        }
      }
      leaf priority {
        description
          "Configures which Locators from a set are preferred";
        tailf:cli-optional-in-sequence;
        type uint8;
      }
      leaf weight {
        description
          "Traffic load-spreading among Locators";
        tailf:cli-optional-in-sequence;
        type uint8 {
          range "0..100";
        }
      }
    }
  }

  grouping router-lisp-common-grouping {
    container alt {
      description
        "LISP Alternative Topology, LISP-ALT";
      tailf:display-when "../../../eid-table";
      list summary-route {
        description
          "Summary route to install into the ALT table";
        tailf:cli-suppress-mode;
        key "eid-prefix";
        leaf eid-prefix {
          type union {
            type inet:ipv4-prefix;
            type inet:ipv6-prefix;
          }
        }
        leaf route-tag {
          description
            "ALT RIB route tag for EID prefix";
          type uint32;
        }
      }
    }
    container control-packet {
      description
        "Configure control packet tx option";
      tailf:display-when "../../lisp or ../../lisp-list";
      leaf mtu {
        description
          "Configure control packet MTU";
        type uint32 {
          range "304..10000";
        }
      }
    }
    container ddt {
      description
        "Delegated Database Tree (DDT) mapping system";
      tailf:display-when "../../lisp or ../../lisp-list";
      presence "true";
      container authoritative {
        description
          "DDT authoritative prefix";
        list instance-id-eid-prefix-list {
          tailf:cli-drop-node-name;
          tailf:cli-mode-name "config-router-lisp-ddt-auth";
          key "instance-id eid-prefix";
          leaf instance-id {
            description
              "EID instance-ID";
            tailf:cli-expose-key-name;
            type uint32;
          }
          leaf eid-prefix {
            type union {
              type inet:ipv4-prefix;
              type inet:ipv6-prefix;
            }
          }
          uses router-lisp-ddt-authoritative-grouping;
        }
        list instance-id-list {
          tailf:cli-drop-node-name;
          tailf:cli-mode-name "config-router-lisp-ddt-auth";
          key "instance-id";
          leaf instance-id {
            type string;
          }
          uses router-lisp-ddt-authoritative-grouping;
        }
      }
      leaf cache-limit {
        description
          "DDT resolver cache entry limit";
        type uint32 {
          range "1..100000";
        }
      }
      leaf root {
        description
          "DDT root node";
        type union {
          type inet:ipv4-address;
          type inet:ipv6-address;
        }
      }
    }
    container decapsulation {
      description
        "Decapsulation behavior (e.g. filters)";
      container filter {
        description
          "Filters traffic";
        container rloc {
          description
            "Filter based on Routing Locator (RLOC) in packet header";
          container source {
            description
              "Filters traffic based on RLOC source address";
            tailf:cli-compact-syntax;
            leaf locator-set {
              description
                "Locator-set Name";
              type string;
            }
            leaf member {
              description
                "Members learned from map-server";
              type empty;
            }
          }
        }
      }
    }
    leaf disable-ttl-propagate {
      description
        "Disable ttl propagation";
      tailf:cli-full-command;
      type empty;
    }
    container ipv4 {
      description
        "IPv4 address family";
      uses router-lisp-ip-grouping;
    }
    container ipv6 {
      description
        "IPv6 address family";
      uses router-lisp-ip-grouping;
    }
    container loc-reach-algorithm {
      description
        "Configure locator reachability algorithm";
      container lsb-reports {
        description
          "Configure data packet LSB report handling";
        leaf do-not-transmit {
          description
            "Force the setting of the encapsulation header L bit to zero";
          type empty;
        }
        leaf ignore {
          description
            "Ignore data packet LSB reports";
          type empty;
        }
      }
      leaf rloc-probing {
        description
          "Probe high priority RLOCs with Map-Requests as last resort";
        type empty;
      }
    }
    container locator-down {
      description
        "Manually set locator status to down";
      tailf:display-when "../../lisp or ../../lisp-list";
      leaf address {
        description
          "IPv4/6 Locator address to be set down";
        tailf:cli-drop-node-name;
        tailf:cli-full-command;
        type union {
          type inet:ipv4-address;
          type inet:ipv6-address;
        }
      }
      leaf IPv4-interface {
        description
          "Use IPv4 address of interface as locator";
        tailf:cli-full-command;
        type string;
      }
      leaf IPv6-interface {
        description
          "Use IPv6 address of interface as locator";
        tailf:cli-full-command;
        type string;
      }
    }
    container locator-table {
      description
        "Specify the RLOC table";
      tailf:display-when "../../lisp or ../../lisp-list";
      leaf vrf-name {
        tailf:cli-drop-node-name;
        tailf:cli-full-command;
        type string;
      }
      leaf default {
        description
          "Default VRF";
        tailf:cli-full-command;
        type empty;
      }
      leaf vrf {
        description
          "VRF name";
        tailf:cli-full-command;
        type string;
      }
    }
    container map-request {
      description
        "Configure map-request handling";
      tailf:display-when "../../lisp or ../../lisp-list";
      leaf itr-rlocs {
        description
          "Configure to use the specified RLOC set as ITR RLOC in map-request";
        type string;
      }
    }
    container map-server {
      description
        "Map-Server commands";
      container rloc {
        description
          "EID instance RLOC membership";
        container members {
          description
            "EID instance RLOC membership";
          leaf distribute {
            description
              "EID instance RLOC membership distribution";
            type empty;
          }
          container modify-discovered {
            description
              "Modify the EID instance membership that is automaticallydiscovered from ETR registrations";
            tailf:cli-compact-syntax;
            tailf:cli-sequence-commands;
            leaf operator {
              tailf:cli-drop-node-name;
              type enumeration {
                enum "add";
                enum "override";
              }
            }
            leaf locator-set {
              description
                "Locator set from which to get member RLOC addresses";
              type string;
            }
          }
        }
      }
      container site-registration {
        description
          "Map-server site registration options";
        tailf:display-when "../../../lisp or ../../../lisp-list";
        tailf:cli-sequence-commands;
        tailf:cli-compact-syntax;
        leaf limit {
          description
            "Maximum number of site registrations as a result of accept-more-specifics";
          type uint32;
        }
        leaf warning-threshold {
          description
            "Warning threshold to issue system logging";
          tailf:cli-optional-in-sequence;
          type uint8 {
            range "1..100";
          }
        }
      }
    }
    container other-xtr-probe {
      description
        "Configure parameters for probing of other xTRs in our site";
      leaf period {
        description
          "Period between probes in seconds";
        type uint16 {
          range "5..900";
        }
      }
    }
    container remote-rloc-probe {
      description
        "Configure parameters for probing of remote RLOCs";
      leaf on-membership-change {
        description
          "Trigger probing upon membership changes for remote RLOC";
        tailf:cli-full-command;
        type empty;
      }
      leaf on-route-change {
        description
          "Trigger probing upon routing changes for remote RLOC";
        tailf:cli-full-command;
        type empty;
      }
    }
  }

  grouping router-lisp-locator-set-grouping {
    leaf priority {
      description
        "Configures which Locators from a set are preferred";
      tailf:cli-optional-in-sequence;
      type uint8;
    }
    leaf weight {
      description
        "Traffic load-spreading among Locators";
      tailf:cli-optional-in-sequence;
      type uint8 {
        range "0..100";
      }
    }
  }

  grouping router-lisp-key-grouping {
    leaf ak-0 {
      tailf:alt-name "0";
      description
        "The UNENCRYPTED (cleartext) password";
      type string;
    }
    leaf ak-6 {
      tailf:alt-name "6";
      description
        "The ENCRYPTED password";
      type string;
    }
    leaf unc-pwd {
      description
        "The UNENCRYPTED (cleartext) password";
      tailf:cli-drop-node-name;
      type string;
    }
  }

  grouping router-lisp-grouping {
    container encapsulation {
      description
        "Select encapsulation type for data packets";
      leaf vxlan {
        description
          "Use VXLAN encapsulation for data packets";
        type empty;
      }
    }
    list locator-set {
      description
        "Configure a named locator set";
      tailf:cli-mode-name "config-router-lisp-locator-set";
      key "name";
      leaf name {
        type string;
      }
      leaf auto-discover-rlocs {
        description
          "Auto discover locators registered by other xTRs";
        tailf:cli-full-command;
        type empty;
      }
      list IPv4-interface {
        description
          "Use IPv4 address of interface as locator";
        tailf:cli-suppress-mode;
        tailf:cli-sequence-commands;
        tailf:cli-compact-syntax;
        key "name";
        leaf name {
          type string;
        }
        uses router-lisp-locator-set-grouping;
      }
      list IPv6-interface {
        description
          "Use IPv6 address of interface as locator";
        tailf:cli-suppress-mode;
        tailf:cli-sequence-commands;
        tailf:cli-compact-syntax;
        key "name";
        leaf name {
          type string;
        }
        uses router-lisp-locator-set-grouping;
      }
      list ip-address {
        description
          "Use IPv6 address of interface as locator";
        tailf:cli-suppress-mode;
        tailf:cli-drop-node-name;
        tailf:cli-sequence-commands;
        tailf:cli-compact-syntax;
        key "ip";
        leaf ip {
          type union {
            type inet:ipv4-address;
            type inet:ipv6-address;
          }
        }
        uses router-lisp-locator-set-grouping;
      }
    }
    list locator-scope {
      description
        "Configure a locator scope";
      tailf:cli-mode-name "config-router-lisp-locator-scope";
      key "name";
      leaf name {
        type string;
      }
      leaf-list rloc-prefix {
        description
          "RLOC prefix to check against ITR RLOC and ETR RLOC";
        tailf:cli-list-syntax;
        type union {
          type inet:ipv4-prefix;
          type inet:ipv6-prefix;
        }
      }
      leaf-list rtr-locator-set {
        description
          "Locator-set of RTR to use in proxy reply for disjoint/cross AF RLOC";
        tailf:cli-list-syntax;
        type string;
      }
    }
    uses router-lisp-common-grouping;
    container eid-table {
      description
        "Configure an EID instance for a VRF";
      list instance-list {
        tailf:cli-drop-node-name;
        tailf:cli-mode-name "config-router-lisp-eid-table";
        key "instance-id";
        leaf instance-id {
          tailf:cli-expose-key-name;
          description
            "EID instance-ID";
          type uint32 {
            range "0..16777214";
          }
        }
        leaf vrf-name {
          tailf:cli-drop-node-name;
          tailf:cli-prefix-key;
          type string;
        }
        leaf default {
          description
            "Default VRF";
          tailf:cli-prefix-key;
          type empty;
        }
        leaf vrf {
          tailf:cli-prefix-key;
          type string;
        }
        list database-mapping {
          description
            "Configures Locator addresses for an ETR";
          tailf:cli-suppress-mode;
          key "eid-prefix";
          leaf eid-prefix {
            type union {
              type inet:ipv4-prefix;
              type inet:ipv6-prefix;
            }
          }
          leaf locator-set {
            description
              "Use locators defined by locator-set";
            tailf:cli-full-command;
            type string;
          }
        }
        list dynamic-eid {
          description
            "Configure a dynamic EID";
          tailf:cli-mode-name "config-router-lisp-eid-table-dynamic-eid";
          key "name";
          leaf name {
            type string;
          }
          list database-mapping {
            description
              "Configures EID-prefix and locator-set for dynamic-EID";
            tailf:cli-suppress-mode;
            key "eid-prefix";
            leaf eid-prefix {
              type inet:ipv4-prefix;
            }
            leaf locator-set {
              description
                "Use locators defined by locator-set";
              tailf:cli-full-command;
              type string;
            }
          }
          container eid-notify {
            description
              "Configure options for sending/receiving EID-notify";
            container authentication-key {
              description
                "Authentication key used for validating received EID-notify";
              uses router-lisp-key-grouping;
            }
            list gateway-key {
              tailf:cli-drop-node-name;
              tailf:cli-suppress-mode;
              tailf:cli-compact-syntax;
              key "gateway-ip";
              leaf gateway-ip {
                type union {
                  type inet:ipv4-address;
                  type inet:ipv6-address;
                }
              }
              uses router-lisp-key-grouping;
              leaf hash-function {
                description
                  "EID-notify authentication type";
                type enumeration {
                  enum "sha1";
                  enum "sha2";
                }
              }
            }
          }
          leaf map-notify-group {
            description
              "Multicast group which to send map-notifies to";
            tailf:cli-full-command;
            type union {
              type inet:ipv4-address;
              type inet:ipv6-address;
            }
          }
          list map-server {
            description
              "Configures map server for ETR registration";
            tailf:cli-suppress-mode;
            key "ip";
            leaf ip {
              type union {
                type inet:ipv4-address;
                type inet:ipv6-address;
              }
            }
            container key {
              description
                "Authentication key used with map server";
              tailf:cli-compact-syntax;
              leaf key-0 {
                tailf:alt-name "0";
                description
                  "The UNENCRYPTED (cleartext) password";
                type string;
              }
              leaf key-6 {
                tailf:alt-name "6";
                description
                  "The ENCRYPTED password";
                type string;
              }
              leaf key-7 {
                tailf:alt-name "7";
                description
                  "The HIDDEN password";
                type string;
              }
              leaf pwd {
                description
                  "The UNENCRYPTED (cleartext) password";
                tailf:cli-drop-node-name;
                type string;
              }
              leaf hash-function {
                description
                  "Map-Register authentication type";
                type enumeration {
                  enum "sha1";
                  enum "sha2";
                }
              }
            }
            leaf proxy-reply {
              description
                "Request Map-Server to send Map-Replies on behalf of site";
              tailf:cli-full-command;
              type empty;
            }
          }
        }
        uses router-lisp-common-grouping;
        list map-cache {
          description
            "Configures static EID-to-RLOC mappings for an ITR";
          tailf:cli-suppress-mode;
          key "eid-prefix";
          leaf eid-prefix {
            type union {
              type inet:ipv4-prefix;
              type inet:ipv6-prefix;
            }
          }
          container etr-interface-ip {
            tailf:cli-drop-node-name;
            tailf:cli-sequence-commands;
            tailf:cli-compact-syntax;
            leaf etr-interface-ip-address {
              tailf:cli-drop-node-name;
              type union {
                type inet:ipv4-address;
                type inet:ipv6-address;
              }
            }
            leaf priority {
              description
                "Configures which Locators from a set are preferred";
              type uint8;
            }
            leaf weight {
              description
                "Traffic load-spreading among Locators";
              type uint8 {
                range "0..100";
              }
            }
          }
          leaf drop {
            description
              "Drop packets that match this map-cache entry";
            tailf:cli-full-command;
            type empty;
          }
          leaf map-request {
            description
              "Send Map-Request for LISP destination EID";
            tailf:cli-full-command;
            type empty;
          }
          leaf native-forward {
            description
              "Natively forward packets that match this map-cache entry";
            tailf:cli-full-command;
            type empty;
          }
        }
      }
    }
    container security {
      description
        "Enable default LISP security and authentication in reply is optional";
      presence "true";
      leaf strong {
        description
          "Enable default LISP security and authentication in reply is required";
        type empty;
      }
    }
    list site {
      description
        "Configure a LISP site on a map server (MS)";
      tailf:cli-mode-name "config-router-lisp-site";
      key "sname";
      leaf sname {
        description
          "The site name";
        type string;
      }
      container authentication-key {
        description
          "Authentication key used by LISP site";
        uses router-lisp-key-grouping;
      }
      leaf description {
        description
          "Site description";
        tailf:cli-multi-value;
        type string;
      }
      container allowed-locator {
        description
          "Locator from LISP site";
        leaf ls-ipv4 {
          description
            "IPv4 locator allowed in registered locator-set";
          tailf:cli-drop-node-name;
          type inet:ipv4-address;
        }
        leaf ls-ipv6 {
          description
            "IPv6 locator allowed in registered locator-set";
          tailf:cli-drop-node-name;
          type inet:ipv6-address;
        }
        container list {
          description
            "Prefixes allowed in registerd locator-set";
          leaf ipv4 {
            description
              "IPv4 prefix-list name";
            type string;
          }
          leaf ipv6 {
            description
              "IPv6 prefix-list name";
            type string;
          }
        }
      }
      list eid-prefix {
        description
          "Site EID address prefix";
        tailf:cli-suppress-mode;
        tailf:cli-compact-syntax;
        key "prefix";
        leaf prefix {
          type union {
            type inet:ipv4-prefix;
            type inet:ipv6-prefix;
          }
        }
        leaf instance-id {
          description
            "EID instance-ID";
          tailf:cli-prefix-key;
          type uint32 {
            range "1..16777214";
          }
        }
        leaf accept-more-specifics {
          description
            "Accept registrations for more specific EID prefixes";
          tailf:cli-full-command;
          type empty;
        }
        leaf route-tag {
          description
            "RIB route tag";
          type uint32 {
            range "0..4294967295";
          }
        }
      }
      leaf site-id {
        description
          "Configure a site-id for this site";
        type uint32;
      }
    }
    leaf site-id {
      description
        "Configure a site-id for this site";
      type uint32;
    }
    container syslog {
      description
        "Configure syslog option";
      container session {
        description
          "Enable session syslog";
        leaf changes {
          description
            "Enable session change syslog";
          type empty;
        }
      }
      leaf verbose {
        description
          "Enable verbose syslog";
        type empty;
      }
    }
  }

  grouping object-group-service-grouping {
    leaf description {
      description
        "Service object group description";
      tailf:cli-multi-value;
      tailf:cli-full-command;
      type string;
    }
    leaf group-object {
      description
        "Nested object group";
      type string;
    }
    choice protocal-choice {
      case protocal-number-case {
        leaf protocal-number {
          tailf:cli-drop-node-name;
          tailf:cli-full-command;
          type uint8;
        }
      }
      case protocal-name-case {
        leaf ahp {
          description
            "Authentication Header Protocol";
          tailf:cli-full-command;
          type empty;
        }
        leaf eigrp {
          description
            "Cisco's EIGRP routing protocol";
          tailf:cli-full-command;
          type empty;
        }
        leaf esp {
          description
            "Encapsulation Security Payload";
          tailf:cli-full-command;
          type empty;
        }
        leaf gre {
          description
            "Cisco's GRE tunneling";
          tailf:cli-full-command;
          type empty;
        }
        container icmp {
          description
            "Internet Control Message Protocol";
          presence "true";
          leaf port-number {
            tailf:cli-drop-node-name;
            type uint8;
          }
          leaf alternate-address {
            description
              "Alternate address";
            tailf:cli-full-command;
            type empty;
          }
          leaf conversion-error {
            description
              "Datagram conversion";
            tailf:cli-full-command;
            type empty;
          }
          leaf echo {
            description
              "Echo (ping)";
            tailf:cli-full-command;
            type empty;
          }
          leaf echo-reply {
            description
              "Echo reply";
            tailf:cli-full-command;
            type empty;
          }
          leaf information-reply {
            description
              "Information replies";
            tailf:cli-full-command;
            type empty;
          }
          leaf information-request {
            description
              "Information requests";
            tailf:cli-full-command;
            type empty;
          }
          leaf mask-reply {
            description
              "Mask replies";
            tailf:cli-full-command;
            type empty;
          }
          leaf mask-request {
            description
              "Mask requests";
            tailf:cli-full-command;
            type empty;
          }
          leaf mobile-redirect {
            description
              "Mobile host redirect";
            tailf:cli-full-command;
            type empty;
          }
          leaf parameter-problem {
            description
              "All parameter problems";
            tailf:cli-full-command;
            type empty;
          }
          leaf redirect {
            description
              "All redirects";
            tailf:cli-full-command;
            type empty;
          }
          leaf router-advertisement {
            description
              "Router discovery advertisements";
            tailf:cli-full-command;
            type empty;
          }
          leaf router-solicitation {
            description
              "Router discovery solicitations";
            tailf:cli-full-command;
            type empty;
          }
          leaf source-quench {
            description
              "Source quenches";
            tailf:cli-full-command;
            type empty;
          }
          leaf time-exceeded {
            description
              "All time exceededs";
            tailf:cli-full-command;
            type empty;
          }
          leaf timestamp-reply {
            description
              "Timestamp replies";
            tailf:cli-full-command;
            type empty;
          }
          leaf timestamp-request {
            description
              "Timestamp requests";
            tailf:cli-full-command;
            type empty;
          }
          leaf traceroute {
            description
              "Traceroute";
            tailf:cli-full-command;
            type empty;
          }
          leaf unreachable {
            description
              "All unreachables";
            tailf:cli-full-command;
            type empty;
          }
        }
        leaf igmp {
          description
            "Internet Gateway Message Protocol";
          tailf:cli-full-command;
          type empty;
        }
        leaf ip {
          description
            "Any Internet Protocol";
          tailf:cli-full-command;
          type empty;
        }
        leaf ipinip {
          description
            "IP in IP tunneling";
          tailf:cli-full-command;
          type empty;
        }
        leaf nos {
          description
            "KA9Q NOS compatible IP over IP tunneling";
          tailf:cli-full-command;
          type empty;
        }
        leaf ospf {
          description
            "OSPF routing protocol";
          tailf:cli-full-command;
          type empty;
        }
        leaf pcp {
          description
            "Payload Compression Protocol";
          tailf:cli-full-command;
          type empty;
        }
        leaf pim {
          description
            "Protocol Independent Multicast";
          tailf:cli-full-command;
          type empty;
        }
        container tcp {
          description
            "Transmission Control Protocol";
          presence "true";
          list tcp-port-list {
            tailf:cli-drop-node-name;
            tailf:cli-suppress-mode;
            tailf:cli-compact-syntax;
            key "tcp-port";
            leaf tcp-port {
              type acl-tcp-port-type;
            }
            leaf operator {
              tailf:cli-drop-node-name;
              tailf:cli-prefix-key;
              type enumeration {
                enum "eq";
                enum "gt";
                enum "lt";
                enum "range";
              }
            }
            leaf max-tcp-port {
              tailf:cli-drop-node-name;
              type acl-tcp-port-type;
            }
          }
        }
        container tcp-udp {
          description
            "TCP or UDP protocol";
          presence "true";
          list udp-port-list {
            tailf:cli-drop-node-name;
            tailf:cli-suppress-mode;
            tailf:cli-compact-syntax;
            key "udp-port";
            leaf udp-port {
              type acl-udp-port-type;
            }
            leaf operator {
              tailf:cli-prefix-key;
              tailf:cli-drop-node-name;
              type enumeration {
                enum "eq";
                enum "gt";
                enum "lt";
                enum "range";
              }
            }
            leaf max-udp-port {
              tailf:cli-drop-node-name;
              type acl-udp-port-type;
            }
          }
        }
        container udp {
          description
            "User Datagram Protocol";
          presence "true";
          list udp-port-list {
            tailf:cli-drop-node-name;
            tailf:cli-suppress-mode;
            tailf:cli-compact-syntax;
            key "udp-port";
            leaf udp-port {
              type acl-udp-port-type;
            }
            leaf operator {
              tailf:cli-prefix-key;
              tailf:cli-drop-node-name;
              type enumeration {
                enum "eq";
                enum "gt";
                enum "lt";
                enum "range";
              }
            }
            leaf max-udp-port {
              tailf:cli-drop-node-name;
              type acl-udp-port-type;
            }
          }
        }
      }
    }
  }

  grouping mpls-te-path-selection-common {
    leaf metric {
      description
        "Metric Type Configuration";
      tailf:cli-full-command;
      type enumeration {
        enum "igp" {
          tailf:code-name "metric_igp";
        }
        enum "te" {
          tailf:code-name "metric_te";
        }
      }
    }
    container invalidation {
      description
        "Path invalidation configuration";
      tailf:cli-sequence-commands;
      tailf:cli-compact-syntax;
      leaf value {
        tailf:cli-drop-node-name;
        description
          "Enter path invalidation timer value in milliseconds";
        type int32 {
          range "0 .. 60000";
        }
      }
      leaf drop {
        description
          "Drop Tunnel Traffic";
        type empty;
      }
    }
  }

  grouping cts-server-grouping {
    leaf deadtime {
      description
        "Configure how long a server marked as dead should not be used";
      tailf:cli-full-command;
      type uint32 {
        range "0..864000";
      }
    }
    leaf enable {
      description
        "Enable server liveness automated test";
      tailf:cli-boolean-no;
      tailf:cli-trim-default;
      type boolean;
    }
    leaf idle-time {
      description
        "Configure how often to send an automated test message";
      tailf:cli-full-command;
      type uint32 {
        range "0..14400";
      }
    }
  }
  grouping diagnostic-daily-on-weekly {
    container daily {  
      description
        " Daily Schedule ";
      tailf:cli-break-sequence-commands;
      leaf hh-mm {
        description
          "Begin Time hh:mm";
	tailf:cli-drop-node-name;
	tailf:cli-full-command;
        type hhmm-type;
      }
    }  
    container on {  
      description
        " Absolute Schedule ";
      tailf:cli-sequence-commands;
      tailf:cli-compact-syntax;  
      leaf month {
        description
          "Enter month ->
	   Jan|Feb|Mar|Apr|May|Jun|Jul|Aug|Sep|Oct|Nov|Dec";
        tailf:cli-drop-node-name;
        type month-type;
      }
      leaf day-of-month {
        description
          " <1-31>  Day of month ";
        tailf:cli-drop-node-name;
        type uint16 {
          range "1..31";
        }
      }
      leaf Year {
        description
          "Enter Year <1993-2035>";
        tailf:cli-drop-node-name;
        type uint16 {
          range "1993..2035";
        }
      } 
      leaf hh-mm {
        description
          "Begin Time hh:mm";
	tailf:cli-drop-node-name;
	tailf:cli-full-command;
        type hhmm-type;
      }
    } // container on
    container weekly {
      description
	"Weekly schedule";
      tailf:cli-sequence-commands;
      tailf:cli-compact-syntax;
      leaf day {
        description
	"Enter Day of the week 
	 Mon|Tue|Wed|Thu|Fri|Sat|Sun";
	tailf:cli-drop-node-name;
        type weekday-type;
      }
      leaf hh-mm {
	description
          "Begin Time hh:mm";
	tailf:cli-drop-node-name;
	tailf:cli-full-command;
        type hhmm-type;
      }
    } // container weekly
  }

  grouping diagnostic-schedule-port {
    container port {
      description
	"Interface port selection"; 
      list interface-port-number {
        description
	  "Interface port number";
	tailf:cli-drop-node-name;
	tailf:cli-sequence-commands;
	tailf:cli-compact-syntax;
	key "number";
	leaf number {
          type uint8 {
            range "1..32";
          }
        }
        uses diagnostic-daily-on-weekly;
      } // list port-number 
      list port-number-list {
       	description
	  "Port number list (e.g. 2,4-7)";
	tailf:cli-drop-node-name;
	tailf:cli-sequence-commands;
	tailf:cli-compact-syntax;
	key "number-list";
	leaf number-list {
	  description
	    "Port number list (e.g. 2,4-7)";
  	  type string;
	}
	uses diagnostic-daily-on-weekly;
      } // port-number-list
      container all {
	description
	  "Select all ports";
	uses diagnostic-daily-on-weekly;
      }
    }
  }

// =========================================================================
//                        MODEL
// =========================================================================

  container native {
    tailf:cli-drop-node-name;
    //========================================================================
    // device yang model version information
    //========================================================================
//start-keep-defaults  
    container device-model-version {
      description
        "Version information for the device YANG model";
      leaf major {
        description
          "Major model version number";
        type string;
        default "2"; 
      }
      leaf minor {
        description
          "Minor model version number";
        type string;
        default "1";
      }
      leaf bug-fix {
        description
          "Bug fix version number";
        type string;
        default "0";
      }
    }
    
    /// ========================================================================
    /// version
    /// ========================================================================

    
    leaf version {
      description "Version";
      type string; 
    }
    /// ========================================================================
    /// boot system image file configurations for NG3K
    /// ========================================================================
    leaf boot-start-marker {
      type empty;
    }
      container boot {
        description "Modify boot system parameters";
        container system {
            description 
                "System Image";
                leaf  flash {
                  description 
                    "Boot from flash memory";
                  type string;
                }
                leaf tftp-path {
                tailf:alt-name "tftp://";
                tailf:cli-allow-join-with-value {
                   tailf:cli-display-joined;
                   }
                description "Example: 192.x.x.x/<path to image>";
                   type string;
                }
            container switch {
                description "Set system image for switches in the stack";
                list switch-number {
                    tailf:cli-drop-node-name;
                    tailf:cli-suppress-mode;
                    key "range";
                    leaf range {
                        description "Switch number";
                        type uint8 {
                            range "1..9";
                        }
                    }
                    leaf flash-1-path {
                        tailf:alt-name "flash-1:";
                        tailf:cli-allow-join-with-value {
                           tailf:cli-display-joined;
                        }
                        description "Example edison.bin";
                        type string;
                    }
                    leaf flash-path {
                        tailf:alt-name "flash:";
                        tailf:cli-allow-join-with-value {
                          tailf:cli-display-joined;
                        }
                        description "Example edison.bin";
                        type string;
                    }
                    leaf tftp-path {
                        tailf:alt-name "tftp://";
                        tailf:cli-allow-join-with-value {
                          tailf:cli-display-joined;
                        }
                        description "Example 192.x.x.x/<path>";
                        type string;
                    }
                }
                container all {
                    description "Set system image for all switches in the stack";
                    leaf flash-1 {
                        tailf:alt-name "flash-1:";
                        tailf:cli-allow-join-with-value {
                         tailf:cli-display-joined;
                        }
                        description "Example edison.bin";
                        type string;
                    }
                    leaf flash {
                        tailf:alt-name "flash:";
                        tailf:cli-allow-join-with-value {
                          tailf:cli-display-joined;
                        }
                        description "Example edison.bin";
                        type string;
                    }
                    leaf tftp {
                        tailf:alt-name "tftp://";
                        tailf:cli-allow-join-with-value {
                          tailf:cli-display-joined;
                        }
                        description "Example 192.x.x.x/<image-path>";
                        type string;
                    }
                }
            }
            leaf tftp {
                tailf:alt-name "tftp://";
                tailf:cli-allow-join-with-value {
                  tailf:cli-display-joined;
                }
                description "Example 192.168.x.x/<image-path>";
                type string;
            }
        }
        container enable-break {
            description "Enable break";
            presence true;
            leaf switch {
                description "Set enable break for switches in the stack";
                type uint8 {
                    range "1..9";
                }
            }
        }
        container manual {
            description "Manual boot";
            presence true;
            leaf switch {
                description "Set manual boot for switches in the stack:Switch number(s)";
                type uint8 {
                    range "1..9";
                }
            }
        }

    }

      
    leaf boot-end-marker {
      type empty;
    }
    /// ========================================================================
    /// call-home
    /// ========================================================================
    container call-home {
      description
        "Enter call-home configuration mode";
      tailf:cli-add-mode;
      tailf:cli-mode-name "cfg-call-home";
      presence true;      
      leaf contact-email-addr {
        description
          "Use email address";          
        type string;        
      }
      list profile {
        description
          "Enter call-home profile configuration mode";
        tailf:cli-mode-name "cfg-call-home-profile";          
        key profile-name;
        leaf profile-name {          
          type string;
        }
        uses cfg-call-home-profile;        
      }      
    }
    /// ========================================================================
    /// service-list
    /// ========================================================================
    container service-list {
      description "Enter the service list";
      list mdns-sd {
        description "Service-list for mdns-sd";
        tailf:cli-compact-syntax;
        tailf:cli-suppress-mode;
        key service-list-name;
        leaf service-list-name {
          description "service-list name";
          type string;                    
        }
        list deny {
          description "Specify packets to reject";
          key deny-pack;
          leaf deny-pack{
           type uint8 {            
            range "0..100";
           }
          }
          uses service-list-match-grouping;      
        }
        list permit {
          description "Specify packets to forward";
          key deny-pack;
          leaf deny-pack{
           type uint8 {
            range "0..100";
           }
          }
          uses service-list-match-grouping;
        }
        container query{
          description "Service-list Query for mdns-sd";
          tailf:cli-add-mode;
          leaf service-type {
            description "Configure periodicity for each service-type";
            type string;
          }
        }
      }
    }
    /// ========================================================================
    /// memory
    /// ========================================================================
    container memory {
      description "Configure memory management";
      container statistics {
        description "Configure statistics history table";
        container history {
          description "Configure statistics history table";
          leaf table {
            description "Configure statistics history table";
            type uint8 {
              range "12..72";
            }
          }
        }
      }
    }
    /// ========================================================================
    /// location
    /// ========================================================================
    container location {
      description "Global location configuration commands";
      container civic-location {
        description "Civic location information";
        list identifier {
          description "Set the identifier";
          tailf:cli-mode-name "config-civic";
          key identifier;
          leaf identifier{
            type string;
          }
          leaf building {
            description "Building information";
            type string;
          }
          leaf floor {
            description "Floor number";
            type string;
          }
          leaf landmark {
            description "Landmark";
            type string;
          }
          leaf name {
            description "Resident name";
            type string;
          }
          leaf number {
            description "Street number";
            type string;
          }
        }
      }
    }
    /// ========================================================================
    /// hw-module
    /// ========================================================================
    container hw-module {
      description
        "Control of individual components in the system";
      container uplink {
        description
          "Uplink control";
        leaf select {
          description
            "Select uplink interface";
          type string;
        }
        leaf mode {
          description
            "Uplink mode";
          type enumeration {
            enum "shared-backplane";
          }
        }
      }
      leaf sm {
        type uint8;
      }
      leaf pvdm {
        type string;
      }
    }
    ///========================================
    /// cisp
    ///=======================================
    container cisp {
      description "Set CISP parameters";
      leaf enable {
        description "Enable CISP";
        type empty;
      }
    }
    /// ========================================================================
    /// module
    /// ========================================================================
    container module {
      description
        "Module";
      container provision {
        description
          "Configure module provision status";
        list switch {
          key "number";
          leaf number {
            type uint8;
          }
          container chassis {
            tailf:cli-drop-node-name;
            tailf:cli-sequence-commands;
            tailf:cli-compact-syntax;
            leaf chassis-type {
              type uint32;
            }
            leaf base-mac {
              type string;
            }
          }
          list slot {
            tailf:cli-suppress-mode;
            tailf:cli-compact-syntax;
            key "number";
            leaf number {
              type uint8;
            }
            leaf slot-type {
              type uint32;
            }
            leaf base-mac {
              type string;
            }
          }
        }
      }
    }


    /// ========================================================================
    /// domain
    /// ========================================================================
    list domain {
      description
        "Domain Configuration Commands";
      tailf:cli-mode-name "config-domain";
      key "name";
      leaf name {
        type string;
      }
      list vrf {
        description
          "Specify vrf for domain";
        tailf:cli-mode-name "config-domain-vrf";
        key "name";
        leaf name {
          type string;
        }
        container border {
          description
            "Enter border router configuration submode";
          tailf:cli-add-mode;
          tailf:cli-mode-name "config-domain-vrf-br";
          container source-interface {
            description
              "Source Interface for border";
            leaf Loopback {
              description
                "Loopback interface";
              tailf:cli-allow-join-with-value {
                tailf:cli-display-joined;
              }
              type uint32;
            }
          }
          leaf master {
            description
              "Specify IP address of Domain master controller";
            type union {
              type inet:ipv4-address;
              type enumeration {
                enum "local";
              }
            }
          }
          container password {
            description
              "MD5 password to be used with MC";
            tailf:cli-compact-syntax;
            leaf encryption {
              tailf:cli-drop-node-name;
              type enumeration {
                enum "0";
                enum "7";
              }
            }
            leaf clear-key {
              tailf:cli-drop-node-name;
              tailf:cli-full-command;
              type string;
            }
          }
        }
        container master {
          description
            "Enter master controller configuration submode";
          tailf:cli-add-mode;
          tailf:cli-mode-name "config-domain-vrf-mc";
          choice master-type {
            case branch {
              leaf branch {
                description
                  "Set master type as branch hub";
                tailf:cli-hide-in-submode;
                type empty;
              }
            }
            case hub {
              leaf hub {
                description
                  "Set master type as hub";
                tailf:cli-hide-in-submode;
                type empty;
              }
            }
            case transit {
              leaf transit {
                description
                  "Set master type as transit";
                tailf:cli-hide-in-submode;
                type empty;
              }
            }
          }
          container advanced {
            description
              "Advanced configuration submode";
            tailf:cli-add-mode;
            tailf:cli-mode-name "config-domain-vrf-mc-advanced";
            leaf byte-loss-threshold {
              description
                "Specify minimum byte loss calculation threshold";
              tailf:cli-full-command;
              type uint16 {
                range "0..5600";
              }
            }
            leaf channel-unreachable-timer {
              description
                "Unreach interval detection";
              tailf:cli-full-command;
              type uint16 {
                range "1..65535";
              }
            }
            leaf load-sharing {
              description
                "Enable load-sharing";
              tailf:cli-full-command;
              type empty;
            }
            leaf minimum-mask-length {
              description
                "Specify minimum mask length";
              tailf:cli-full-command;
              type uint8 {
                range "1..32";
              }
            }
            leaf mitigation-mode {
              description
                "Enable brownout detection in domain";
              tailf:cli-full-command;
              type enumeration {
                enum "aggressive";
              }
            }
            leaf packet-loss-threshold {
              description
                "Specify minimum packet loss calculation threshold";
              tailf:cli-full-command;
              type uint8 {
                range "1..100";
              }
            }
            container smart-probes {
              description
                "Smart probes configuration";
              leaf destination-port {
                description
                  "Specify smart probes destination port number";
                tailf:cli-full-command;
                type uint16 {
                  range "1..65535";
                }
              }
              leaf source-port {
                description
                  "Specify smart probes source port number";
                tailf:cli-full-command;
                type uint16 {
                  range "1..65535";
                }
              }
            }
            container syslog {
              description
                "Specify syslog minimim time between tca";
              leaf tca-time-min {
                description
                  "Specify time between syslog tcas in seconds";
                type uint32 {
                  range "30..36000";
                }
              }
            }
            container tcp {
              description
                "Specify tcp port numbers for mc-br communication";
              leaf mc-port {
                description
                  "Specify tcp MC self port for mc-br communication";
                type uint16 {
                  range "1..65535";
                }
              }
            }
            leaf threshold-variance {
              description
                "Policy decision Threshold variance";
              tailf:cli-full-command;
              type uint8 {
                range "0..100";
              }
            }
            container traffic-class-ageout-timer {
              description
                "Traffic-class DB age timer";
              tailf:cli-sequence-commands;
              tailf:cli-compact-syntax;
              leaf interval {
                tailf:cli-drop-node-name;
                description
                  "Specify new timer interval value mins/hours";
                type uint16 {
                  range "5..65535";
                }
              }
              leaf interval-unit {
                tailf:cli-drop-node-name;
                type enumeration {
                  enum "hours";
                  enum "minutes";
                }
              }
            }
            leaf transit-site-affinity {
              description
                "Enable Transit Site Affinity";
              tailf:cli-full-command;
              type empty;
            }
          }
          container collector {
            description
              "NMS/v9 collector configuration";
            tailf:cli-sequence-commands;
            tailf:cli-compact-syntax;
            leaf ip {
              tailf:cli-drop-node-name;
              type inet:ipv4-address;
            }
            leaf port {
              description
                "Specify collector port number";
              tailf:cli-optional-in-sequence;
              type uint16;
            }
          }
          container enterprise-prefix {
            description
              "Enterprise prefix configuration";
            leaf prefix-list {
              description
                "Specify prefix-list with static site targets";
              type string;
            }
          }
          container load-balance {
            description
              "load balance non-policy traffic";
            presence "true";
            leaf advanced {
              description
                "Load balancing configuration mode";
              type empty;
            }
          }
          container password {
            description
              "MD5 password to be used with BRs";
            tailf:cli-compact-syntax;
            leaf encryption {
              tailf:cli-drop-node-name;
              type enumeration {
                enum "0";
                enum "7";
              }
            }
            leaf clear-key {
              tailf:cli-drop-node-name;
              tailf:cli-full-command;
              type string;
            }
          }
          container site-prefixes {
            description
              "site-prefixes configuration";
            leaf prefix-list {
              description
                "Specify prefix-list with static site targets";
              type string;
            }
          }
          container source-interface {
            description
              "Source Interface for master controller";
            leaf Loopback {
              description
                "Loopback interface";
              tailf:cli-allow-join-with-value {
                tailf:cli-display-joined;
              }
              type uint32;
            }
          }
          list class {
            description
              "Create domain class and enter domain class command mode";
            tailf:cli-mode-name "config-domain-vrf-mc-class";
            key "name sequence";
            leaf name {
              type string;
            }
            leaf sequence {
              description
                "Set the Sequence for the class";
              tailf:cli-expose-key-name;
              type uint16;
            }
            container match {
              description
                "Specify the applications the policy applies to";
              list dscp {
                description
                  "specify DSCP";
                tailf:cli-suppress-mode;
                key "value";
                leaf value {
                  type dscp-type;
                }
                leaf policy {
                  description
                    "Specify the policy (user defined/predefined)";
                  type enumeration {
                    enum "best-effort";
                    enum "bulk-data";
                    enum "custom";
                    enum "low-latency-data";
                    enum "real-time-video";
                    enum "scavenger";
                    enum "voice";
                  }
                }
              }
            }
            container path-preference {
              description
                "Specify the preferred provider";
              tailf:cli-sequence-commands;
              tailf:cli-compact-syntax;
              leaf-list primary {
                description
                  "Primary service provider";
                tailf:cli-drop-node-name;
                tailf:cli-flat-list-syntax;
                tailf:cli-disallow-value "fallback";
                ordered-by user;
                type string;
              }
              leaf-list fallback {
                description
                  "Specify the fallback provider";
                tailf:cli-flat-list-syntax;
                tailf:cli-disallow-value "primary";
                ordered-by user;
                type string;
              }
            }
          }
          leaf hub-ip {
            tailf:alt-name "hub";
            type inet:ipv4-address;
          }
        }
      }
    }

    /// ========================================================================
    /// parser
    /// ========================================================================
    container parser {
      description
        "Configure parser";
      container config {
        description
          "Configure config generation";
        leaf cache {
          description
            "Cache the configuration";
          type enumeration {
            enum "interface";
          }
        }
        leaf partition {
          description
            "Enable configuration Partitioning";
          tailf:cli-full-command;
          type empty;
        }
      }
    }


    /// ========================================================================
    /// service
    /// ========================================================================
    container service {
      description
        "Modify use of network based services";
      // service internal
      leaf internal {
        // Note: allow additional control of the LTE modem
        description 
          "Enable/Disable Internal commands";
        type empty;
      }
      // service keepalive-timeout-disable
      leaf keepalive-timeout-disable {
        description
          "Disable the IPC keepalive timeout mechanism";
        type empty;
      }
      // service pad
      container pad-conf {
        tailf:cli-no-keyword;
        tailf:cli-drop-node-name;
        leaf pad {
          description
            "Enable PAD commands";
          tailf:cli-boolean-no;
          type boolean;
        }
      }
      container pad {
        description
          "Enable PAD commands";
        tailf:cli-show-no;
        presence "true";
        leaf cmns {
          description
            "Enable PAD over CMNS connections";
          type empty;
        }
        leaf from-xot {
          description
            "Accept XOT to PAD connections";
          type empty;
        }
        leaf to-xot {
          description
            "Allow outgoing PAD over XOT connections";
          type empty;
        }
      }
      // service password-encryption
      leaf password-encryption {
        description
          "Encrypt system passwords";
        tailf:cli-full-command;
        type empty;
      }
          // service password-recovery
      leaf password-recovery {
        description "Enable password recovery";
        tailf:cli-boolean-no;
        tailf:cli-full-command;
        type boolean;
      }

      // service timestamps
      container timestamps {
        description
          "Timestamp debug/log messages";
        tailf:cli-compact-syntax;
        tailf:cli-delete-when-empty;
        presence "true";
        // service timestamps debug
        container debug {
          description
            "Timestamp debug messages";
          // service timestamps datetime
          container datetime {
            description
              "Timestamp with date and time";
            tailf:cli-compact-syntax;
            tailf:cli-delete-when-empty;
            presence "true";
            // service timestamps datetime msec
            leaf msec {
              description
                "Include milliseconds in timestamp";
              type empty;
            }
            leaf localtime {
              description
                "Use local time zone for timestamps";
              type empty;
            }
            leaf show-timezone {
              description
                "Add time zone information to timestamp";
              type empty;
            }
            leaf year {
              description
                "Include year in timestamp";
              type empty;
            }
          }
          leaf uptime {
            description
              "Timestamp with system uptime";
            type empty;
          }
        }
        // service timestamps log
        container log {
          description
            "Timestamp log messages";
          container datetime {
            description
              "Timestamp with date and time";
            tailf:cli-compact-syntax;
            tailf:cli-delete-when-empty;
            presence "true";
            leaf msec {
              description
                "Include milliseconds in timestamp";
              type empty;
            }
            leaf localtime {
              description
                "Use local time zone for timestamps";
              type empty;
            }
            leaf show-timezone {
              description
                "Add time zone information to timestamp";
              type empty;
            }
            leaf year {
              description
                "Include year in timestamp";
              type empty;
            }
          }
          leaf uptime {
            description
              "Timestamp with system uptime";
            type empty;
          }
        }
      }
      // service alignment
      container alignment {
        description
          "Control alignment correction and logging";
        leaf detection {
          description
            "Enable detection of alignment issues";
          type empty;
        }
        leaf logging {
          description
            "Enable logging of alignment issues";
          type empty;
        }
      }
      // service call-home
      leaf call-home {
        description
          "Enable call-home service";
        tailf:cli-full-command;
        type empty;
      }
      // service complete
      container complete {
        description
          "auto completion of";
        container hidden {
          description
            "hidden commands";
          leaf commands {
            description
              "commands enable";
            type empty;
          }
        }
      }
      // service compress-config
      leaf compress-config {
        description
          "Compress the configuration file";
        tailf:cli-full-command;
        type empty;
      }
      leaf config {
        description
          "TFTP load config files";
        tailf:cli-full-command;
        type empty;
      }
      // service counters
      container counters {
        description
          "Control aging of interface counters";
        container max {
          description
            "Maximum counter aging threshold";
          leaf age {
            description
              "Aging threshold";
            type uint8 {
              range "0..60";
            }
          }
        }
      }
      // service dhcp
      leaf dhcp {
        description
          "Enable DHCP server and relay agent";
        tailf:cli-full-command;
        type empty;
      }
      // service disable-ip-fast-frag
      leaf disable-ip-fast-frag {
        description
          "Disable IP particle-based fast fragmentation";
        tailf:cli-full-command;
        type empty;
      }
      // service exec-callback
      leaf exec-callback {
        description
          "Enable exec callback";
        tailf:cli-full-command;
        type empty;
      }
      // service exec-wait
      leaf exec-wait {
        description
          "Delay EXEC startup on noisy lines";
        tailf:cli-full-command;
        type empty;
      }
      // service finger
      leaf finger {
        description
          "Allow responses to finger requests";
        tailf:cli-full-command;
        type empty;
      }
      // service heartbeat
      container heartbeat {
        description
          "Enable heartbeat processing";
        leaf fatal-count {
          description
            "Set heartbeat fatal count";
          type uint8 {
            range "1..60";
          }
        }
        leaf interrupt-interval {
          description
            "Set heartbeat interrupt test interval";
          type uint8 {
            range "0..60";
          }
        }
        leaf interrupt-max {
          description
            "Set maximum message count from interrupt test";
          type uint8 {
            range "0..60";
          }
        }
        leaf transmit-interval {
          description
            "Set heartbeat transmit interval";
          type uint8 {
            range "1..30";
          }
        }
        leaf warning-timeout {
          description
            "Set heartbeat warning timeout interval";
          type uint8 {
            range "5..60";
          }
        }
      }
      // service hide-telnet-addresses
      leaf hide-telnet-addresses {
        description
          "Hide destination addresses in telnet command";
        tailf:cli-full-command;
        type empty;
      }
      //  image-version          image-version
      // service linenumber
      leaf linenumber {
        description
          "enable line number banner for each exec";
        tailf:cli-full-command;
        type empty;
      }
      // log-hidden
      leaf log-hidden {
          description 
            "Enable syslog msgs for hidden/internal commands";
          type empty;
      }
      // service nagle
      leaf nagle {
        description
          "Enable Nagle's congestion control algorithm";
        tailf:cli-full-command;
        type empty;
      }
      // service old-slip-prompts
      leaf old-slip-prompts {
        description
          "Allow old scripts to operate with slip/ppp";
        tailf:cli-full-command;
        type empty;
      }
      //  prompt                 Enable mode specific prompt
      container prompt {
          description 
            "Enable mode specific prompt";
          leaf config {
              description 
                "Enable configuration mode prompt";
              type empty;
          }
      }
      // service pt-vty-logging
      leaf pt-vty-logging {
        description
          "Log significant VTY-Async events";
        tailf:cli-full-command;
        type empty;
      }
      // service sequence-numbers
      leaf sequence-numbers {
        description
          "Stamp logger messages with a sequence number";
        tailf:cli-full-command;
        type empty;
      }
      // service slave-log
      leaf slave-log {
        description
          "Enable log capability of slave IPs";
        tailf:cli-full-command;
        type empty;
      }
      // service tcp-keepalives-in
      leaf tcp-keepalives-in {
        description
          "Generate keepalives on idle incoming network connections";
        tailf:cli-full-command;
        type empty;
      }
      // service tcp-keepalives-out
      leaf tcp-keepalives-out {
        description
          "Generate keepalives on idle outgoing network connections";
        tailf:cli-full-command;
        type empty;
      }
      //  telnet-zeroidle        Set TCP window 0 when connection is idle
      leaf telnet-zeroidle {
          description 
            "Set TCP window 0 when connection is idle";
          type empty;
      }
      //  timestamps             Timestamp debug/log messages
      //  service tcp-small-servers
      leaf tcp-small-servers {
        description
          "Enable small TCP servers (e.g., ECHO)";
        tailf:cli-show-no;
        type empty;
      }
      //  service udp-small-servers      Enable small UDP servers (e.g., ECHO)
      leaf udp-small-servers {
        description
          "Enable small UDP servers (e.g., ECHO)";
        tailf:cli-show-no;
        type empty;
      }
      // service unsupported-transceiver
      leaf unsupported-transceiver {
        description
          "Enable support for third-party transceivers";
        tailf:cli-full-command;
        type empty;
      }
    }
    /// ========================================================================
    /// platform
    /// ========================================================================
    container platform {
      description
        "platform specific configuration";
      leaf atm-cdvt {
        description
          "Configure platform atm cdvt";
        tailf:cli-boolean-no;
        type boolean;
      }
      leaf cfm {
        description 
          "Configure Multi-NNI CFM feature";
        type empty;
      }
      container cli-agent {
        description
          "Platform specific CLI Agent configuration";
        leaf error {
          description
            "Enable cliagent error at all time";
            type empty; 
        }
        leaf nvgen {
          description 
            "Enable cliagent NVGEN";
            type empty;
          }
      }
      container icmp {
        description 
          "Configure platform icmp";
        container rate-limit {
            description 
              "Rate limit of each ICMP types which are generated by data path";
            tailf:cli-sequence-commands;
            tailf:cli-compact-syntax;
            leaf packet {
              description 
                "Maximum # of packets allowed given a duration";
              tailf:cli-drop-node-name;
              type uint32 {
                 range "0..4294967295";
              }
            }
            leaf duration {
              description
                "Duration in seconds (default value is 1 second)";
              tailf:cli-drop-node-name;
              tailf:cli-optional-in-sequence;
              type uint32 {
                 range "0..4294967295";
              }
            }   
        }
      }
      container ip-ports {
         description
           "Configure Kernel IP ephemeral ports";
         leaf ephemeral-max {
              description
                "Maximum value for ephemeral ports for IOS";
              type uint16 {
                 range "49152..65534";
              }
         }
      }
      container bfd {
        description
          "Platform specific BFD commands";
        leaf disable-offload {
          description
            "Disable bfd hw offload";
          type empty;
        }
        leaf allow-svi {
          tailf:cli-full-command;
          type empty;
        }
        leaf enable-offload {
          tailf:cli-full-command;
          type empty;
        }
      }
      leaf bfd-debug-trace {
        type uint8;
      }
      container console {
        description
          "Direct IOS output to console";
        presence "true";
        leaf output {
          tailf:cli-drop-node-name;
          type enumeration {
            enum "auto";
            enum "serial";
            enum "virtual";
          }
        }
      }
      container enable {
        list controller {
          tailf:cli-suppress-mode;
          key "SONET";
          leaf SONET {
            description
              "SONET";
            tailf:cli-expose-key-name;
            type string;

            tailf:non-strict-leafref {
              path "/ios:native/controller/SONET/name";
            }

          }
        }
      }
      container external-alarm {
        tailf:cli-sequence-commands;
        tailf:cli-compact-syntax;
        leaf line {
          type uint32;
        }
        leaf alarm {
          type logging-level-type;
        }
      }
      container hardware {
        description
          "Configure platform hardware";
        container lite {
          leaf license {
            type enumeration {
              enum "enable";
            }
          }
        }
        container throughput {
          description
            "Configure throughput";
          choice throughput-choice {
            leaf disable {
              description
                "Disable throughput upgrade licenses";
              type enumeration {
                enum "internal-license";
              }
            }
            container level {
              description
                "Configure the current traffic throughput level";
              tailf:cli-compact-syntax;
              tailf:cli-sequence-commands;
              leaf kbps {
                tailf:cli-drop-node-name;
                type enumeration {
                  enum "10000";
                  enum "25000";
                  enum "50000";
                }
              }
              leaf eval-only {
                description
                  "Use only evaluation license";
                type empty;
              }
            }
          }
        }
      }
      container ipsec {
        description
          "Platform specific ipsec command";
        leaf arlog-supress {
          description 
            "supress anti-replay error log";
          type empty;
        }
        leaf fips-mode {
          description
            "enable FIPS mode";
          type empty;
        }
        leaf gdoi {
          description
            "gdoi";
          type enumeration {
            enum "accept-both";
          }
        }
        container llq {
          description
            "config LLQ";
          leaf qos-group {
            description
              "config LLQ QoS Group";
            type uint8 {
              range "1..99";
            }
          }
        }
        container reassemble {
          description
            "reassemble packets";
          leaf transit {
            description
              "transit IPSEC packets";
            type empty;
          }
        }
      }
      container l2vpn {
        description 
          "Configure platform l2vpn global configurtion";
        leaf hdlc-pass-through {
          description 
            "l2vpn HDLC force pass through";
          type empty;
        }
        container statistics {
          description 
            "l2vpn statistics";
          leaf enable {
            description 
              "enable the stats";
            type empty;
          }
        }
      }
      container multicast {
        description
          "Configure multicast";
        container mgre {
          description
            "Multi-point GRE tunnel";
          leaf injection {
            description
              "Enable packet injection";
            type empty;
          }
        }
        container oce {
          description
            "multicast oce";
          container flag {
            description
              "multicast oce flag";
            leaf suppress {
              description
                "Enable oce flag suppress";
              type empty;
            }
          }
        }
      }
      container punt-keepalive {
        description
          "punt-keepalive messages";
        presence true;
        leaf disable-kernel-core {
          description
            "Disable IOSXE kernel core generation for keepalive fault";
          type boolean;
          tailf:cli-boolean-no;
        }
        container settings {
          description
            "Set the keepalive parameters";
          leaf fatal-count {
            description
              "Set punt-inject keepalive fatal count";
            type uint16 {
              range "15..60";
            }
          }
          leaf transmit-interval {
            description
              "Set punt-inject keepalive transmit interval";
            type uint16 {
              range "2..30";
            }
          }
          leaf warning-count {
            description
              "Set punt-inject keepalive warning count";
            type uint16 {
              range "10..60";
            }
          }
        }
      }
      container punt-policer {
        description
          "Configures punt policers";
        //Check augmented platform specific modules for supported nodes
      }
      container qos {
        description
          "Platform specific qos configuration";
        leaf cac-policer {
          description 
            "packet per second";
          type uint16 {
             range "1..10000";
          }
        }
        leaf marker-statistics {
          description
            "Configure marking statistics";
          type empty;
        }
        container match-statistics {
          description
            "Configure match stats";
          leaf per-filter {
            description
              "Configure per-filter match statistics";
            tailf:cli-full-command;
            type empty;
          }
          leaf per-ace {
            description
              "Configure per-ace match statistics (per-filter must be enabled first)";
            tailf:cli-full-command;
            type empty;
          }
        }
        leaf performance-monitor {
          description
            "Configure performance-monitor statistics";
          type empty;
        }
        leaf punt-path-matching {
          description 
            "Configure punt-path matching on input interface (PPPoE-Discovery, PPPoE-PPP-LCP)";
          type empty;
        }
      }
      container reload {
        description
          "Platform specific reload command";
        leaf immediate {
          description
            "Immediately stop forwarding traffic";
          type empty;
        }
      }
      leaf shell {
        description
          "Control platform shell access command availability";
        type boolean;
        tailf:cli-boolean-no;
      }
      container snmp {
        tailf:alt-name "snp";
        description
          "Platform specific SNMP trap forwarding subsystem configuration";
        leaf polling {
          description 
            "Set SNMP trap filter polling interval in seconds";
            type uint16 {
                range "0..1000";
            }
        }
      }
      leaf tcam-parity-error {
        type enumeration {
          enum "enable";
          enum "disable";
        }
      }
      container urpf {
         description 
           "Platform specific urpf commands";
         container loose {
           description 
             "uRPF loose mode";
           container counter {
             description 
               "drop counter";
             container ipv4 {
               description
                 "ipv4 protocol";
               container supress {
                 description 
                   "supress drop";
                 leaf asymmetric_only {
                   description 
                     "it works only for asymmetric traffic";
                   type empty;
                 }
               }
             }
             container ipv6 {
               description 
                 "ipv6 protocol";
               container supress {
                  description 
                    "supress drop";
                  leaf asymmetric_only {
                     description 
                       "it works only for asymmetric traffic";
                     type empty;
                  }
               }
             }
          }
        }
      }
      container tcam-threshold {
        leaf alarm-frequency {
          type uint32;
        }
      }
      container trace {
        list runtime {
          tailf:cli-suppress-mode;
          key "slot bay";
          leaf slot {
            tailf:cli-expose-key-name;
            type uint8;
          }
          leaf bay {
            tailf:cli-expose-key-name;
            type uint8;
          }
          leaf process {
            tailf:cli-hide-in-submode;
            type enumeration {
              enum "iomd";
            }
          }
          leaf module {
            tailf:cli-hide-in-submode;
            type enumeration {
              enum "all-modules";
            }
          }
          leaf level {
            tailf:cli-hide-in-submode;
            type enumeration {
              enum "info";
            }
          }
        }
      }
    }
    /// ========================================================================
    /// hostname
    /// ========================================================================

    leaf hostname {
      description "Set system's network name";
      tailf:cli-no-value-on-delete;
      type string; 
    }


    /// ========================================================================
    /// enable
    /// ========================================================================
    container enable {
      description
        "Modify enable password parameters";
      container password {
        description
          "Assign the privileged level password (MAX of 25 characters)";
        tailf:cli-compact-syntax;
        tailf:cli-sequence-commands;
        tailf:cli-reset-container;
        uses password-07-grouping;
      }
      leaf last-resort {
        description
          "Define enable action if no TACACS servers respond";
        tailf:cli-full-command;
        type enumeration {
          enum "password";
          enum "succeed";
        }
      }
      container secret {
        description
          "Assign the privileged level secret";
        tailf:cli-compact-syntax;
        tailf:cli-sequence-commands;
        leaf level {
          description
            "Set exec level password";
          tailf:cli-optional-in-sequence;
          type uint8;
        }
        leaf type {
          tailf:cli-drop-node-name;
          tailf:cli-optional-in-sequence;
          type enumeration {
            enum "0";
            enum "4";
            enum "5";
          }
        }
        leaf secret {
          tailf:cli-drop-node-name;
          type string;
        }
      }
      leaf use-tacacs {
        description
          "Use TACACS to check enable passwords";
        tailf:cli-full-command;
        type empty;
      }
    }
    /// ========================================================================
    /// archive
    /// ========================================================================
    container archive {
      description
        "Archive the configuration";
      tailf:cli-add-mode;
      tailf:cli-mode-name "config-archive";
      // archive log
      container log {
        description
          "Logging commands";
        container config {
          description
            "Logging changes to the running configuration";
          tailf:cli-add-mode;
          tailf:cli-mode-name "config-archive-log-cfg";
          leaf hidekeys {
            description
              "suppress output (e.g. passwords) when displaying logged commands";
            type empty;
          }
          //archive log config / logging
          container logging {
            description
              "Modify config logging parameters";
            leaf enable {
              description
                "Enable the config logger";
              type empty;
            }
            leaf size {
              description
                "Maximum number of logged commands that will be kept by the config log";
              type uint16 {
                range "1..1000";
              }
            }
            container persistent {
              description
                "Log configuration persistent";
              presence "true";
              leaf auto {
                description
                  "Log configuration commands automatically";
                type empty;
              }
              leaf reload {
                description
                  "Apply persisted commands on reload";
                type empty;
              }
            }
          }
          //archive log config /notify
          container notify {
            description
              "Send logged commands to target applications";
            container syslog {
              description
                "Send logged commands as syslog messages";
              presence "true";
              leaf contenttype {
                description
                  "Type of the syslog message content";
                type enumeration {
                  enum "plaintext";
                  enum "xml";
                }
              }
            }
          }
        }
      }
      //archive path
      leaf path {
        description
          "path for backups";
        type union {
          type enumeration {
            enum "bootflash:";
            enum "flash:";
            enum "ftp:";
            enum "harddisk:";
            enum "http:";
            enum "https:";
            enum "pram:";
            enum "rcp:";
            enum "scp:";
            enum "tftp:";
          }
          type string;
        }
      }
      //archive maximum
      leaf maximum {
        description
          "maximum number of backup copies";
        tailf:cli-full-command;
        type uint8 {
          range "1..14";
        }
      }
      //archive time-period
      leaf time-period {
        description
          "Period of time in minutes to automatically archive the running-config";
        tailf:cli-full-command;
        type uint32 {
          range "1..525600";
        }
      }
    }
    /// ========================================================================
    /// username
    /// ========================================================================
    list username {
      description
        "Establish User Name Authentication";
      tailf:cli-suppress-mode;
      tailf:cli-delete-when-empty;
      tailf:cli-compact-syntax;
      key "name";
      leaf name {
        type string;
      }
      leaf privilege {
        description
          "Set user privilege level";
        type uint8 {
          range "0..15";
        }
      }
      //  access-class            Restrict access by access-class
      //  autocommand Automatically issue a command after the user logs in
      //  callback-dialstring     Callback dialstring
      //  callback-line           Associate a specific line with this callback
      //  callback-rotary         Associate a rotary group with this callback
      //  common-criteria-policy  Enter the common-criteria policy name
      //  dnis                    Do not require password when obtained via DNIS
      //  nocallback-verify       Do not require authentication after callback
      //  noescape                Prevent the user from using an escape character
      //  nohangup                Do not disconnect after an automatic command
      //  nopassword              No password is required for the user to log in
      
      //username * one-time
      leaf one-time {
        description
          "Specify that the username/password is valid for only one time";
        type empty;  
      }
      // username * privilege
      container password {
        description
          "Specify the password for the user";
        tailf:cli-compact-syntax;
        tailf:cli-flatten-container;
        tailf:cli-sequence-commands;
        //tailf:cli-reset-container;
        leaf encryption {
          tailf:cli-drop-node-name;
          tailf:cli-incomplete-command;
          tailf:cli-optional-in-sequence;
          type enumeration {
            enum "0";
            enum "7";
          }
        }
        // username * password
        leaf password {
          tailf:cli-drop-node-name;
          tailf:cli-trim-default;
          type string;
        }
      }
      // username * secret
      container secret {
        description
          "Specify the secret for the user";
        tailf:cli-compact-syntax;
        tailf:cli-flatten-container;
        tailf:cli-sequence-commands;
        //tailf:cli-reset-container;
        leaf encryption {
          tailf:cli-drop-node-name;
          tailf:cli-incomplete-command;
          tailf:cli-optional-in-sequence;
          type enumeration {
            enum "0";
            enum "5";
          }
        }
        leaf secret {
          tailf:cli-drop-node-name;
          tailf:cli-trim-default;
          type string;
        }
      }
      //  user-maxlinks           Limit the user's number of inbound links
      //  view                    Set view name
    }

    /// ========================================================================
    /// controller
    /// ========================================================================
    container controller {
      description
        "Configure controller";
      list controller-tx-ex-list {
        tailf:cli-drop-node-name;
        tailf:cli-mode-name "config-controller";
        key "name number";
        leaf name {
          type enumeration {
            enum "t1";
            enum "e1";
            enum "t3";
            enum "T1";
            enum "E1";
            enum "T3";
          }
        }
        leaf number {
          // Depending on device type:
          // slot/port
          // number
          // dial-shelf/slot/t3-port:t1-num
          // dial-shelf/slot/t3-port
          // slot/port-adapter/port
          type string;
        }
        // controller * / atm
        leaf atm {
          description
            "Specify atm";
          tailf:cli-full-command;
          type empty;
        }
        // controller * / framing
        leaf framing {
          tailf:cli-full-command;
          type string;
        }
        // controller * / clock
        container clock {
          container source {
            choice source-choice {
              container line {
                presence "true";
                leaf line-mode {
                  tailf:cli-drop-node-name;
                  tailf:cli-full-command;
                  type enumeration {
                    enum "primary";
                    enum "secondary";
                  }
                }
              }
              leaf internal {
                tailf:cli-full-command;
                type empty;
              }
              leaf loop-timed {
                tailf:cli-full-command;
                type empty;
              }
            }
          }
        }
        // controller * / linecode
        leaf linecode {
          tailf:cli-full-command;
          type enumeration {
            enum "ami";
            enum "b8zs";
            enum "hdb3";
          }
        }
        // controller * / cablelength
        container cablelength {
          choice cablelength-choice {
            leaf long {
              tailf:cli-full-command;
              type string;
            }
            leaf short {
              tailf:cli-full-command;
              type string;
            }
          }
        }
        // controller * / channel-group
        list channel-group {
          tailf:cli-suppress-mode;
          tailf:cli-delete-when-empty;
          key "number";
          leaf number {
            type uint8 {
              range "0..30";
            }
          }
          leaf-list timeslots {
            tailf:cli-replace-all;
            tailf:cli-range-list-syntax;
            type union {
              type uint16;
              type string;
            }
          }
        }
      }
      // controller * / Cellular
      list Cellular {
        key "id";
        leaf id {
          type string;
        }
        container lte {
          container modem {
            container link-recovery {
              container rssi {
                leaf onset-threshold {
                  type int32;
                }
              }
              leaf monitor-timer {
                tailf:cli-full-command;
                type uint32;
              }
              leaf wait-timer {
                tailf:cli-full-command;
                type uint32;
              }
              leaf debounce-count {
                tailf:cli-full-command;
                type uint32;
              }
            }
          }
        }
      }
      // controller SONET *
      list SONET {
        description
          "SONET";
        tailf:cli-allow-join-with-key {
          tailf:cli-display-joined;
        }
        tailf:cli-mode-name "config-sonet";
        tailf:cli-suppress-key-abbreviation;
        tailf:cli-full-command;
        key "name";
        leaf name {
          type string;
        }
        uses sonet-grouping;
      }
      // controller SONET-ACR *
      list SONET-ACR {
        description
          "SONET-ACR";
        tailf:cli-allow-join-with-key {
          tailf:cli-display-joined;
        }
        tailf:cli-mode-name "config-sonet";
        tailf:cli-suppress-key-abbreviation;
        tailf:cli-full-command;
        key "name";
        leaf name {
          type string {
            pattern "([0-9\\.])+";
          }
        }
        uses sonet-grouping;
      }
      // controller wanphy *
      list wanphy {
        description
          "wanphy";
        tailf:cli-allow-join-with-key {
          tailf:cli-display-joined;
        }
        tailf:cli-mode-name "config-sonet";
        tailf:cli-suppress-key-abbreviation;
        tailf:cli-full-command;
        key "name";
        leaf name {
          type string;
        }
      }
    }


    /// ========================================================================
    /// vrf
    /// ========================================================================
    // Note: /vrf must be before /ip and /ipv6
    container vrf {
      description
        "VRF commands";
      // vrf definition *
      list definition {
        description
          "VRF definition mode";
        tailf:cli-full-command;
        tailf:cli-mode-name "config-vrf";
        key "name";
        leaf name {
          description
            "WORD;;VRF name";
          type string;
        }
        // vrf definition * / description
        leaf description {
          description
            "VRF specific description";
          tailf:cli-multi-value;
          type string {
            length "1..244";
          }
        }
        // vrf definition * / rd
        leaf rd {
          description
            "Specify Route Distinguisher";
          tailf:cli-full-command;
          type union {
            type string {
              pattern "[0-9]+:[0-9]+";
            }
            type inet:ipv4-address;
          }
        }
        // vrf definition * / address-family
        container address-family {
          description
            "Enter Address Family command mode";
          // vrf definition * / address-family ipv4
          container ipv4 {
            description
              "Address family";
            tailf:cli-exit-command "exit-address-family";
            tailf:cli-add-mode;
            presence "true";
            //  bgp                  Commands pertaining to BGP
            container export {
              description
                "VRF export";
              tailf:cli-incomplete-command;
              leaf map {
                description
                  "WORD;;Route-map reference";
                type string;
              }
            }
            //  import               VRF import
            //  inter-as-hybrid      Inter AS hybrid mode
            //  maximum              Set a limit
            // vrf definition * / address-family ipv4 mdt
            container mdt {
              description
                "Backbone Multicast Distribution Tree";
              container default {
                description
                  "The default group";
                leaf address {
                  tailf:cli-drop-node-name;
                  tailf:cli-full-command;
                  tailf:cli-remove-before-change;
                  type inet:ipv4-address;
                }
                container mpls {
                  description
                    "MPLS tunnel options";
                  leaf mldp {
                    description
                      "Use a MLDP LSP to create the default MDT";
                    type inet:ipv4-address;
                  }
                }
              }
              container data {
                description
                  "MDT data trees";
                list multicast {
                  tailf:cli-drop-node-name;
                  tailf:cli-suppress-mode;
                  tailf:cli-delete-when-empty;
                  key "address wildcard";
                  leaf address {
                    type inet:ipv4-address;
                  }
                  leaf wildcard {
                    type inet:ipv4-address;
                  }
                }
                leaf list {
                  description
                    "Access-list";
                  type ext-acl-type;
                }
                // mpls     MPLS tunnel options
                leaf threshold {
                  description
                    "MDT switching threshold";
                  type uint32;
                }
              }
              leaf log-reuse {
                description
                  "Event logging for data MDT reuse";
                type empty;
              }
              leaf-list preference {
                description
                  "MDT preference (default pim mldp)";
                tailf:cli-flat-list-syntax {
                  tailf:cli-replace-all;
                }
                type enumeration {
                  enum "mldp";
                  enum "pim";
                }
              }
            }
            //  route-replicate      Replicate (import) routes..
            // ..from another topology (and another VRF)
            container route-target {
              description
                "Specify Target VPN Extended Communities";
              uses vrf-route-target-grouping;
            }
            //  snmp                 Modify snmp parameters
          }
          // vrf definition * / address-family ipv6
          container ipv6 {
            description
              "Address family";
            tailf:cli-exit-command "exit-address-family";
            tailf:cli-add-mode;
            presence "true";
            //  exit-address-family  Exit from vrf
            //                       address-family configuration submode
            //  export               VRF export
            //  import               VRF import
            //  inter-as-hybrid      Inter AS hybrid mode
            //  maximum              Set a limit
            //  route-target         Specify Target VPN Extended Communities
            container route-target {
              description
                "Specify Target VPN Extended Communities";
              uses vrf-route-target-grouping;
            }
            //  snmp                 Modify snmp parameters
          }
        }
        // vrf definition * / route-target
        container route-target {
          description
            "Specify Target VPN Extended Communities";
          uses vrf-route-target-grouping;
        }
        //  vnet            Virtual NETworking configuration
        //  vpn             Configure VPN ID as specified in rfc2685
      }
      // list "list" {
      //   tailf:info "List of VRFs";
      //   key id;
      // }
      //  selection    selection criteria
      //  upgrade-cli  upgrade cli
    }
    
    /// ========================================================================
    /// rmon
    /// ========================================================================
    container rmon {
      description
        "Remote Monitoring";
      list alarm {
        description
          "Configure an RMON alarm";
        tailf:cli-suppress-mode;
        tailf:cli-sequence-commands;
        tailf:cli-compact-syntax;
        key "number";
        leaf number {
          type uint16;
        }
        leaf mib-object {
          tailf:cli-drop-node-name;
          type string;
        }
        leaf sample-interval {
          tailf:cli-drop-node-name;
          type uint32;
        }
        leaf test-mode {
          tailf:cli-drop-node-name;
          type enumeration {
            enum "absolute";
            enum "delta";
          }
        }
        leaf rising-threshold {
          description
            "Configure the rising threshold";
          type int32;
        }
        leaf rising-event {
          tailf:cli-drop-node-name;
          tailf:cli-optional-in-sequence;
          type uint16;
        }
        leaf falling-threshold {
          description
            "Configure the falling threshold";
          type int32;
        }
        leaf falling-event {
          tailf:cli-drop-node-name;
          tailf:cli-optional-in-sequence;
          type uint16;
        }
        leaf owner {
          description
            "Specify an owner for the alarm";
          type string;
        }
      }
      list event {
        description
          "Configure an RMON event";
        tailf:cli-suppress-mode;
        key "number";
        leaf number {
          type uint16;
        }
        container log {
          description
            "Generate RMON log when the event fires";
          tailf:cli-compact-syntax;
          presence "true";
          leaf trap {
            description
              "Generate SNMP trap when the event fires";
            type string;
          }
          leaf description {
            description
              "Specify a description of the event";
            type string;
          }
          leaf owner {
            description
              "Specify an owner for the event";
            type string;
          }
        }
      }
    }
    /// ======================================================================
    /// sampler 
    /// ======================================================================
    list sampler {
      description
        "Define a Sampler";
      tailf:cli-mode-name "config-sampler";
      key "name";
      leaf name {
        tailf:cli-suppress-range;
        type string;
      }
      leaf description {
        description
          "Provide a description for this Sampler";
        tailf:cli-multi-value;
        tailf:cli-full-command;
        type string;
      }
      container mode {
        description
          "Sampling mode";
        container deterministic {
          description
            "Deterministic mode of sampling";
          tailf:cli-sequence-commands;
	  tailf:cli-compact-syntax;
          leaf number {
            tailf:cli-drop-node-name;
            type uint8;
          }
          leaf out-of {
            description
              "Select M packets out of an N packet window";
            tailf:cli-full-command;
            type uint16 {
              range "2..32768";
            }
          }
        }
        container hash {
          tailf:cli-sequence-commands;
	  tailf:cli-compact-syntax;
          description
            "Hash mode of sampling";
          leaf number {
            tailf:cli-drop-node-name;
            type uint8;
          }
          leaf out-of {
            tailf:cli-full-command;
            description
              "Select 1 packets out of an N packets based on hash of ip-id and udp / tcp checksum";
            type uint16 {
              range "1..65535";
            }
          }
        }
        container random {
          tailf:cli-sequence-commands;
	  tailf:cli-compact-syntax;
          description
            "Random mode of sampling";
          leaf number {
            tailf:cli-drop-node-name;
            type uint8;
          }
          leaf out-of {
            tailf:cli-full-command;
            description
              "Select M packets out of an N packet window";
            type uint16 {
              range "1..65535";
            }
          }
        }
      }
      container granularity {
        description
          "Specify sampler granularity";
        leaf connection {
          tailf:cli-full-command;
          type empty;
        }
        leaf packet {
          tailf:cli-full-command;
          type empty;
        }
      }
    }
    
    /// ========================================================================
    /// flow
    /// ========================================================================
    container flow {
      description
        "Global Flow configuration subcommands";
      list record {
        description
          "Define a Flow Record";
        tailf:cli-mode-name "config-flow-record";
        key "name";
        leaf name {
          type string;
          tailf:cli-disallow-value "type";
        }
        leaf type {
          description
            "Type of the Flow Record";
          tailf:cli-prefix-key;
          type enumeration {
            enum "performance-monitor";
          }
        }
        // flow record collect
        uses flow-record-collect-grouping;
        // flow record default
        container default {
          description
            "Set a command to its defaults";
          uses flow-record-collect-grouping;
          leaf description {
            description
              "Provide a description for this Flow Record";
            tailf:cli-multi-value;
            tailf:cli-full-command;
            type string;
          }
          //flow record match
          uses flow-record-match-grouping;
        }
        leaf description {
          description
            "Provide a description for this Flow Record";
          tailf:cli-multi-value;
          tailf:cli-full-command;
          type string;
        }
        uses flow-record-match-grouping;
      }
      list exporter {
        description
          "Define a Flow Exporter";
        tailf:cli-mode-name "config-flow-exporter";
        key "name";
        leaf name {
          type string;
        }
        uses flow-exporter-grouping;
        container default {
          description
            "Set a command to its defaults";
          uses flow-default-exporter-grouping;
        }
      }
      list monitor {
        description
          "Define a Flow Monitor";
        tailf:cli-mode-name "config-flow-monitor";
        tailf:cli-diff-dependency "../record";
        key "name";
        leaf name {
          type string;
          tailf:cli-disallow-value "type";
        }
        leaf type {
          description
            "Type of the Flow Record";
          tailf:cli-prefix-key;
          type enumeration {
            enum "performance-monitor";
          }
        }
        uses flow-monitor-grouping;
        container default {
          description
            "Set a command to its defaults";
          uses flow-default-monitor-grouping;
        }
      }
    }
    
    /// ========================================================================
    /// ip
    /// ========================================================================
    container ip {
      description
        "Global IP configuration subcommands";
      // ip mroute
      container mroute {
        description 
          "Configure static multicast routes";
        tailf:cli-compact-syntax;
        tailf:cli-sequence-commands;
        leaf source-address {
          tailf:cli-drop-node-name;
          type inet:ipv4-address;
        }
        leaf subnet-mask {
          tailf:cli-drop-node-name;
          type inet:ipv4-address;
        }
        leaf Tunnel {
          description
            "Tunnel interface";
            tailf:cli-allow-join-with-value {
              tailf:cli-display-joined;
            }
          type int32 {
            range "0..2147483647";
          }
        }
      }
      //ip admission
      container admission {
        description "Network Admission Control (NAC)";
        container watch-list {
          description "Watch-list";
          leaf expiry-time {
            description "Configure expiry time for watch-list entries";
            type uint16{
              range "0..35791";
            }
          }
        }  
        container name {
          description "Specify an Authentication Proxy Rule";
          container webauth {
            description "help";
            container proxy {
              description "Authentication Proxy Protocol";
              leaf http {
                description "HTTP Protocol";
		type empty;
	      }	 	
	    }
	  }
	}
      }
	
      // ip radius
      container radius {
        description 
          "RADIUS configuration commands";
        container source-interface {
          description 
            "Specify interface for source address in RADIUS packets";
          uses ethernet-grouping;
        }
      }
      //ip arp
      container arp {
        description
          "IP ARP global configuration";
        container incomplete {
          description "Fine-tune the ARP Retry parameters";
          leaf entries {
            description "Specify the number of IP addresses to resolve";
            type uint32 {
              range "1..2147483647";
            }
          }
        }  
        container inspection {
          description
            "Arp Inspection configuration";
          list filter {
            description "Specify ARP acl to be applied";
            tailf:cli-compact-syntax;
            tailf:cli-suppress-mode;
            key arpacl ;
            leaf arpacl {
              type string;
            }
            list vlan {
              description "Vlans to apply the filter";
              tailf:cli-compact-syntax;
              tailf:cli-suppress-mode;
              key vlan-range; 
              leaf vlan-range{
                type string;
              }
              leaf static {
                description "Apply the ACL statically";
                type empty;
              }
            }
          }
          container validate {
            description "Validate addresses";
            tailf:cli-compact-syntax;
            tailf:cli-flatten-container;
            leaf src-mac {
              description "Validate source MAC address";
              type empty;
            }
            leaf dst-mac {
              description "Validate destination MAC address";
              type empty;
            }
            leaf ip {
              description "Validate IP addresses";
              type empty;
            }
            container allow{
              tailf:cli-flatten-container;
              leaf zeros{
                description "Allow 0.0.0.0 sender IP address";
                type empty;
              }
            } 
          }
          container log-buffer {
            description
              "Log Buffer Configuration";
            leaf entries {
              description
                "Number of entries for log buffer";
              tailf:cli-full-command;
              type uint16 {
                range "0..1024";
              }
            }
            container logs {
              description
                "Number of logs per interval";
              tailf:cli-sequence-commands;
              tailf:cli-compact-syntax;
              leaf entries {
                tailf:cli-drop-node-name;
                description
                  "Number of entries for log buffer";
                type uint16 {
                  range "0..1024";
                }
              }
              leaf interval {
                description
                  "Interval for controlling logging rate";
                type uint32 {
                  range "0..86400";
                }
              }
            }
          }
          leaf vlan {
            description
              "Enable/Disable ARP Inspection on vlans";
            type string;
          }
        }
      }
      //ip domain-list
      container domain-list {
        description
          "Domain name to complete unqualified host names";
        leaf domain-name {
          tailf:cli-drop-node-name;
          type string;
        }
        container vrf {
          description
            "Specify VRF";
          tailf:cli-sequence-commands;
          tailf:cli-compact-syntax;
          leaf vrf-name {
            tailf:cli-drop-node-name;
            type string;
          }
          leaf domain-name {
            tailf:cli-drop-node-name;
            type string;
          }
        }
      }
      //ip finger
      container finger {
        description
          "finger server";
        tailf:cli-show-no;
        presence "true";
      }
      //ip icmp
      container icmp {
        description
          "ICMP options";
        container rate-limit {
          description
            "rate limit ICMP messages generated";
          container unreachable {
            description
              "ICMP type 3, Destination Unreachable";
            tailf:cli-compact-syntax;
            leaf time {
              description
                "Once per milliseconds";
              tailf:cli-drop-node-name;
              type uint32;
            }
            leaf DF {
              description
                "code 4, fragmentation needed and DF set";
              tailf:cli-incomplete-command;
              type empty;
            }
            container log {
              tailf:display-when "../time";
              description
                "log message if rate limiting is excessive";
              tailf:cli-compact-syntax;
              tailf:cli-sequence-commands;
              presence "true";
              leaf number-unreachables {
                tailf:cli-drop-node-name;
                description
                  "number of unreachables within interval to trigger a message";
                type uint32;
              }
              leaf log-message {
                tailf:cli-drop-node-name;
                tailf:cli-optional-in-sequence;
                description
                  "log message once per milliseconds";
                type uint32 {
                  range "10000..4294967295";
                }
              }
            }
          }
          leaf redirect {
            description
              "description";
            type enumeration {
              enum "host";
              enum "subnet";
            }
          }
        }
      }
      //ip rcmd
      container rcmd {
        description
          "Rcmd commands";
        leaf rcp-enable {
          description
            "Enable server side of RCP";
          tailf:cli-show-no;
          tailf:cli-full-command;
          type empty;
        }
        leaf rsh-enable {
          description
            "Enable server side of RSh";
          tailf:cli-show-no;
          tailf:cli-full-command;
          type empty;
        }
      }
      // ip subnet-zero
      leaf subnet-zero {
        description
          "Allow 'subnet zero' subnets";
        tailf:cli-boolean-no;
        tailf:cli-full-command;
        type boolean;
      }
      // ip bgp-community
      container bgp-community {
        description
          "format for BGP community";
        leaf new-format {
          description
            "select aa:nn format for BGP community";
          type empty;
        }
      }
      //ip host-routing
      leaf host-routing {
        description
          "Enable host-based routing (proxy ARP and redirect)";
        tailf:cli-full-command;
        type empty;
      }
      //ip msdp
      container msdp {
        description
          "MSDP global commands";
        uses ip-msdp-grouping;
        list vrf {
          description
            "Select VPN Routing/Forwarding instance";
          tailf:cli-suppress-mode;
          key "name";
          leaf name {
            type string;
          }
          uses ip-msdp-grouping;
        }
      }
      // ip vrf *
      list vrf {
        description
          "Configure an IP VPN Routing/Forwarding instance";
        tailf:cli-mode-name "config-vrf";
        key "name";
        leaf name {
          description
            "WORD;;VPN Routing/Forwarding instance name";
          type string;
        }
        // ip vrf * / bgp
        container bgp {
          description
            "Commands pertaining to BGP";
          container next-hop {
            description
              "Next-hop for the routes of a VRF in the backbone";
            leaf Loopback {
              description
                "Loopback interface number";
              type uint32 {
                range "0..2147483647";
              }
            }
          }
        }
        // ip vrf * / context
        leaf context {
          description
            "Associate SNMP context with this vrf";
          type string;
        }
        leaf description {
          description
            "VRF specific description";
          tailf:cli-multi-value;
          type string {
            length "1..244";
          }
        }
        // ip vrf * / rd
        leaf rd {
          description
            "Specify Route Distinguisher";
          type rd-type;
        }
        // ip vrf * / export
        container export {
          description
            "VRF export";
          leaf map {
            description
              "Route-map based VRF export";
            type string;
          }
        }
        // ip vrf * / import
        container import {
          // NOTE: needs special treatment when talking to backend
          // broken in real c7200 CLI
          description
            "VRF import";
          choice import-choice {
            leaf map {
              description
                "Route-map based VRF import";
              type string;
            }
            container ipv4 {
              tailf:cli-compact-syntax;
              tailf:cli-sequence-commands;
              description
                "Address family based VRF import";
              leaf ipv4-type {
                tailf:cli-drop-node-name;
                type enumeration {
                  enum "unicast" {
                    tailf:code-name "ipv41_unicast";
                  }
                  enum "multicast" {
                    tailf:code-name "ipv41_multicast";
                  }
                }
              }
              leaf upper-limit {
                tailf:cli-break-sequence-commands;
                tailf:cli-drop-node-name;
                type uint32 {
                  range "1..2147483647";
                }
              }
              leaf map {
                description
                  "Route-map based VRF import";
                type string;
              }
            }
          }
        }
        // ip vrf * / maximum
        container maximum {
          description
            "Maximum number of routes allowed in this routing table";
          tailf:cli-incomplete-command;
          tailf:cli-compact-syntax;
          tailf:cli-sequence-commands;
          presence "Maximum number of routes allowed in this routing table";
          leaf routes {
            description
              "Maximum number of routes allowed in this routing table";
            tailf:cli-incomplete-command;
            type uint32 {
              range "1..4294967295";
            }
          }
          choice maximum-choice {
            mandatory true;
            case threshold-case {
              leaf threshold {
                tailf:cli-drop-node-name;
                description
                  "";
                type uint16 {
                  range "1..100";
                }
              }
              leaf reinstall {
                description
                  "Reinstall previous rejected route due to over maximum route limit";
                type uint16 {
                  range "1..100";
                }
              }
            }
            case warning-case {
              leaf warning-only {
                description
                  "Only give a warning message if is limit exceeded";
                type empty;
              }
            }
          }
        }
        // ip vrf * / mdt
        container mdt {
          description
            "Backbone Multicast Distribution Tree";
          tailf:cli-incomplete-command;
          presence "Backbone Multicast Distribution Tree";
          leaf default {
            description
              "The default group";
            type inet:ipv4-address;
          }
          leaf log-reuse {
            description
              "Event logging for data MDT reuse";
            type empty;
          }
          container data {
            description
              "MDT data group range";
            tailf:cli-compact-syntax;
            leaf mulicast-address {
              tailf:cli-drop-node-name;
              tailf:cli-incomplete-command;
              type inet:ipv4-address;
            }
            leaf wildcard-bits {
              tailf:cli-drop-node-name;
              type inet:ipv4-address;
            }
            choice mdt-data-choice {
              case mdt-data-threshold {
                leaf threshold {
                  description
                    "MDT switching threshold";
                  type uint32 {
                    range "1..4294967";
                  }
                }
                leaf threshold-list {
                  tailf:alt-name "list";
                  description
                    "Access-list";
                  type mdt-data-list-type;
                }
              }
              case mdt-data-list {
                leaf list {
                  description
                    "Access-list";
                  type mdt-data-list-type;
                }
              }
            }
          }
        }
        // ip vrf * / route-target
        list route-target {
          description
            "Specify Target VPN Extended Communities";
          tailf:cli-suppress-mode;
          tailf:cli-delete-when-empty;
          key "direction target";
          // NOTE: the Cisco CLI does not require you to give
          // the direction, it will default to 'export' if not
          // given.
          leaf direction {
            type enumeration {
              enum "both";
              enum "export" {
                tailf:code-name "direction_export";
              }
              enum "import" {
                tailf:code-name "direction_import";
              }
            }
          }
          leaf target {
            type rd-type;
          }
        }
        // ip vrf * / vpn
        container vpn {
          description
            "Configure VPN ID as specified in rfc2685";
          leaf id {
            description
              "Configure VPN ID in rfc2685 format";
            type vpn-id-type;
          }
        }
      }
      // ip multicast-routing
      container mcr-conf {
        tailf:cli-no-keyword;
        tailf:cli-drop-node-name;
        leaf multicast-routing {
          description
            "Enable IP multicast forwarding";
          type empty;
        }
      }
      container multicast-routing {
        description
          "Enable IP multicast forwarding";
        tailf:cli-incomplete-no;
        tailf:cli-incomplete-command;
        tailf:cli-diff-dependency "/ios:native/ip/vrf";
        tailf:cli-diff-dependency "/ios:native/vrf/definition";
        tailf:cli-diff-dependency "../mcr-conf/multicast-routing";
        // ip multicast-routing vrf *
        list vrf {
          description
            "Select VPN Routing/Forwarding instance";
          tailf:cli-suppress-list-no;
          tailf:cli-suppress-mode;
          tailf:cli-delete-when-empty;
          tailf:cli-compact-syntax;
          tailf:cli-reset-container;
          tailf:cli-diff-dependency "../../mcr-conf/multicast-routing";
          key "name";
          leaf name {
            type string;
          }
          leaf distributed {
            description
              "Distributed multicast switching";
            type empty;
          }
        }
        // ip multicast-routing distributed
        leaf distributed {
          description
            "Distributed multicast switching";
          tailf:cli-full-command;
          type empty;
        }
      }
      // ip as-path
      container as-path {
        description
          "BGP autonomous system path filter";
        // ip as-path access-list *
        list access-list {
          description
            "Specify an access list number";
          tailf:cli-suppress-mode;
          tailf:cli-delete-when-empty;
          tailf:cli-incomplete-command;
          tailf:cli-compact-syntax;
          key "name";
          leaf name {
            tailf:cli-incomplete-command;
            tailf:cli-full-no;
            type uint16 {
              range "1..500";
            }
          }
          uses ip-community-list-expanded-grouping;
        }
      }
      // ip local
      container local {
        description
          "Specify local options";
        // ip local pool *
        list pool {
          description
            "IP Local address pool lists";
          tailf:cli-suppress-mode;
          tailf:cli-delete-when-empty;
          tailf:cli-compact-syntax;
          tailf:cli-sequence-commands {
            tailf:cli-reset-siblings;
          }
          key "id";
          leaf id {
            type union {
              type string;
              type enumeration {
                enum "default";
              }
            }
          }
          leaf start {
            tailf:cli-drop-node-name;
            type inet:ipv4-address;
          }
          leaf last {
            tailf:cli-drop-node-name;
            tailf:cli-optional-in-sequence;
            type inet:ipv4-address;
          }
          leaf group {
            description
              "Create ip local pool group";
            type string;
          }
        }
      }
      // ip cef
      container cef {
        description
          "Cisco Express Forwarding";
        presence "true";
        leaf distributed {
          description
            "Distributed Cisco Express Forwarding";
          tailf:cli-full-command;
          type empty;
        }
        //accounting          Enable CEF accounting
        //event-log           CEF event log commands
        //load-sharing        Load sharing
        //table               Set CEF forwarding table characteristics
        //traffic-statistics  Enable collection of traffic statistics
      }
      // ip classless
      leaf classless {
        description
          "Follow classless routing forwarding rules";
        type empty;
      }
      // ip community-list
      container community-list {
        description
          "Add a community list entry";
        list number-standard {
          tailf:cli-drop-node-name;
          tailf:cli-incomplete-command;
          tailf:cli-suppress-mode;
          tailf:cli-delete-when-empty;
          key "no";
          leaf no {
            type uint16 {
              range "1..99";
            }
          }
          uses ip-community-list-standard-grouping;
        }
        list number-expanded {
          tailf:cli-drop-node-name;
          tailf:cli-incomplete-command;
          tailf:cli-suppress-mode;
          tailf:cli-delete-when-empty;
          key "no";
          leaf no {
            type uint16 {
              range "100..500";
            }
          }
          uses ip-community-list-expanded-grouping;
        }
        list expanded {
          description
            "Add an expanded community-list entry";
          tailf:cli-incomplete-command;
          tailf:cli-suppress-mode;
          tailf:cli-delete-when-empty;
          key "name";
          leaf name {
            tailf:cli-full-no;
            type string;
          }
          uses ip-community-list-expanded-grouping;
        }
        list standard {
          description
            "Add a standard community-list entry";
          tailf:cli-incomplete-command;
          tailf:cli-suppress-mode;
          tailf:cli-delete-when-empty;
          key "name";
          leaf name {
            tailf:cli-full-no;
            type string;
          }
          uses ip-community-list-standard-grouping;
        }
      }
      // ip extcommunity-list
      container extcommunity-list {
        description
          "Extended a community list entry";
        list number-standard {
          tailf:cli-drop-node-name;
          tailf:cli-incomplete-command;
          tailf:cli-suppress-mode;
          tailf:cli-delete-when-empty;
          key "no";
          leaf no {
            type uint16 {
              range "1..99";
            }
          }
          uses ip-extcommunity-list-standard-grouping;
        }
        list number-expanded {
          tailf:cli-drop-node-name;
          tailf:cli-incomplete-command;
          tailf:cli-suppress-mode;
          tailf:cli-delete-when-empty;
          key "no";
          leaf no {
            type uint16 {
              range "100..500";
            }
          }
          uses ip-community-list-expanded-grouping;
        }
        list expanded {
          description
            "Extended an expanded community-list entry";
          tailf:cli-incomplete-command;
          tailf:cli-suppress-mode;
          tailf:cli-delete-when-empty;
          key "name";
          leaf name {
            tailf:cli-full-no;
            type string;
          }
          uses ip-community-list-expanded-grouping;
        }
        list standard {
          description
            "Extended a standard community-list entry";
          tailf:cli-incomplete-command;
          tailf:cli-suppress-mode;
          tailf:cli-delete-when-empty;
          key "name";
          leaf name {
            tailf:cli-full-no;
            type string;
          }
          uses ip-extcommunity-list-standard-grouping;
        }
      }
      // ip domain
      container domain {
        description
          "IP DNS Resolver";
        container list {
          description
            "Domain name to complete unqualified host names";
          leaf domain-name {
            tailf:cli-drop-node-name;
            type string;
          }
          container vrf {
            description
              "Specify VRF";
            tailf:cli-sequence-commands;
            tailf:cli-compact-syntax;
            leaf vrf-name {
              tailf:cli-drop-node-name;
              type string;
            }
            leaf domain-name {
              tailf:cli-drop-node-name;
              type string;
            }
          }
        }
        // ip domain lookup
        leaf lookup {
          description
            "Enable IP Domain Name System hostname translation";
          tailf:cli-boolean-no;
          tailf:cli-trim-default;
          type boolean;
        }
        container lookup-settings {
          tailf:cli-drop-node-name;
          container lookup {
            description
              "Enable IP Domain Name System hostname translation";
            leaf nsap {
              description
                "Enable IP DNS queries for CLNS NSAP addresses";
              tailf:cli-full-command;
              type empty;
            }
            container source-interface {
              description
                "Specify source interface for DNS resolver";
              tailf:cli-diff-dependency "/ios:native/interface";
              uses interface-grouping;
            }
          }
          leaf name {
            description
              "Define the default domain name";
            type string;
          }
        }
        // ip domain name
        leaf name {
          description
            "Define the default domain name";
          type string;
        }
      }
      // ip domain-lookup
      container domain-lookup-conf {
        tailf:cli-drop-node-name;
        leaf domain-lookup {
          tailf:cli-boolean-no;
          tailf:cli-full-command;
          type boolean;
        }
      }
      container domain-lookup {
        description
          "Enable IP Domain Name System hostname translation";
        tailf:cli-show-no;
        presence "true";
        leaf nsap {
          description
            "Enable IP DNS queries for CLNS NSAP addresses";
          type empty;
        }
        container source-interface {
          description
            "Specify source interface for DNS resolver";
          tailf:cli-diff-dependency "/ios:native/interface";
          uses interface-grouping;
        }
      }
      // ip domain-name
      leaf domain-name {
        description
          "Define the default domain name";
        type string;
      }
      // ip dns
      container dns {
        description
          "Configure DNS server for a zone";
        container server {
          description
            "Enable DNS server";
          presence "true";
        }
      }
      // ip default-gateway
      leaf default-gateway {
        description
          "Specify default gateway (if not routing IP)";
        type inet:ipv4-address;
      }
      // ip dhcp
      container dhcp {
        description
          "Configure DHCP server and relay parameters";
        list class {
          description
            "Configure DHCP classes";
          key "id";
          leaf id {
            type string;
          }
          // ip dhcp class * / relay
          container relay {
            description
              "Enter relay agent information option configuration submode";
            container agent {
              description
                "Enter relay agent information option configuration submode";
              leaf information {
                description
                  "Enter relay agent information option configuration submode";
                type empty;
              }
            }
          }
          // ip dhcp class * / remark
          leaf remark {
            description
              "Specify a remark for this class";
            tailf:cli-multi-value;
            type string {
              length "1..240";
            }
          }
        }
        //  compatibility              Compatibility configuration
        //  conflict                   DHCP address conflict parameters
        //  database                   Configure DHCP database agents
        //  excluded-address        Prevent DHCP from assigning certain addresses
        //  limit                      Limit DHCP Lease
        //  limited-broadcast-address  Use all 1's broadcast address
        //  ping                       Specify ping parameters used by DHCP

        //ip dhcp conflict *
        container conflict {
          description
            "DHCP address conflict parameters";
          leaf logging {
            description
              "Record address conflicts in a log file";
            tailf:cli-boolean-no;
            tailf:cli-trim-default;
            type boolean;
          }
          container resolution {
            description
              "DHCP address conflict resolution";
            presence "true";
            leaf interval {
              description
                "Time in Minutes";
              type uint32 {
                range "5..1440";
              }
            }
          }
        }
        //ip dhcp excluded-address
        list excluded-address {
          description
            "Prevent DHCP from assigning certain addresses";
          tailf:cli-suppress-mode;
          tailf:cli-compact-syntax;
          tailf:cli-sequence-commands;
          key "low-address";
          leaf low-address {
            type inet:ipv4-address;
          }
          leaf vrf {
            description
              "VRF name for excluded address range";
            tailf:cli-prefix-key;
            tailf:cli-optional-in-sequence;
            type string;
          }
          leaf high-address {
            tailf:cli-drop-node-name;
            type inet:ipv4-address;
          }
        }
        // ip dhcp pool *
        list pool {
          description
            "Configure DHCP address pools";
          tailf:cli-mode-name "dhcp-config";
          key "id";
          leaf id {
            type string;
          }
          //  accounting           Send Accounting Start/Stop messages
          //  bootfile             Boot file name
          //  class                Specify a DHCP class
          //  client-identifier    Client identifier
          //  client-name          Client name
          //  default-router       Default routers
          //  dns-server           DNS servers
          //  domain-name          Domain name
          //  exit                 Exit from DHCP pool configuration mode
          //  hardware-address     Client hardware address
          //  host                 Client IP address and mask
          //  lease                Address lease time
          //  netbios-name-server  NetBIOS (WINS) name servers
          //  netbios-node-type    NetBIOS node type
          //  network              Network number and mask
          //  next-server          Next server in boot process
          //  no                   Negate a command or set its defaults
          //  option               Raw DHCP options
          //  origin               Configure the origin of the pool
          //  relay                Function as a DHCP relay
          //  renew                Configure renewal policy
          //  server               Configure the server ID option value
          //  subnet               Subnet allocation commands
          //  update               Dynamic updates
          //  utilization          Configure various utilization parameters
          //  vrf                  Associate this pool with a VRF
          list lease {
            description 
              "Address lease time";
            tailf:cli-suppress-mode;
            tailf:cli-compact-syntax;
            tailf:cli-sequence-commands;
            key "Days";
            leaf Days {
                type uint16 {
                range "0..365";
              }
            }
            leaf Hours {
              tailf:cli-drop-node-name;
              description 
                "Hours";
              type uint8;
            }
            leaf Minutes {
              tailf:cli-drop-node-name;
              description 
                "Minutes";
              type uint8;
            }
          }
          leaf-list default-router {
            description
              "Default routers";
            tailf:cli-flat-list-syntax;
            type union {
              type string;
              type inet:ipv4-address;
            }
          }
          leaf-list dns-server {
            description
              "DNS servers";
            tailf:cli-flat-list-syntax;
            type union {
              type string;
              type inet:ipv4-address;
            }
          }
          leaf domain-name {
            description
              "Domain name";
            tailf:cli-full-command;
            type string;
          }
          container network {
            description
              "Network number and mask";
            tailf:cli-compact-syntax;
            tailf:cli-sequence-commands;
            leaf number {
              tailf:cli-drop-node-name;
              type inet:ipv4-address;
            }
            leaf mask {
              tailf:cli-drop-node-name;
              tailf:cli-optional-in-sequence;
              type union {
                type string;
                type inet:ipv4-address;
              }
            }
            leaf secondary {
              description
                "Configure as secondary subnet";
              type empty;
            }
          }
        }
        //  relay                      DHCP relay agent parameters
        container relay {
          description
            "DHCP relay agent parameters";
          container information {
            description
              "Relay agent information option";
            leaf trust-all {
              description
                "Received DHCP packets may contain relay info option with zero giaddr";
              type empty;
            }
          }
        }
        //  route  Specify the type of routes for clients on unnumbered interfaces

        // ip dhcp smart-relay
        leaf smart-relay {
          description
            "Enable Smart Relay feature";
          type empty;
        }
        // ip dhcp snooping
        container snooping-conf {
          tailf:cli-no-keyword;
          tailf:cli-drop-node-name;
          leaf snooping {
            description
              "DHCP Snooping";
            type empty;
          }
        }
        container snooping {
          description
            "DHCP Snooping";
          //  database     DHCP snooping database agent
          container database {
            description
              "DHCP snooping database agent";
            leaf url {
              tailf:cli-drop-node-name;
              tailf:cli-full-command;
              type string;
            }
            leaf timeout {
              description
                "Configure abort timeout interval";
              tailf:cli-full-command;
              type uint32 {
                range "0..86400";
              }
            }
            leaf write-delay {
              description
                "Configure delay timer for writes to URL";
              tailf:cli-full-command;
              type uint32 {
                range "15..86400";
              }
            }
          }
          container information {
            description
              "DHCP Snooping information";
            leaf option-conf {
              tailf:alt-name "option";
              tailf:cli-boolean-no;
              tailf:cli-full-command;
              type boolean;
            }  
            container option {
              description
                "DHCP Snooping information option";
              presence "true";
              leaf allow-untrusted {
                description
                  "DHCP Snooping information option allow-untrusted";
                type empty;
              }
              container format {
                description
                  "Option 82 information format";
                container remote-id {
                  description
                    "Remote id option 82 format";
                  choice remote-id-choice {
                    leaf hostname {
                      description
                        "Use configured hostname for remote id";
                      type empty;
                    }
                    leaf string {
                      description
                        "User defined string for remote id";
                      type string;
                    }
                  }
                }
              }
            }
          }
          container track {
            description
              "DHCP snooping track";
            leaf host {
              description
                "DHCP snooping track host";
              type empty;
            }
          }
          container verify {
            description
              "DHCP snooping verify";
            leaf mac-address {
              description
                "DHCP snooping verify mac-address";
              type empty;
            }
            leaf no-relay-agent-address {
              description
                "DHCP snooping verify giaddr";
              type empty;
            }
          }
          leaf vlan {
            description
              "DHCP Snooping vlan";
            type string;
          }
        }
        //  use        Configure use of certain parameters during allocation
      }
      // ip flow-cache
      container flow-cache {
        description
          "Configure netflow cache parameters";
        container timeout {
          description
            "Specify flow cache timeout parameters";
          leaf active {
            description
              "Specify the active flow timeout";
            type uint16 {
              range "1..60";
            }
          }
        }
      }
      // ip flow-export
      container flow-export {
        description
          "Specify host/port to send flow statistics";
        // ip flow-export destination
        container destination {
          description
            "Specify the Destination IP address";
          tailf:cli-sequence-commands {
            tailf:cli-reset-all-siblings;
          }
          tailf:cli-compact-syntax;
          leaf ip {
            tailf:cli-drop-node-name;
            type host-type;
          }
          leaf port {
            tailf:cli-drop-node-name;
            type uint16 {
              range "1..65535";
            }
          }
        }
        // ip flow-export source
        container source {
          description
            "Specify the interface for source address";
          tailf:cli-diff-dependency "/ios:native/interface";
          uses interface-grouping;
        }
        //template     Specify the template specific configurations
        // ip flow-export version
        leaf version {
          description
            "Specify the version number";
          type enumeration {
            enum "1";
            enum "5";
            enum "9";
          }
        }
      }
      // ip forward-protocol
      container forward-protocol {
        description
          "Controls forwarding of physical and directed IP broadcasts";
        choice protocol-choice {
          leaf protocol {
            tailf:cli-drop-node-name;
            type enumeration {
              enum "nd";
              enum "sdns";
              enum "turbo-flood";
            }
          }
          container spanning-tree {
            description
              "Use transparent bridging to flood UDP broadcasts";
            presence "true";
            leaf any-local-broadcast {
              description
                "Accept any local broadcast when flooding";
              type empty;
            }
          }
          container udp {
            description 
              "Packets to a specific UDP port";
            leaf biff {
              description 
                "Biff (mail notification, comsat, 512)";
              tailf:cli-boolean-no;
              tailf:cli-full-command;
              type boolean;
            }        
            leaf bootpc {
              description 
                "Bootstrap Protocol (BOOTP) client (68)";
              tailf:cli-boolean-no;
              tailf:cli-full-command;
              type boolean;
            }        
            leaf bootps {
              description
                "Bootstrap Protocol (BOOTP) server (67)";
              tailf:cli-boolean-no;
              tailf:cli-full-command;
              type boolean;
            }
            leaf discard {
              description 
                "Discard (9)";
              tailf:cli-boolean-no;
              tailf:cli-full-command;
              type boolean;
            }
            leaf dnsix {
              description
                "DNSIX security protocol auditing (195)";
              tailf:cli-boolean-no;
              tailf:cli-full-command;
              type boolean;
            }
            leaf domain {
              description 
                "Domain Name Service (DNS, 53)";
              tailf:cli-boolean-no;
              tailf:cli-full-command;
              type boolean;
            }
            leaf echo {
              description
                "Echo (7)";
              tailf:cli-boolean-no;
              tailf:cli-full-command;
              type boolean;
            }
            leaf isakmp {
              description
                "Internet Security Association and Key Management Protocol(500)";
              tailf:cli-boolean-no;
              tailf:cli-full-command;
              type boolean;
            }
            leaf mobile-ip {
              description
                "Mobile IP registration (434)";
              tailf:cli-boolean-no;
              tailf:cli-full-command;
              type boolean;
            }
            leaf nameserver {
              description
                "IEN116 name service (obsolete, 42)";
              tailf:cli-boolean-no;
              tailf:cli-full-command;
              type boolean;
            }
            leaf netbios-dgm {
              description
                "NetBios datagram service (138)";
              tailf:cli-boolean-no;
              tailf:cli-full-command;
              type boolean;
            }
            leaf netbios-ns {
              description
                "NetBios name service (137)";
              tailf:cli-boolean-no;
              tailf:cli-full-command;
              type boolean;
            }
            leaf netbios-ss {
              description
                "NetBios session service (139)";
              tailf:cli-boolean-no;
              tailf:cli-full-command;
              type boolean;
            }
            leaf non500-isakmp {
              description
                "Internet Security Association and Key Management Protocol(4500)";
              tailf:cli-boolean-no;
              tailf:cli-full-command;
              type boolean;
            }
            leaf ntp {
              description
                "Network Time Protocol (123)";
              tailf:cli-boolean-no;
              tailf:cli-full-command;
              type boolean;
            }
            leaf pim-auto-rp {
              description
                "PIM Auto-RP (496)";
              tailf:cli-boolean-no;
              tailf:cli-full-command;
              type boolean;
            }
            leaf rip {
              description
                "Routing Information Protocol (router, in.routed, 520)";
              tailf:cli-boolean-no;
              tailf:cli-full-command;
              type boolean;
            }
            leaf snmp {
              description
                "Simple Network Management Protocol (161)";
              tailf:cli-boolean-no;
              tailf:cli-full-command;
              type boolean;
            }
            leaf snmptrap {
              description
                "SNMP Traps (162)";
              tailf:cli-boolean-no;
              tailf:cli-full-command;
              type boolean;
            }
            leaf sunrpc  {
              description
                "Sun Remote Procedure Call (111)";
              tailf:cli-boolean-no;
              tailf:cli-full-command;
              type boolean;
            }
            leaf syslog  {
              description
                "System Logger (514)";
              tailf:cli-boolean-no;
              tailf:cli-full-command;
              type boolean;
            }
            leaf tacacs  {
              description
                "TAC Access Control System (49)";
              tailf:cli-boolean-no;
              tailf:cli-full-command;
              type boolean;
            }
            leaf talk {
              description
                "Talk (517)";
              tailf:cli-boolean-no;
              tailf:cli-full-command;
              type boolean;
            }
            leaf tftp {
              description
                "Trivial File Transfer Protocol (69)";
              tailf:cli-boolean-no;
              tailf:cli-full-command;
              type boolean;
            }
            leaf time {
              description
                "Time (37)";
              tailf:cli-boolean-no;
              tailf:cli-full-command;
              type boolean;
            }
            leaf who  {
              description
                "Who service (rwho, 513)";
              tailf:cli-boolean-no;
              tailf:cli-full-command;
              type boolean;
            }
            leaf xdmcp {
              description
                "X Display Manager Control Protocol (177)";
              tailf:cli-boolean-no;
              tailf:cli-full-command;
              type boolean;
            }
          }
        }
      }
      // ip ftp
      container ftp {
        description
          "FTP configuration commands";
        container source-interface {
          description
            "Specify interface for source address in FTP connections";
          tailf:cli-diff-dependency "/ios:native/interface";
          uses interface-grouping;
        }
        leaf passive {
          description
            "Connect using passive mode";
          type empty;
        }
        container password {
          description
            "Specify password for FTP connections;";
          uses password-grouping;
        }
        leaf username {
          description
            "Specify username for FTP connections";
          type string;
        }
      }
      // ip telnet
      container telnet {
        description
          "Specify telnet options";
        leaf source-interface {
          description
            "Specify source interface";
          type string;
        }
      }
      // ip host
      list host {
        description
          "Add an entry to the ip hostname table";
        tailf:cli-suppress-mode;
        key "name";
        leaf name {
          type string;
        }
        leaf ip {
          tailf:cli-drop-node-name;
          type inet:ip-address;
        }
      }
      // ip http
      container http {
        description
          "HTTP server configuration";
        leaf access-class {
          description
            "Restrict http server access by access-class";
          tailf:cli-full-command;
          type uint8 {
            range "1..99";
          }
        }
        // ip http authentication
        container authentication {
          description
            "Set http server authentication method";
          choice authentication-choice {
            leaf aaa {
              description
                "Use AAA access control methods";
              tailf:cli-full-command;
              tailf:cli-diff-dependency "/ios:native/aaa/new-model";
              type empty;
            }
            leaf local {
              description
                "Use local username and passwords";
              tailf:cli-full-command;
              type empty;
            }
          }
        }
        // ip http server
        leaf server {
          description
            "Enable http server";
          tailf:cli-boolean-no;
          tailf:cli-show-with-default;
          tailf:cli-full-command;
          type boolean;
        }
        // ip http secure-server
        leaf secure-server {
          description
            "Enable HTTP secure server";
          tailf:cli-boolean-no;
          tailf:cli-show-with-default;
          tailf:cli-full-command;
          type boolean;
        }
        // ip http secure-trustpoint
        leaf secure-trustpoint {
          description
            "Set http secure server certificate trustpoint";
          type string;
        }
        // ip http timeout-policy
        container timeout-policy {
          description
            "Set http server time-out policy parameters";
          tailf:cli-compact-syntax;
          tailf:cli-reset-container;
          tailf:cli-sequence-commands;
          leaf idle {
            description
              "Idle time-out of a http server connection in seconds";
            tailf:cli-incomplete-command;
            type uint16 {
              range "1..600";
            }
          }
          leaf life {
            description
              "Life time of a http server connection in seconds";
            tailf:cli-incomplete-command;
            type uint32 {
              range "1..86400";
            }
          }
          leaf requests {
            description
              "Maximum number of requests allowed on a http server connection";
            type uint32 {
              range "1..86400";
            }
          }
        }
        // ip http client
        container client {
          description
            "Set http client parameters";
          tailf:cli-incomplete-command;
          leaf secure-trustpoint {
            description
              "Set http client certificate secure trustpoint";
            type string;
          }
          leaf source-interface {
            tailf:cli-full-command;
            tailf:cli-multi-value;
            description
              "Specify interface for source address in all HTTP(S) client connections";
            type string;
          }
        }
        leaf secure-client-auth {
          description
            "Set http secure server with client authentication";
          type empty;
        }
      }
      // ip igmp
      container igmp {
        description
          "IGMP global configuration";
        container snooping-conf {
          tailf:cli-no-keyword;
          tailf:cli-drop-node-name;
          leaf snooping {
            tailf:cli-boolean-no;
            type boolean;
          }
        }
        container snooping {
          description
            "Global IGMP Snooping enable for Catalyst Vlans";
          tailf:cli-display-separated;
          tailf:cli-incomplete-no;
          container check {
            description
              "enforce TTL or Rtr-Alert Option checking";
            leaf rtr-alert-option {
              description
                "Only accept IGMP packets with router-alert option";
              tailf:cli-full-command;
              type empty;
            }
            leaf ttl {
              description
                "Only accept IGMP packets with TTL=1";
              tailf:cli-full-command;
              type empty;
            }
          }
          container explicit-tracking {
            description
              "Explicit tracking DB configuration";
            leaf limit {
              description
                "Explicit tracking DB limit";
              type uint32 {
                range "0..128000";
              }
            }
          }
          leaf l2-entry-limit {
            description
              "limit on the l2 entry that can be installed by IGMP snooping";
            type uint32 {
              range "1..100000";
            }
          }
          leaf last-member-query-count {
            description
              "Last member query count";
            type uint8 {
              range "1..7";
            }
          }
          leaf last-member-query-interval {
            description
              "Interval (milliseconds)";
            type uint16 {
              range "100..32767";
            }
          }
          container querier {
            description
              "IGMP querier configuration";
            presence "true";
            leaf address {
              description
                "IGMP querier source IP address";
              type inet:ipv4-address;
            }
            leaf max-response-time {
              description
                "IGMP querier maximum response time (sec)";
              type uint8 {
                range "1..25";
              }
            }
            leaf query-interval {
              description
                "IGMP querier query interval (sec)";
              type uint16 {
                range "1..18000";
              }
            }
            container tcn {
              description
                "IGMP querier TCN related parameters";
              container query {
                leaf count {
                  description
                    "IGMP querier TCN query count";
                  type uint8 {
                    range "1..10";
                  }
                }
                leaf interval {
                  description
                    "IGMP querier TCN query interval (sec)";
                  type uint8 {
                    range "1..255";
                  }
                }
              }
            }
            container timer {
              description
                "IGMP other querier timer";
              leaf expiry {
                description
                  "IGMP querier other querier time out (sec)";
                type uint16 {
                  range "60..300";
                }
              }
            }
            leaf version {
              description
                "IGMP version";
              type uint8 {
                range "1..2";
              }
            }
          }
          leaf report-suppression {
            description
              "Report suppression";
            type empty;
          }
          leaf robustness-variable {
            description
              "Robustness Variable number";
            type uint8 {
              range "1..3";
            }
          }
          container tcn {
            description
              "Topology change notification configuration";
            container flood {
              description
                "TCN flooding configuration";
              container query {
                description
                  "TCN flooding query configuration";
                leaf count {
                  description
                    "Count";
                  type uint8 {
                    range "1..10";
                  }
                }
              }
            }
            container query {
              description
                "TCN query configuration";
              leaf solicit {
                description
                  "Solicit an IGMP general query";
                type empty;
              }
            }
          }
        }
        container ssm-map {
          description
            "SSM mapping commands";
          leaf enable {
            description
              "Enable SSM group to source mapping";
            tailf:cli-full-command;
            type empty;
          }
          container query {
            description
              "Which database should we query for the source";
            leaf dns {
              description
                "Use DNS for source lookup";
              tailf:cli-full-command;
              tailf:cli-show-no;
              type empty;
            }
          }
          container static {
            description
              "SSM static group to source mapping";
            tailf:cli-sequence-commands;
            tailf:cli-compact-syntax;
            leaf acl {
              tailf:cli-drop-node-name;
              type union {
                type uint16 {
                  range "1..99";
                }
                type string;
              }
            }
            leaf source-ip {
              tailf:cli-drop-node-name;
              type inet:ipv4-address;
            }
          }
        }
      }
// ip multicast
      container multicast {
        description
          "Global IP Multicast Commands";
        leaf multipath {
          description
            "RPF across equal-cost paths";
          type empty;
        }
      }

      // ip nat
      container nat {
        description
          "NAT configuration commands";
        tailf:cli-diff-dependency "/ios:native/ip/vrf";
        tailf:cli-diff-dependency "/ios:native/vrf/definition";
        tailf:cli-diff-dependency "/ios:native/vrf/definition/address-family";
        // ip nat pool *
        list pool {
          description
            "Define pool of addresses";
          tailf:cli-suppress-mode;
          tailf:cli-delete-when-empty;
          tailf:cli-compact-syntax;
          tailf:cli-sequence-commands {
            tailf:cli-reset-siblings;
          }
          key "id";
          leaf id {
            type string;
          }
          leaf start-address {
            tailf:cli-drop-node-name;
            tailf:cli-optional-in-sequence;
            type inet:ipv4-address;
          }
          leaf end-address {
            tailf:cli-drop-node-name;
            when "../start-address" {
               tailf:dependency "../start-address";
            }
            type inet:ipv4-address;
          }
          choice prefix-choice {
            leaf netmask {
              description
                "Specify the network mask";
              type inet:ipv4-address;
            }
            leaf prefix-length {
              description
                "Specify the prefix length";
              type uint8 {
                range "1..32";
              }
            }
          }
          leaf accounting {
            tailf:cli-optional-in-sequence;
            description
              "Specify the accounting";
            type string;
          }
          choice nat-choice {
            leaf arp-ping {
              description
                "WLAN ARP Ping";
              type empty;
            }
            leaf type {
              description
                "Specify the pool type";
              type enumeration {
                enum "match-host";
                enum "rotary";
              }
            }
            leaf add-route {
              description
                "Add special route to Virtual Interface";
              type empty;
            }
          }
        }
        // ip nat inside
        container inside {
          description
            "Inside address translation";
          // ip nat inside source
          container source {
            description
              "Source address translation";
            // ip nat inside source list *
            list list {
              description
                "Specify access list describing local addresses";
              tailf:cli-suppress-mode;
              tailf:cli-delete-when-empty;
              tailf:cli-compact-syntax;
              tailf:cli-sequence-commands {
                tailf:cli-reset-all-siblings;
              }
              tailf:cli-incomplete-command;
              key "id";
              leaf id {
                type union {
                  type uint16 {
                    range "1..2699";
                  }
                  type string;
                }
              }
              choice pool-or-interface {
                // ip nat inside source list * pool
                case pool-choice {
                  leaf pool {
                    description
                      "Name pool of global addresses";
                    type string;
                    tailf:non-strict-leafref {
                      path "/ios:native/ip/nat/pool/id";
                    }
                  }
                  // [ redundancy <rg-id> ]
                  leaf redundancy {
                    description
                      "NAT redundancy operation";
                    tailf:cli-optional-in-sequence;
                    type uint8 {
                      range "1..2";
                    }
                  }
                  // [ mapping-id <map-id> ]
                  leaf mapping-id {
                    description
                      "Associate a mapping id to this mapping";
                    tailf:cli-optional-in-sequence;
                    type uint32 {
                      range "1..2147483647";
                    }
                  }
                }
                // ip nat inside source list * interface
                case interface-choice {
                  container interface {
                    description
                      "Specify interface for global address";
                    tailf:cli-compact-syntax;
                    tailf:cli-flatten-container;
                    uses interface-grouping;
                  }
                }
              }
              // [no-payload]
              leaf no-payload {
                description
                  "No translation of embedded address/port in the payload";
                tailf:cli-optional-in-sequence;
                type empty;
              }
              // [reversible]
              leaf reversible {
                tailf:cli-optional-in-sequence;
                type empty;
              }
              // [ vrf name [match-in-vrf] ]
              leaf vrf {
                description
                  "Specify vrf";
                tailf:cli-optional-in-sequence;
                type string;
              }
              leaf match-in-vrf {
                description
                  "Match incoming vrf";
                tailf:cli-optional-in-sequence;
                when "../vrf";
                type empty;
              }
              // [overload]
              leaf overload {
                description
                  "Overload an address translation";
                tailf:cli-optional-in-sequence;
                type empty;
              }
              // [oer]
              leaf oer {
                description
                  "Use with vtemplate only. On new translation, if OER BR is UP, OER will select IP from outgoing Interface. All packets matching translation are forwarded over Interface for duration of translation.";
                type empty;
              }
              // [ portmap name ]
            }
            // ip nat inside source static
            container static {
              description
                "Specify static local->global mapping";
              list nat-static-transport-list {
                tailf:cli-drop-node-name;
                tailf:cli-suppress-mode;
                tailf:cli-delete-when-empty;
                tailf:cli-compact-syntax;
                tailf:cli-sequence-commands {
                  tailf:cli-reset-siblings;
                }
                key "local-ip global-ip";
                leaf local-ip {
                  tailf:cli-drop-node-name;
                  type inet:ipv4-address;
                }
                leaf global-ip {
                  tailf:cli-drop-node-name;
                  type inet:ipv4-address;
                }
                leaf proto {
                  tailf:cli-drop-node-name;
                  tailf:cli-prefix-key {
                    tailf:cli-before-key "1";
                  }
                  tailf:cli-optional-in-sequence;
                  type enumeration {
                    enum "tcp";
                    enum "udp";
                  }
                }
                leaf network {
                  description
                    "Subnet translation";
                  tailf:cli-prefix-key {
                    tailf:cli-before-key "1";
                  }
                  tailf:cli-optional-in-sequence;
                  type empty;
                }
                leaf local-port {
                  tailf:cli-drop-node-name;
                  tailf:cli-optional-in-sequence;
                  tailf:cli-prefix-key {
                    tailf:cli-before-key "2";
                  }
                  type uint16 {
                    range "1..65535";
                  }
                }
                leaf mask {
                  tailf:cli-drop-node-name;
                  tailf:cli-optional-in-sequence;
                  type union {
                    type string;
                    type inet:ipv4-address;
                  }
                }
                leaf global-port {
                  tailf:cli-drop-node-name;
                  tailf:cli-optional-in-sequence;
                  type uint16 {
                    range "1..65535";
                  }
                }
                leaf extendable {
                  description
                    "Extend this translation when used";
                  tailf:cli-optional-in-sequence;
                  type empty;
                }
                leaf no-alias {
                  description
                    "Do not create an alias for the global address";
                  tailf:cli-optional-in-sequence;
                  type empty;
                }
                leaf no-payload {
                  description
                    "No translation of embedded address/port in the payload";
                  tailf:cli-optional-in-sequence;
                  type empty;
                }
                leaf route-map {
                  description
                    "Specify route-map";
                  tailf:cli-optional-in-sequence;
                  type string;
                }
                leaf reversible {
                  tailf:cli-optional-in-sequence;
                  when "../route-map";
                  type empty;
                }
                leaf redundancy {
                  description
                    "NAT redundancy operation";
                  tailf:cli-optional-in-sequence;
                  type union {
                    type uint8;
                    type string;
                  }
                }
                leaf mapping-id {
                  description
                    "Associate a mapping id to this mapping";
                  tailf:cli-optional-in-sequence;
                  when "../redundancy";
                  type uint32 {
                    range "1..2147483647";
                  }
                }
                leaf vrf {
                  description
                    "Specify vrf";
                  tailf:cli-optional-in-sequence;
                  type string;
                }
                leaf match-in-vrf {
                  description
                    "Match incoming vrf";
                  tailf:cli-optional-in-sequence;
                  when "../vrf";
                  type empty;
                }
                leaf forced {
                  description
                    "Delete this entry and its children, even if in use";
                  tailf:cli-optional-in-sequence;
                  type empty;
                }
                leaf overload {
                  description
                    "Overload an address translation";
                  type empty;
                }
              }
              list nat-static-transport-interface-list {
                tailf:cli-drop-node-name;
                tailf:cli-suppress-mode;
                tailf:cli-delete-when-empty;
                tailf:cli-compact-syntax;
                tailf:cli-sequence-commands {
                  tailf:cli-reset-siblings;
                }
                tailf:cli-incomplete-command;
                key "proto local-ip local-port";
                leaf proto {
                  type enumeration {
                    enum "tcp";
                    enum "udp";
                  }
                }
                leaf local-ip {
                  tailf:cli-drop-node-name;
                  type inet:ipv4-address;
                }
                leaf local-port {
                  tailf:cli-drop-node-name;
                  type uint16 {
                    range "1..65535";
                  }
                }
                container interface {
                  description
                    "Specify interface for global address";
                  tailf:cli-compact-syntax;
                  tailf:cli-flatten-container;
                  uses interface-grouping;
                }
                leaf global-port {
                  tailf:cli-drop-node-name;
                  type uint16 {
                    range "1..65535";
                  }
                }
              }
            }
          }
          // ip nat inside destination
          container destination {
            description
              "Destination address translation";
            // ip nat inside destination list *
            list list {
              description
                "Specify access list describing global addresses";
              tailf:cli-suppress-mode;
              tailf:cli-delete-when-empty;
              tailf:cli-compact-syntax;
              tailf:cli-sequence-commands {
                tailf:cli-reset-siblings;
              }
              tailf:cli-incomplete-command;
              key "id";
              leaf id {
                type union {
                  type uint16 {
                    range "1..2699";
                  }
                  type string;
                }
              }
              // ip nat inside destination list * pool *
              leaf pool {
                description
                  "Name pool of local addresses";
                type string;
                tailf:non-strict-leafref {
                  path "/ios:native/ip/nat/pool/id";
                }
              }
              // [ redundancy redundancy-id ]
              leaf redundancy {
                description
                  "NAT redundancy operation";
                tailf:cli-optional-in-sequence;
                type uint8 {
                  range "1..2";
                }
              }
              leaf mapping-id {
                description
                  "Associate a mapping id to this mapping";
                type uint32 {
                  range "1..2147483647";
                }
              }
            }
          }
        }
        // ip nat outside
        container outside {
          description
            "Outside address translation";
          list list {
            description
              "Specify access list describing global addresses";
            tailf:cli-suppress-mode;
            tailf:cli-delete-when-empty;
            tailf:cli-compact-syntax;
            tailf:cli-sequence-commands {
              tailf:cli-reset-siblings;
            }
            key "id";
            leaf id {
              type union {
                type uint16 {
                  range "1..2699";
                }
                type string;
              }
            }
            leaf pool {
              description
                "Name pool of local addresses";
              type string;
              tailf:non-strict-leafref {
                path "/ios:native/ip/nat/pool/id";
              }
            }
            leaf mapping-id {
              description
                "Associate a mapping id to this mapping";
              tailf:cli-optional-in-sequence;
              type uint32 {
                range "1..2147483647";
              }
            }
            leaf vrf {
              description
                "Specify vrf";
              tailf:cli-optional-in-sequence;
              type string;
            }
            leaf add-route {
              description
                "Add a static route for outside local address";
              type empty;
            }
          }
          list route-map {
            description
              "Specify route-map";
            tailf:cli-suppress-mode;
            tailf:cli-delete-when-empty;
            tailf:cli-compact-syntax;
            tailf:cli-sequence-commands {
              tailf:cli-reset-siblings;
            }
            key "id";
            leaf id {
              type string;
            }
            leaf pool {
              description
                "Name pool of local addresses";
              type string;
              tailf:non-strict-leafref {
                path "/ios:native/ip/nat/pool/id";
              }
            }
            leaf mapping-id {
              description
                "Associate a mapping id to this mapping";
              tailf:cli-optional-in-sequence;
              type uint32 {
                range "1..2147483647";
              }
            }
            leaf vrf {
              description
                "Specify vrf";
              tailf:cli-optional-in-sequence;
              type string;
            }
            leaf add-route {
              description
                "Add a static route for outside local address";
              type empty;
            }
          }
        }
      }


      // ip name-server
      container name-server {
        leaf-list no-vrf {
          tailf:cli-drop-node-name;
          tailf:cli-flat-list-syntax;
          tailf:cli-list-syntax;
          type union {
            type inet:ipv4-address;
            type inet:ipv6-address;
          }
        }
        list vrf {
          tailf:cli-suppress-mode;
          description "";
          key "word";
          leaf word {
            tailf:cli-drop-node-name;
            type string;
          }
          leaf server-ip {
            tailf:cli-drop-node-name;
            type union {
              type inet:ipv4-address;
              type inet:ipv6-address;
            }
          }
        }
      }
      // ip pim
      container pim {
        description
          "PIM global commands";
        tailf:cli-diff-dependency "/ios:native/ip/vrf";
        tailf:cli-diff-dependency "/ios:native/vrf/definition";
        tailf:cli-diff-dependency "/ios:native/vrf/definition/address-family";
        uses ip-pim-grouping;
        // ip pim vrf *
        list vrf {
          description
            "Select VPN Routing/Forwarding instance";
          tailf:cli-suppress-mode;
          tailf:cli-delete-when-empty;
          key "id";
          leaf id {
            type string;
          }
          uses ip-pim-grouping;
        }
      }
      // ip prefix-list
      container prefix-list {
        description
          "Build a prefix list";
        // ip prefix-list *
        list prefixes {
          tailf:cli-drop-node-name;
          tailf:cli-suppress-mode;
          tailf:cli-delete-when-empty;
          tailf:cli-compact-syntax;
          key "name";
          leaf name {
            type string {
              pattern "([^s].*)|(s[^e].*)|(se[^q].*)(seq[^u].*)|(sequ[^e].*)|(seque[^n].*)|(sequen[^c].*)|(sequenc[^e].*)|(sequence[^\\-].*)|(sequence\\-[^n].*)|(sequence\\-n[^u].*)|(sequence\\-nu[^m].*)|(sequence\\-num[^b].*)|(sequence\\-numb[^e].*)|(sequence\\-numbe[^r].*)|(sequence\\-number..*)";
            }
          }
          // ip prefix-list * description
          leaf description {
            description
              "Prefix-list specific description";
            tailf:cli-multi-value;
            tailf:cli-full-command;
            type string {
              length "1..80";
            }
          }
          // ip prefix-list * permit
          container permit {
            description
              "Specify packets to forward";
            list permit-list {
              tailf:cli-drop-node-name;
              key "prefix";
              tailf:cli-sequence-commands {
                tailf:cli-reset-all-siblings;
              }
              tailf:cli-compact-syntax;
              tailf:cli-suppress-mode;
              leaf prefix {
                tailf:cli-drop-node-name;
                type ios:ipv4-prefix;
              }
              leaf ge {
                description
                  "Minimum prefix length to be matched";
                tailf:cli-break-sequence-commands;
                type uint8 {
                  range "1..32";
                }
              }
              leaf le {
                description
                  "Maximum prefix length to be matched";
                tailf:cli-full-command;
                type uint8 {
                  range "1..32";
                }
              }
            }
          }
          // ip prefix-list * deny
          container deny {
            description
              "Specify packets to reject";
            list deny-list {
              key "prefix";
              tailf:cli-sequence-commands {
                tailf:cli-reset-all-siblings;
              }
              tailf:cli-compact-syntax;
              tailf:cli-suppress-mode;
              leaf prefix {
                tailf:cli-drop-node-name;
                type ios:ipv4-prefix;
              }
              leaf ge {
                description
                  "Minimum prefix length to be matched";
                tailf:cli-break-sequence-commands;
                type uint8 {
                  range "1..32";
                }
              }
              leaf le {
                description
                  "Maximum prefix length to be matched";
                tailf:cli-full-command;
                type uint8 {
                  range "1..32";
                }
              }
            }
          }
          // ip prefix-list * seq *
          list seq {
            // NOTE: the seq element is not actually mandatory
            // in the Cisco CLI. If it isn't give
            description
              "sequence number of an entry";
            tailf:cli-suppress-mode;
            tailf:cli-delete-when-empty;
            tailf:cli-compact-syntax;
            key "no";
            leaf no {
              type uint32 {
                range "1..4294967294";
              }
              tailf:key-default "10";
            }
            // ip prefix-list * seq * deny
            container deny {
              description
                "Specify packets to reject";
              tailf:cli-sequence-commands {
                tailf:cli-reset-all-siblings;
              }
              tailf:cli-compact-syntax;
              leaf ip {
                tailf:cli-drop-node-name;
                type ios:ipv4-prefix;
              }
              leaf ge {
                description
                  "Minimum prefix length to be matched";
                tailf:cli-break-sequence-commands;
                type uint8 {
                  range "1..32";
                }
              }
              leaf le {
                description
                  "Maximum prefix length to be matched";
                tailf:cli-full-command;
                type uint8 {
                  range "1..32";
                }
              }
            }
            // ip prefix-list * seq * permit
            container permit {
              description
                "Specify packets to forward";
              tailf:cli-sequence-commands {
                tailf:cli-reset-all-siblings;
              }
              tailf:cli-compact-syntax;
              leaf ip {
                tailf:cli-drop-node-name;
                type ios:ipv4-prefix;
              }
              leaf ge {
                description
                  "Minimum prefix length to be matched";
                tailf:cli-break-sequence-commands;
                type uint8 {
                  range "1..32";
                }
              }
              leaf le {
                description
                  "Maximum prefix length to be matched";
                tailf:cli-full-command;
                type uint8 {
                  range "1..32";
                }
              }
            }
          }
        }
        // ip prefix-list sequence-number
        leaf sequence-number {
          description
            "Include/exclude sequence numbers in NVGEN";
          tailf:cli-full-command;
          type empty;
        }
      }
      // ip route
      container route {
        description
          "Establish static routes";
        uses ip-route-grouping;
        // ip route profile
        leaf profile {
          description
            "Enable IP routing table profile";
          tailf:cli-full-command;
          type empty;
        }
        // ip route static
        container static {
          description
            "Allow static routes";
          leaf adjust-time {
            description
              "Time period for adjusting static routes";
            tailf:cli-full-command;
            type uint8 {
              range "1..60";
            }
          }
          container bfd {
            description
              "BFD tracked";
            tailf:cli-compact-syntax;
            tailf:cli-sequence-commands;
            leaf interface {
              tailf:cli-drop-node-name;
              type string;
            }
            leaf gateway-ip {
              tailf:cli-drop-node-name;
              type inet:ipv4-address;
            }
          }
          leaf inter-vrf {
            description
              "Across VRF interfaces";
            tailf:cli-full-command;
            type empty;
          }
        }
        // ip route vrf *
        list vrf {
          description
            "Configure static route for a VPN Routing/Forwarding instance";
          tailf:cli-suppress-mode;
          tailf:cli-delete-when-empty;
          tailf:cli-compact-syntax;
          tailf:cli-reset-container;
          tailf:cli-incomplete-command;
          tailf:cli-diff-dependency "/ios:native/ip/vrf";
          tailf:cli-diff-dependency "/ios:native/vrf/definition";
          tailf:cli-diff-dependency "/ios:native/vrf/definition/address-family";
          key "name";
          leaf name {
            type string;
          }
          uses ip-route-grouping;
        }
      }
      // ip routing
      leaf routing {
        description
          "Enable IP routing";
        tailf:cli-full-command;
        type empty;
      }
      // ip explicit-path name *
      list explicit-path {
        description
          "Configure explicit-path";
        tailf:cli-mode-name "cfg-ip-expl-path";
        key "name";
        leaf name {
          description
            "Specify explicit path by name";
          tailf:cli-expose-key-name;
          type string;
        }
        leaf mode {
          tailf:cli-drop-node-name;
          tailf:cli-hide-in-submode;
          type enumeration {
            enum "enable";
            enum "disable";
          }
        }
        // ip explicit-path name * / next-address-label
        leaf-list next-address {
          description
            "Specify the next address in the path";
          tailf:cli-list-syntax;
          ordered-by user;
          type inet:ipv4-address;
        }
        // ip explicit-path name * / next-label
        leaf-list next-label {
          description
            "Exclude an address from subsequent partial path segments";
          tailf:cli-list-syntax;
          ordered-by user;
          type uint32 {
            range "0..1048575";
          }
        }
        // ip explicit-path name * / exclude-address
        leaf-list exclude-address {
          tailf:cli-list-syntax;
          description
            "Exclude an address from subsequent partial path segments";
          ordered-by user;
          type inet:ipv4-address;
        }
      }
      // ip rsvp signalling hello
      container rsvp {
        description
          "IP RSVP";
        leaf signalling {
          description
            "IP RSVP signalling";
          type string;
        }
      }
      // ip scp
      container scp {
        description
          "Scp commands";
        container server {
          description
            "Configure SCP server-side functionality";
          leaf enable {
            description
              "Enable server side of SCP";
            type empty;
          }
        }
      }

      // ip sla
      container sla {
        description
          "IP Service Level Agreement";
        list entry {
          tailf:cli-drop-node-name;
          tailf:cli-mode-name "config-ip-sla";
          key "number";
          leaf number {
            type uint32;
          }
          container icmp-echo {
            description
              "ICMP Echo Operation";
            tailf:cli-add-mode;
            tailf:cli-mode-name "config-ip-sla-echo";
            leaf destination {
              tailf:cli-drop-node-name;
              tailf:cli-hide-in-submode;
              type union {
                type string;
                type inet:ipv4-address;
              }
            }
            leaf source-interface {
              description
                "Source Interface (ingress icmp packet interface)";
              tailf:cli-hide-in-submode;
              tailf:cli-full-command;
              type string;
            }
            leaf source-ip {
              description
                "Source Address";
              tailf:cli-hide-in-submode;
              tailf:cli-full-command;
              type union {
                type string;
                type inet:ipv4-address;
              }
            }
            leaf data-pattern {
              description
                "Data Pattern";
              tailf:cli-full-command;
              type string;
            }
            leaf frequency {
              description
                "Frequency of an operation";
              tailf:cli-full-command;
              type uint32 {
                range "1..604800";
              }
            }
            container history {
              description
                "History and Distribution Data";
              leaf buckets-kept {
                description
                  "Maximum number of history buckets to collect";
                tailf:cli-full-command;
                type uint8;
              }
              leaf distributions-of-statistics-kept {
                description
                  "Maximum number of statistics distribution buckets to capture";
                tailf:cli-full-command;
                type uint8;
              }
              container enhanced {
                description
                  "Enable enhanced history collection";
                tailf:cli-compact-syntax;
                tailf:cli-sequence-commands;
                leaf interval {
                  description
                    "Aggregation interval";
                  type uint32 {
                    range "1..3600";
                  }
                }
                leaf buckets {
                  description
                    "Number of buckets to collect data";
                  type uint8 {
                    range "1..100";
                  }
                }
              }
              leaf filter {
                description
                  "Add operation to History when...";
                tailf:cli-full-command;
                type enumeration {
                  enum "all";
                  enum "failures";
                  enum "none";
                  enum "overThreshold";
                }
              }
              leaf hours-of-statistics-kept {
                description
                  "Maximum number of statistics hour groups to capture";
                tailf:cli-full-command;
                type uint8 {
                  range "0..25";
                }
              }
              leaf lives-kept {
                description
                  "Maximum number of history lives to collect";
                tailf:cli-full-command;
                type uint8 {
                  range "0..2";
                }
              }
              leaf statistics-distribution-interval {
                description
                  "Statistics distribution interval size";
                tailf:cli-full-command;
                type uint8 {
                  range "1..100";
                }
              }
            }
            leaf owner {
              description
                "Owner of Entry";
              tailf:cli-multi-value;
              type string;
            }
            leaf request-data-size {
              description
                "Request data size";
              tailf:cli-full-command;
              type uint32 {
                range "0..16384";
              }
            }
            leaf tag {
              description
                "User defined tag";
              tailf:cli-multi-value;
              type string;
            }
            leaf threshold {
              description
                "Operation threshold in milliseconds";
              tailf:cli-full-command;
              type uint32 {
                range "0..60000";
              }
            }
            leaf timeout {
              description
                "Timeout of an operation";
              tailf:cli-full-command;
              type uint64 {
                range "0..604800000";
              }
            }
            leaf tos {
              description
                "Type Of Service";
              tailf:cli-full-command;
              type uint8;
            }
            leaf verify-data {
              description
                "Verify data";
              tailf:cli-full-command;
              type empty;
            }
            leaf vrf {
              description
                "Configure IP SLAs for a VPN Routing/Forwarding instance";
              tailf:cli-full-command;
              type string;
            }
          }
          container path-jitter {
            description
              "Path Discovered ICMP Jitter Operation";
            tailf:cli-add-mode;
            tailf:cli-mode-name "config-ip-sla-path-jitter";
            leaf dst-ip {
              tailf:cli-drop-node-name;
              tailf:cli-hide-in-submode;
              type union {
                type string;
                type inet:ipv4-address;
                type inet:ipv6-address;
              }
            }
            leaf source-ip {
              description
                "Source IP Address";
              tailf:cli-hide-in-submode;
              type union {
                type string;
                type inet:ipv4-address;
              }
            }
            container default {
              description
                "Set a command to its defaults";
              uses ip-sla-default-path-jitter-grouping;
            }
            uses ip-sla-path-jitter-grouping;
          }
        }
        // ip sla enable
        container enable {
          leaf reaction-alerts {
            type empty;
          }
        }
         // ip sla responder
        container responder {
          description "Enable IP SLAs Responder";
          presence true;
          container udp-echo {
            description "Setup udp-echo responder";
            leaf port {
              description "Permanent port";
              type uint16 {
                range "1..65535";
              }
            }
            list ipaddress {
              tailf:cli-suppress-mode;
              description "Permanent address";
              key "host";
              leaf host {
                tailf:cli-drop-node-name;
                type union {
                  type inet:ipv4-address;
                  type inet:ipv6-address;
                }
              }
              leaf port {
                description "Permanent port";
                type uint16 {
                  range "1..65535";
                }
              }
            }
          }
          container tcp-connect {
            description "Setup tcp-connect responder";
            leaf port {
              description "Permanent port";
              type uint16 {
                range "1..65535";
              }
            }
            list ipaddress {
              tailf:cli-suppress-mode;
              description "Permanent address";
              key "host";
              leaf host {
                tailf:cli-drop-node-name;
                type union {
                  type inet:ipv4-address;
                  type inet:ipv6-address;
                }
              }
              leaf port {
                description "Permanent port";
                type uint16 {
                  range "1..65535";
                }
              }
            }
          }
        }
        // ip sla logging
        container logging {
          description "low-memory";
          leaf traps {
            description "Enable syslog traps";
            type empty;
          }
        }
        // ip sla group
        container group {
          description "Group Configuration or Group Scheduling";
          list schedule {
            description "Group scheduling";
            tailf:cli-suppress-mode;
            key "entry-number";
            leaf entry-number {
              description "Group schedule entry number";
              tailf:cli-drop-node-name;
              type uint32 {
                range "1..2147483647";
              }
            }
            list probe-ids {
              tailf:cli-drop-node-name;
              tailf:cli-suppress-mode;
              key "word";
              leaf word {
                tailf:cli-drop-node-name;
                type string;
              }
              list schedule-period {
                tailf:cli-suppress-mode;
                description "Group schedule period range";
                key "seconds";
                leaf seconds {
                  description "seconds";
                  tailf:cli-drop-node-name;
                  type uint32;
                }
                container start-time {
                  description "When to start this entry";
                  leaf pending {
                    description "Start pending";
                    type empty;
                  }
                }
              }
            }
          }
        }
        // ip sla schedule
        list schedule {
          description
            "Entry Scheduling";
          tailf:cli-suppress-mode;
          tailf:cli-compact-syntax;
          key "entry-number";
          leaf entry-number {
            type uint32;
          }
          leaf ageout {
            description
              "How long to keep this Entry when inactive";
            tailf:cli-hide-in-submode;
            type uint32 {
              range "0..2073600";
            }
          }
          leaf life {
            description
              "Length of time to execute in seconds";
            tailf:cli-hide-in-submode;
            type union {
              type uint32;
              type enumeration {
                enum "forever";
              }
            }
          }
          leaf recurring {
            description
              "Probe to be scheduled automatically every day";
            tailf:cli-hide-in-submode;
            type empty;
          }
          container start-time {
            description
              "When to start this entry";
            tailf:cli-hide-in-submode;
            tailf:cli-flatten-container;
            leaf after {
              description
                "Start after a certain amount of time from now";
              tailf:cli-full-command;
              type string;
            }
            leaf hour-min {
              tailf:cli-drop-node-name;
              tailf:cli-full-command;
              type string;
            }
            leaf hour-min-sec {
              tailf:cli-drop-node-name;
              tailf:cli-full-command;
              type string;
            }
            leaf now {
              description
                "Start now";
              tailf:cli-full-command;
              type empty;
            }
            leaf pending {
              description
                "Start pending";
              tailf:cli-full-command;
              type empty;
            }
            leaf random {
              description
                "Start after random time (range)";
              tailf:cli-full-command;
              type uint32 {
                range "500..10000";
              }
            }
          }
        }
      }
      //ip spd
      container spd {
        description
          "spd";
        leaf mode {
          type enumeration {
            enum "aggressive";
          }
        }
      }


      // ip bootp
      container bootp {
        description
          "Config BOOTP services";
        leaf server {
          description
            "Enable BOOTP server";
          tailf:cli-boolean-no;
          tailf:cli-trim-default;
          type boolean;
        }
      }
      // ip source-route
      leaf source-route {
        description
          "Process packets with source routing header options";
        tailf:cli-boolean-no;
        tailf:cli-show-with-default;
        tailf:cli-full-command;
        type boolean;
      }
      // ip ssh
      container ssh {
        description
          "Configure ssh options";
        leaf authentication-retries {
          description
            "Specify number of authentication retries";
          type uint8 {
            range "0..5";
          }
        }
        leaf dscp {
          description
            "IP DSCP value for SSH traffic";
          type uint8 {
            range "0..63";
          }
        }
        container logging {
          description
            "Configure logging for SSH";
          leaf events {
            description
              "Log SSH events";
            type empty;
          }
        }
        container pubkey-chain {
          description
            "Configure public key-chain parameters";
          tailf:cli-add-mode;
          tailf:cli-mode-name "conf-ssh-pubkey";
          tailf:cli-full-command;
          list username {
            tailf:cli-mode-name "conf-ssh-pubkey-user";
            tailf:cli-full-command;
            tailf:cli-no-key-completion;
            tailf:cli-no-match-completion;
            max-elements "10";
            key "name";
            leaf name {
              type string;
            }
            list key-hash {
              max-elements "2";
              tailf:cli-suppress-mode;
              key "key-type key-hash-value";
              leaf key-type {
                type enumeration {
                  enum "ssh-rsa";
                }
              }
              leaf key-hash-value {
                tailf:cli-multi-value;
                type string;
              }
            }
          }
        }
        leaf precedence {
          description
            "IP Precedence value for SSH traffic";
          type uint8 {
            range "0..7";
          }
        }
        container rsa {
          description
            "Configure RSA keypair name for SSH";
          leaf keypair-name {
            description
              "keypair-name";
            type string;
          }
        }
        //  source-interface Specify interface for source address in
        // ip ssh source-interface
        leaf source-interface {
          description
            "Specify interface for source address in SSH connections";
          type string;
        }
        //  SSH connections
        leaf time-out {
          description
            "Specify SSH time-out interval";
          type uint8 {
            range "1..120";
          }
        }
        leaf version {
          description
            "Specify protocol version supported";
          type uint8 {
            range "1..2";
          }
        }
        list port {
          description
            "Starting (or only) Port number to listen on";
          tailf:cli-compact-syntax;
          tailf:cli-suppress-mode;
          key port-no;
          leaf port-no {
            description
              "Starting Port number";
            type uint16{
              range "2000..10000";
            }
          }
          leaf low-rotary {
            description
              "Starting (or only) rotary group number";
            tailf:alt-name "rotary";
            type uint8 {
              range "1..127";
            }
          }
          leaf high-rotary {
            description
              "Starting (or only) rotary group number";
            tailf:cli-drop-node-name;
            type uint8 {
              range "1..127";
            }
          }          
        }
      }
      // ip tacacs
      container tacacs {
        description
          "TACACS configuration commands";
        container source-interface {
          description
            "Specify interface for source address in TACACS packets";
          tailf:cli-diff-dependency "/ios:native/interface";
          uses interface-grouping;
        }
      }
      // ip tcp
      container tcp {
        description
          "Global TCP parameters";
        container path-mtu-discovery {
          description
            "Enable path-MTU discovery on new TCP connections";
          presence "true";
          leaf age-timer {
            description
              "Set PMTU aging timer";
            type union {
              type enumeration {
                enum "infinite";
              }
              type uint8 {
                range "10..30";
              }
            }
          }
        }
      }
      // ip tftp
      container tftp {
        description
          "tftp configuration commands";
        container boot-interface {
          description
            "Force interface to use for TFTP booting";
          tailf:cli-diff-dependency "/ios:native/interface";
          uses interface-grouping;
        }
        container source-interface {
          description
            "Specify interface for source address in TFTP connections";
          tailf:cli-diff-dependency "/ios:native/interface";
          uses interface-grouping;
        }
        leaf blocksize {
          description
            "Specify TFTP client blocksize";
          type uint16 {
            range "512..8192";
          }
        }
      }
      // ip access-list
      container access-list {
        description
          "Named access list";
        tailf:cli-incomplete-command;
        tailf:cli-compact-syntax;
        // ip access-list standard *
        list standard {
          description
            "Standard Access List";
          tailf:cli-full-command;
          tailf:cli-no-key-completion;
          tailf:cli-mode-name "config-std-nacl";
          key "name";
          leaf name {
            type std-acl-type;
          }
          uses ipv4-std-acl-grouping;
          container default {
            description
              "Set a command to its defaults";
            uses ipv4-std-acl-grouping;
          }
        }
        // ipv4 access-list role-based 
        list role-based {
          description
            "Role-based Access List";
          tailf:cli-no-key-completion;
          tailf:cli-mode-name "config-rb-acl";
          key "name";
          leaf name {
            type string;
          }
          uses ipv4-role-acl-grouping;
          container default {
            description
              "Set a command to its defaults";
            uses ipv4-role-acl-grouping;
          }
        }
        //  ip access-list extended *
        list extended {
          description
            "Extended Access List";
          tailf:cli-full-command;
          tailf:cli-mode-name "config-ext-nacl";
          key "name";
          leaf name {
            type ext-acl-type;
          }
          uses ipv4-ext-acl-grouping;
          container default {
            description
              "Set a command to its defaults";
            uses ipv4-ext-acl-grouping;
          }          
        }
        // ip access-list helper
        container helper {
          description
            "Access List acts on helper-address";
          tailf:cli-sequence-commands;
          tailf:cli-compact-syntax;
          leaf egress {
            description
              "Outbound";
            type empty;
          }
          leaf check {
            description
              "Enable filtering on helper-address destined";
            tailf:cli-full-command;
            type empty;
          }
        }
        //ip access-list log-update
        container log-update {
          description
            "Control access list log updates";
          leaf threshold {
            description
              "Set access-list logging threshold";
            type uint64 {
              range "0..2147483647";
            }
          }
        }
        //ip access-list logging
        container logging {
          description
            "Control access list logging";
          leaf hash-generation {
            description
              "Enable syslog hash code generation";
            tailf:cli-full-command;
            type empty;
          }
          leaf interval {
            description
              "Set access list logging interval";
            type uint64 {
              range "0..2147483647";
            }
          }
        }
        //ip access-list match-local-traffic 
        leaf match-local-traffic {
          description
            "Enable ACL matching for locally generated traffic";
          type empty;
        }
        //ip access-list persistent
        leaf persistent {
          description
            "enable persistency across reload";
          type empty;
        }
        //ip access-list resequence
        container resequence {
          description
            "Resequence Access List";
          tailf:cli-sequence-commands;
          tailf:cli-compact-syntax;
          leaf numbers {
            tailf:cli-drop-node-name;
            type union {
              type std-acl-type;
              type ext-acl-type;
            }
          }
          leaf start-seq-no {
            tailf:cli-drop-node-name;
            type uint64 {
              range "1..2147483647";
            }
          }
          leaf step-seq-no {
            tailf:cli-drop-node-name;
            type uint64 {
              range "1..2147483647";
            }
          }
        }
      }
      //ip device 
      container device {
        description
          "Device tracking";
        container tracking {
          description
            "Device tracking";
          presence "true";
          container probe {
            description
              "Probe";
            container auto-source {
              description
                "Probe source selection algorithm";
              tailf:cli-compact-syntax;
              presence "true";
              container fallback {
                description
                  "Specify IP and MASK to use as last resort";
                tailf:cli-sequence-commands;
                tailf:cli-compact-syntax;
                tailf:cli-flatten-container;
                leaf src-ip {
                  tailf:cli-drop-node-name;
                  description
                    "IP and MASK of fallback source";
                  type inet:ipv4-address;
                }
                leaf mask {
                  tailf:cli-drop-node-name;
                  description
                    "IP prefix mask";
                  type inet:ipv4-address;
                }
              }
              leaf override {
                description
                  "Do not select source address from device track table";
                tailf:cli-full-command;
                type empty;
              }
            }
            leaf count {
              description
                "Probe count";
              tailf:cli-full-command;
              type uint8;
            }
            leaf delay {
              description
                "Probe delay";
              tailf:cli-full-command;
              type uint8 {
                range "1..120";
              }
            }
            leaf interval {
              description
                "Probe interval";
              tailf:cli-full-command;
              type uint32 {
                range "30..1814400";
              }
            }
          }
          leaf trace-buffer {
            description
              "Enable Tracing Support";
            tailf:cli-full-command;
            type empty;
          }
        }
      }
      //ip nbar
      container nbar {
        description
          "NBAR - Network Based Application Recognition";
        container attribute {
          description
            "Attribute for which custom group value can be created";
          container application-group {
            description
              "Application-group attribute";
            uses ip-nbar-attribute-custom-grouping;
          }
          container category {
            description
              "Category attribute";
            uses ip-nbar-attribute-custom-grouping;
          }
          container sub-category {
            description
              "Sub-category attribute";
            uses ip-nbar-attribute-custom-grouping;
          }
        }
        list attribute-map {
          description
            "Attribute Map";
          tailf:cli-mode-name "config-attribute-map";
          key "name";
          leaf name {
            type string;
          }
          container attribute {
            description
              "Attribute Name";
            leaf application-group {
              description
                "Application-group attribute";
              tailf:cli-full-command;
              type union {
                type string;
                type enumeration {
                  enum "aol-group";
                  enum "apple-group";
                  enum "apple-talk-group";
                  enum "banyan-group";
                  enum "bittorrent-group";
                  enum "capwap-group";
                  enum "cisco-jabber-group";
                  enum "cisco-phone-group";
                  enum "corba-group";
                  enum "dameware-group";
                  enum "edonkey-emule-group";
                  enum "espn-group";
                  enum "fasttrack-group";
                  enum "flash-group";
                  enum "fring-group";
                  enum "ftp-group";
                  enum "gnutella-group";
                  enum "google-group";
                  enum "gtalk-group";
                  enum "icq-group";
                  enum "imap-group";
                  enum "ipsec-group";
                  enum "irc-group";
                  enum "kakao-group";
                  enum "kerberos-group";
                  enum "ldap-group";
                  enum "ms-cloud-group";
                  enum "ms-crm-group";
                  enum "ms-lync-group";
                  enum "msn-messenger-group";
                  enum "netbios-group";
                  enum "nntp-group";
                  enum "npmp-group";
                  enum "other";
                  enum "pop3-group";
                  enum "prm-group";
                  enum "qq-group";
                  enum "skype-group";
                  enum "smtp-group";
                  enum "snmp-group";
                  enum "sqlsvr-group";
                  enum "stun-group";
                  enum "telepresence-group";
                  enum "tftp-group";
                  enum "vmware-group";
                  enum "vnc-group";
                  enum "wap-group";
                  enum "webex-group";
                  enum "xns-xerox-group";
                  enum "xunlei-group";
                  enum "yahoo-group";
                  enum "yahoo-messenger-group";
                }
              }
            }
            leaf business-relevance {
              description
                "Application business-relevance";
              tailf:cli-full-command;
              type enumeration {
                enum "business-irrelevant";
                enum "business-relevant";
                enum "default";
              }
            }
            leaf category {
              description
                "Category attribute";
              tailf:cli-full-command;
              type union {
                type string;
                type enumeration {
                  enum "anonymizers";
                  enum "backup-and-storage";
                  enum "browsing";
                  enum "business-and-productivity-tools";
                  enum "consumer-file-sharing";
                  enum "consumer-internet";
                  enum "consumer-messaging";
                  enum "consumer-streaming";
                  enum "database";
                  enum "email";
                  enum "epayement";
                  enum "file-sharing";
                  enum "gaming";
                  enum "industrial-protocols";
                  enum "instant-messaging";
                  enum "inter-process-rpc";
                  enum "internet-security";
                  enum "layer3-over-ip";
                  enum "location-based-services";
                  enum "net-admin";
                  enum "newsgroup";
                  enum "other";
                  enum "social-networking";
                  enum "software-updates";
                  enum "trojan";
                  enum "voice-and-video";
                }
              }
            }
            leaf encrypted {
              description
                "Encrypted applications";
              tailf:cli-full-command;
              type enumeration {
                enum "encrypted-no";
                enum "encrypted-unassigned";
                enum "encrypted-yes";
              }
            }
            leaf sub-category {
              description
                "Sub-category attribute";
              tailf:cli-full-command;
              type union {
                type string;
                type enumeration {
                  enum "authentication-services";
                  enum "backup-systems";
                  enum "consumer-audio-streaming";
                  enum "consumer-cloud-storage";
                  enum "consumer-multimedia-messaging";
                  enum "consumer-video-streaming";
                  enum "consumer-web-browsing";
                  enum "control-and-signaling";
                  enum "desktop-virtualization";
                  enum "enterprise-cloud-data-storage";
                  enum "enterprise-cloud-services";
                  enum "enterprise-data-center-storage";
                  enum "enterprise-media-conferencing";
                  enum "enterprise-realtime-apps";
                  enum "enterprise-rich-media-content";
                  enum "enterprise-sw-deployment-tools";
                  enum "enterprise-transactional-apps";
                  enum "enterprise-video-broadcast";
                  enum "enterprise-voice-collaboration";
                  enum "file-transfer";
                  enum "naming-services";
                  enum "network-management";
                  enum "os-updates";
                  enum "other";
                  enum "p2p-file-transfer";
                  enum "p2p-networking";
                  enum "remote-access-terminal";
                  enum "routing-protocol";
                  enum "tunneling-protocols";
                }
              }
            }
            leaf traffic-class {
              description
                "SRND class";
              tailf:cli-full-command;
              type enumeration {
                enum "broadcast-video";
                enum "bulk-data";
                enum "multimedia-conferencing";
                enum "multimedia-streaming";
                enum "network-control";
                enum "ops-admin-mgmt";
                enum "real-time-interactive";
                enum "signaling";
                enum "transactional-data";
                enum "voip-telephony";
              }
            }
            leaf tunnel {
              description
                "Tunnelled applications";
              tailf:cli-full-command;
              type enumeration {
                enum "tunnel-no";
                enum "tunnel-unassigned";
                enum "tunnel-yes";
              }
            }
          }
        }
        list attribute-set {
          description
            "Set attribute Map";
          tailf:cli-suppress-mode;
          key "protocol-name";
          leaf protocol-name {
            type string;
              //3com-amp3                      3Com AMP3
              //3com-tsmux                     3Com TSMUX
              //... ...
              //zserv                          Zebra server
              //zulily                         Zulily - 
              //Online shopping aimed for Moms apparel and home decor items.
          }
          leaf profile-name {
            tailf:cli-drop-node-name;
            tailf:cli-hide-in-submode;
            type string;
          }
        }
        list custom {
          description
            "Custom PDL (protocol description language) Module";
          tailf:cli-suppress-mode;
          key "name";
          leaf name {
            type string;
          }
          container http {
            description
              "Custom protocols based on http parameters";
            tailf:cli-hide-in-submode;
            tailf:cli-flatten-container;
            leaf cookie {
              description
                "HTTP Cookie";
              type string;
            }
            leaf host {
              description
                "Host name of Origin Server containing resource";
              type string;
            }
            leaf method {
              description
                "HTTP method";
              type string;
            }
            leaf referer {
              description
                "Address the resource request was obtained from";
              type string;
            }
            choice http-uv {
              case url-case {
                leaf url {
                  description
                    "Uniform Resource Locator path";
                  type string;
                }
              }
              case user-agent-case {
                leaf user-agent {
                  description
                    "Software used by agent sending the request";
                  type string;
                }
              }
              case version-case {
                leaf version {
                  description
                    "HTTP version";
                  type string;
                }
              }
              case via-case {
                leaf via {
                  description
                    "HTTP via field";
                  type string;
                }
              }
            }
            leaf id {
              description
                "Selector ID";
              tailf:cli-full-command;
              type uint16;
            }
          }
        }
      }
      //ip wccp
      container wccp {
        description
          "Web-Cache Coordination Protocol IPv4 Commands";
        uses ip-wccp-grouping;
        container check {
          description
            "Enable a WCCP check";
          container acl {
            description
              "Enable acl check";
            leaf outbound {
              description
                "Enable acl check on original outbound interface";
              type empty;
            }
          }
          container services {
            description
              "Enable services check";
            leaf all {
              description
                "Enable all services check for redirection";
              type empty;
            }
          }
        }
        list vrf {
          description
            "Configure WCCP for a VRF";
          tailf:cli-suppress-mode;
          tailf:cli-compact-syntax;
          key "name";
          leaf name {
            type string;
          }
          uses ip-wccp-grouping;
        }
      }
    }
    
    ///================================================================
    /// password
    ///=================================================================
    container password {
      description "Configure encryption password (key)";
      container encryption {
        description "Encrypt system passwords";
        leaf aes {
          description "Enable stronger (AES) password encryption";
          type empty;
        }
      }
    }
    ///=============================================================
    /// eap
    ///=============================================================
    container eap {
      description "Configure EAP authenticator parameters";
      list profile {
        description "EAP authenticator profile configuration";
        key "name";
        leaf name {
          description "WORD;;EAP authenticator profile name";
          type string; 
        }
        container method {
          description "Add an allowed method";
          leaf fast {
            description 
              "EAP-FAST method allowed";
            type empty;
          }
          leaf gtc {
            description
              "EAP-GTC method allowed";
            type empty;
          }
          leaf leap {
            description
              "EAP-LEAP method allowed";
            type empty;
          }
          leaf mschapv2 {
            description
              "EAP-MSCHAPV2 method allowed";
            type empty;
          }
          leaf peap {
            description
              "EAP-PEAP method allowed";
            type empty;
          }
          leaf md5 {
            description "EAP-MD5 method allowed";
            type empty;
          }	  
          leaf tls {
            description "EAP-TLS method allowed";
            type empty;
          }
        }
        leaf pki-trustpoint {
          description "Set the default pki trustpoint";
          type string;
        }
      }
    }
    ///==================================================================
    /// vstack
    ///==============================================================
    container vstack {
      description "Configure vstack parameters and enable or disable SmartInstall";
      leaf director {
        description "Configure director's IP address";
        type inet:ipv4-address;             
      }
    }
    ///====================================================================
    /// mka 
    ///====================================================================
    container mka {
      description "MACsec Key Agreement (MKA) configuration";
      list policy {
        description "Configure MKA Policy";
        key "name";
        leaf name {
          description "MKA Policy NAME";
          type string;    
        }
        container macsec-cipher-suite {
          description "Cipher Suite for SAK derivation";
          leaf gcm-aes-128 {
            description 
              "GCM-AES-128 Cipher Suite";
            type empty;  
          }
          leaf gcm-aes-256 {
            description 
              "GCM-AES-256 Cipher Suite";
            type empty;       
          }
        }
      }
    }
    ///==============================
    /// device
    ///========================
    container device {
      description "device classifier configuration";
      leaf classifier {
        description "Enable/Disable classification of attached devices";
        type empty;
      }
    }
        
    /// ========================================================================
    /// macro
    /// ========================================================================
    container macro {
      description
        "Macro configuration";
      container global {
        description
          "Enter global macro configuration";
        leaf description {
          description
            "Macro description of this device";
          tailf:cli-multi-value;
          type string;
        }
      }
      container auto {
        description "Macro autoexecution settings";
        list execute {
          description "Map event trigger to macro";
          tailf:cli-compact-syntax;
          tailf:cli-suppress-mode;
          key trigger-event;
          leaf trigger-event{
            tailf:cli-drop-node-name;
            type string;
          }
          container builtin{
            description "Display builtin shell functions";
            tailf:cli-compact-syntax;
            leaf smart-port-configuration{
              tailf:cli-drop-node-name;
              type enumeration {
                enum "CISCO_AP_AUTO_SMARTPORT";
                enum "CISCO_DMP_AUTO_SMARTPORT";
                enum "CISCO_DMP_AUTO_SMARTPORT_V1";
                enum "CISCO_IP_CAMERA_AUTO_SMARTPORT";
                enum "CISCO_LAST_RESORT_SMARTPORT";
                enum "CISCO_LIGHT_AUTO_SMARTPORT";
                enum "CISCO_LWAP_AUTO_SMARTPORT";
                enum "CISCO_PHONE_AUTO_SMARTPORT";
                enum "CISCO_PHONE_AUTO_SMARTPORT_V1";
                enum "CISCO_ROUTER_AUTO_SMARTPORT";
                enum "CISCO_SWITCH_AUTO_SMARTPORT";
                enum "MS_IP_CAMERA_AUTO_SMARTPORT";
                enum "MS_VIDEO_CONF_AUTO_SMARTPORT";
              }
            }
            leaf parameters{
              tailf:cli-drop-node-name;
              tailf:cli-multi-value;
              type string;
            }
          }
        }
        container global{
          description "Macro auto execution configuration";
          leaf processing {
            description "Enable auto smartports, all ports enabled by default";
            type empty;
          }
        }
      }
    }

    /// ========================================================================
    /// vmps
    /// ========================================================================    
    container vmps {
      description
        "VMPS settings";
      leaf reconfirm {
        description
          "Set VMPS reconfirm interval";
        type uint8 {
          range "0..120";
        }
      }
      leaf retry {
        description
          "Set VMPS retry count";
        type uint8 {
          range "1..10";
        }
      }
      list server {
        description
          "Configure server IP address";
        tailf:cli-suppress-mode;
        tailf:cli-delete-when-empty;
        tailf:cli-compact-syntax;
        key "name";
        leaf name {
          type host-type;
        }
        leaf primary {
          description
            "Specify primary server";
          type empty;
        }
      }
    }

    /// ========================================================================
    /// ipv6
    /// ========================================================================
    container ipv6 {
      description
        "Global IPv6 configuration commands";
      container source-guard {
        description "Configure IPv6 sourceguard";
        list policy {
          description "Configure a policy for feature sourceguard";
          tailf:cli-mode-name "config-sisf-sourceguard";
          key "source-guard-policy-name";
          leaf source-guard-policy-name{
            type string;
          }
          container validate {
            description "Validate the src of the received data traffic";
            leaf address {
              description "Validate against addresses learned in NDP/DHCP traffic (default)";
              type empty;
            }
            leaf prefix {
              description "Validate against prefixes learned in RA or DHCP-PD traffic";
              type empty;
            }
          }          
        }
      }
      container destination-guard {
        description "Configure Destination guard";
        list policy {
          description "Configure a policy for feature destguard";
          tailf:cli-mode-name "config-destguard";          
          key "destination-guard-policy-name" ;
          leaf destination-guard-policy-name{
            type string;
          }
          container enforcement {
            description "Sets the enforcement level";
            leaf always {
              description "Enforced under all conditions (default)";
              type empty;
            }
            leaf stressed {
              description "Enforced when system is under stress";
              type empty;
            }
          }
        }
      }
      container dhcp {
        description "Configure IPv6 DHCP";
        container guard {
          description "Configure IPv6 DHCP guard";
          list policy {
            description "Configure a policy for feature dhcp guard";
              tailf:cli-mode-name "config-dhcp-guard";
            key "dhcp-guard-policy-name" ;
            leaf dhcp-guard-policy-name{
              type string;
            }
            container device-role {
              description "Sets the role of the device attached to the port";
              leaf server {
                description "Attached device is a dhcp server";
                type empty;
              }
              leaf client {
                description "Attached device is a client (default)";
                type empty;
              }            
            }
          }
        }
        list pool {
          description
            "Configure IPv6 DHCP pool";
          key name-dhcp-gaurd-policy;
          leaf name-dhcp-gaurd-policy{
            type string;
          }
          container address {
            description
              "IPv6 address allocation";
            list prefix {
              description
                "IPv6 address allocation prefix";
              tailf:cli-compact-syntax;
              tailf:cli-suppress-mode;
              key ipv6-address;
              leaf ipv6-address {
                type ipv6-prefix;
              }
              container lifetime {
                description
                  "Configure prefix lifetimes";
                tailf:cli-compact-syntax;
                tailf:cli-sequence-commands;
                leaf valid-lifetime {
                  tailf:cli-drop-node-name;
                  type union {
                    type uint32 {
                      range "0 .. 4294967295";
                    }
                    type enumeration {
                      enum "infinite";
                    }
                  }
                }
                leaf preferred-lifetime {
                  tailf:cli-drop-node-name;
                  type union {
                    type uint32 {
                      range "0 .. 4294967295";
                    }
                    type enumeration {
                      enum "infinite";
                    }
                  }
                }
              }
            }
          }
        }
      }
      container access-list {
        description
          "Configure access lists";
        // ipv6 access-list *
        list named-acl {
          tailf:cli-drop-node-name;
          tailf:cli-no-key-completion;
          tailf:cli-mode-name "config-ipv6-acl";
          key "name";
          leaf name {
            type string;
          }
          uses ipv6-acl-grouping;

          container default {
            description
              "Set a command to its defaults";
            uses ipv6-acl-grouping;
          }

        }
        // ipv6 role-based access-list 
        list named-rb-acl {
          tailf:cli-drop-node-name;
          tailf:cli-no-key-completion;
          tailf:cli-mode-name "config-ipv6rb-acl";
          key "name";
          leaf name {
            type string;
          }
          leaf role-based {
            description
              "Role-based Access List";
            tailf:cli-hide-in-submode;
            tailf:cli-prefix-key;
            type empty;
          }
          uses ipv6-acl-grouping;

          container default {
            description
              "Set a command to its defaults";
            uses ipv6-acl-grouping;
          }

        }
        container log-update {
          description
            "Control access list log updates";
          leaf threshold {
            description
              "Set access-list logging threshold";
            type uint64 {
              range "0..2147483647";
            }
          }
        }
        leaf match-local-traffic {
          description
            "Match locally-generated traffic";
          tailf:cli-full-command;
          type empty;
        }
      }
      // ipv6 unicast-routing
      leaf unicast-routing {
        description
          "Enable unicast routing";
        type empty;
      }
      // ipv6 mld
      container mld {
        description
          "Global mld commands";
        container ssm-map {
          description
            "SSM mapping commands";
          leaf enable {
            description
              "Enable SSM mapping";
            tailf:cli-full-command;
            type empty;
          }
          container query {
            description
              "Which database should we query for the source";
            leaf dns {
              description
                "Use DNS for source lookup";
              tailf:cli-full-command;
              tailf:cli-show-no;
              type empty;
            }
          }
          container static {
            description
              "SSM static group to source mapping";
            tailf:cli-sequence-commands;
            tailf:cli-compact-syntax;
            leaf acl {
              tailf:cli-drop-node-name;
              type string;
            }
            leaf source-ip {
              tailf:cli-drop-node-name;
              type inet:ipv6-address;
            }
          }
        }
      }
      // ipv6 multicast
      container multicast {
        description
          "Configure multicast related commands";
        tailf:cli-compact-syntax;
              //  group-range         Enable/disable multicasting for selected
              //                      group ranges
              //  limit               Configure global multicast limit
              //  multipath           RPF across equal-cost paths
              //  pim-passive-enable  Enable PIM Passive feature
        leaf vrf {
          description
            "Select VPN Routing/Forwarding instance";
          type string;
        }
        container rpf {
          description
            "Configure multicast RPF related commands";
          tailf:cli-flatten-container;
          container backoff {
            description
              "Backoff delay after unicast routing change";
            tailf:cli-compact-syntax;
            tailf:cli-sequence-commands {
              tailf:cli-reset-siblings;
            }
            leaf initial-delay {
              tailf:cli-drop-node-name;
              type uint16 {
                range "200..65535";
              }
            }
            leaf max-delay {
              tailf:cli-drop-node-name;
              type uint16 {
                range "200..65535";
              }
            }
          }
          leaf use-bgp {
            description
              "Use BGP routes for multicast RPF lookup";
            type empty;
          }
        }
      }
      // ipv6 multicast-routing
      container multicast-routing {
        description
          "Enable IPv6 multicast";
        presence "true";
        leaf vrf {
          description
            "Select VPN Routing/Forwarding instance";
          type string;
        }
      }
      // ipv6 cef
      container cef {
        description
          "Cisco Express Forwarding";
        tailf:cli-delete-when-empty;
              //tailf:cli-diff-dependency "/ios:native/ipv6/unicast-routing";
              //must "../unicast-routing" { tailf:dependency "."; }
        presence "true";
        container accounting {
          description
            "Enable CEF accounting";
          leaf per-prefix {
            description
              "Enable per prefix accounting";
            type empty;
          }
          leaf prefix-length {
            description
              "Enable prefix length accounting";
            type empty;
          }
        }
        leaf distributed {
          description
            "Distributed Cisco Express Forwarding";
          tailf:cli-full-command;
          type empty;
        }
      }
      //ipv6 nd
      container nd {
        description
          "Configure IPv6 ND";
        container inspection {
          description "Configure NDP Inspection";
          list policy {
            description "Configure a policy for feature NDP inspection";
            tailf:cli-mode-name "config-nd-inspection";
            key "name-nd-inspection-policy" ;
            leaf name-nd-inspection-policy{
              type string;
            }
            container device-role {
              description "Sets the role of the device attached to the port";
              leaf host {
                description "Attached device is a host (default)";
                type empty;
              }
              leaf monitor {
                description
                  "Attached device is a monitor/sniffer";
                type empty;
              }
              leaf router {
                description
                  "Attached device is a route";
                type empty;
              }
              leaf switch {
                description "Attached device is a switch";
                type empty;
              }
            }
            leaf drop-unsecure {
              description "drop unsecure (3971) messages";
              type empty;
            }
            container limit {
              description "Specifies a limit";
              leaf address-count {
                description "Configure maximum address per port";
                type uint16 {
                  range "1..10000";
                }
              }
            }
            container sec-level {
              description "Specifies a minimum sec-level";
              leaf minimum {
                description "Configure minimum sec-level";
                type uint8 {
                  range "1..7";
                }
              }
            }
            container tracking {
              description "Override default tracking behavior";
              container disable {
                description "Tracking off";
                presence true;
                container stale-lifetime {
                  description "Time entry is kept inactive before delete";
                  leaf seconds {
                    description "Seconds";
                    tailf:cli-drop-node-name;
                    type uint32 {
                      range "1..86400";
                    }
                  }
                  leaf infinite {
                    description "Keep in STALE forever";
                    type empty;
                  }
                }
              }
              container enable {
                description "Tracking on";
                presence true;
                container reachable-lifetime {
                  description "Time entry is kept REACHABLE";
                  leaf seconds {
                    description "Seconds";
                    tailf:cli-drop-node-name;
                    type uint32 {
                      range "1..86400";
                    }
                  }
                  leaf infinite {
                    description "Keep in REACHABLE forever";
                    type empty;
                  }
                }
              }
            }
            leaf trusted-port {
              description "setup trusted port";
              type empty;
            }
            container validate {
              description
                "specific validation";
              leaf source-mac {
                description
                  "check source mac against link-layer-address";
                type empty;
              }
            }
          }
        }
        container cache {
          description
            "Cache entry";
          container expire {
            description
              "Expiry time for ND entries";
            tailf:cli-compact-syntax;
            leaf time {
              tailf:cli-drop-node-name;
              type uint16;
            }
            leaf refresh {
              description
                "Automatically refresh entry";
              tailf:cli-full-command;
              type empty;
            }
          }
        }
        container raguard {
          description
            "Configure RA guard";
          list policy {
            description
              "Configure a policy for feature RA guard";
            tailf:cli-mode-name "config-nd-raguard";
            tailf:cli-explicit-exit;
            key "raguard-policy-name" ;
            leaf raguard-policy-name{
              type string;
            }            
            container device-role {
              description "Sets the role of the device attached to the port";
              leaf host {
                description "Attached device is a host (default)";
                type empty;
              }
              leaf monitor {
                description "Attached device is a monitor/sniffer";
                type empty;
              }
              leaf router {
                description "Attached device is a router";
                type empty;
              }
              leaf switch {
                description "Attached device is a switch";
                type empty;
              }
            }
            container hop-limit {
              description
                "Enable verification of the advertised Hop count limit";
              leaf maximum {
                description
                  "Maximum hop count value allowed";
                tailf:cli-full-command;
                type uint8 {
                  range "1..255";
                }
              }
              leaf minimum {
                description
                  "Minimum hop count value allowed";
                tailf:cli-full-command;
                type uint8 {
                  range "1..255";
                }
              }
            }
            leaf trusted-port {
              description
                "setup trusted port";
              type empty;
            }
          }
          leaf attach-policy {
            description
              "Configure a policy for feature RA guard";
            type string;
          }
        }
      }
      // ipv6 pim
      container pim {
        description
          "Configure Protocol Independent Multicast";
        uses ipv6-pim-grouping;
        // ipv6 pim vrf *
        list vrf {
          description
            "Select VPN Routing/Forwarding instance";
          tailf:cli-suppress-mode;
          tailf:cli-delete-when-empty;
          key "id";
          leaf id {
            type string;
          }
          uses ipv6-pim-grouping;
        }
      }
      // dhcp               Configure IPv6 DHCP
      // flow-aggregation   Configure flow aggregation
      // flow-cache         Configure netflow cache parameters
      // flow-capture       Capture additional netflow information
      // flow-export        Specify host/port to send flow statistics
      // general-prefix     Configure a general IPv6 prefix
      // hop-limit          Configure hop count limit
      // host               Configure static hostnames
      // icmp               Configure ICMP parameters
      // inspect            Context-based Access Control Engine
      // local              Specify local options
      // mfib               Multicast Forwarding
      // mobile             Mobile IPv6
      // multicast-routing  Enable IPv6 multicast
      // nat                NAT-PT Configuration commands
      // neighbor           Neighbor
      // ospf               OSPF
      // pim                Configure Protocol Independent Multicast
      // port-map  Port to application mapping (PAM) configuration commands

      //ipv6 rip
      container rip {
        description
          "Configure ipv6 RIP settings";
        leaf vrf-mode {
          description
            "Enable RIPng VRF support";
          type enumeration {
            enum "enable";
          }
        }
      }
      // ipv6 route
      container route {
        description
          "Configure static routes";
        // ipv6 route prefix
        uses ipv6-route-grouping;
        // ipv6 route vrf *
        list vrf {
          description
            "Configure static route for a VPN Routing/Forwarding instance";
          tailf:cli-suppress-mode;
          tailf:cli-delete-when-empty;
          tailf:cli-compact-syntax;
          tailf:cli-reset-container;
          tailf:cli-incomplete-command;
          tailf:cli-diff-dependency "/ios:native/vrf/definition";
          tailf:cli-diff-dependency "/ios:native/vrf/definition/address-family";
          key "name";
          leaf name {
            type string;
          }
          uses ipv6-route-grouping;
        }
      }

      // router             Enable an IPV6 routing process
      // ipv6 router
      container router {
        description
          "Enable an IPV6 routing process";
        //ipv6 router eigrp *
        list eigrp {
          description
            "Enhanced Interior Gateway Routing Protocol (EIGRP)";
          tailf:cli-mode-name "config-rtr";
          key "id";
          leaf id {
            description
              "Autonomous System ID";
            type uint16 {
              range "1..65535";
            }
          }
          container default-metric {
            description
              "Set metric of redistributed routes";
            tailf:cli-sequence-commands;
            tailf:cli-compact-syntax;
            leaf dm-rdr {
              tailf:cli-drop-node-name;
              description
                "Bandwidth in Kbits per second";
              type uint32 {
                range "1..4294967295";
              }
            }
            leaf dm-rdr0 {
              tailf:cli-drop-node-name;
              description
                "delay metric in 10 microsecond units";
              type uint32 {
                range "0..4294967295";
              }
            }
            leaf dm-rdr-pct {
              description
                "Reliability metric where 255 is 100% reliable";
              tailf:cli-drop-node-name;
              type uint8 {
                range "0..255";
              }
            }
            leaf effective-bandwith-metric {
              tailf:cli-drop-node-name;
              description
                "Effective bandwidth metric (Loading) where 255 is 100% loaded";
              type uint8;
            }
            leaf mtu {
              tailf:cli-drop-node-name;
              description
                "Maximum Transmission Unit metric of the path ";
              type uint16;
            }
          }
          container distance {
            description
              "Define an administrative distance";
            container eigrp {
              description
                "EIGRP-IPV6 distance";
              tailf:cli-sequence-commands;
              tailf:cli-compact-syntax;
              leaf internal-route {
                tailf:cli-drop-node-name;
                description
                  "Distance for internal routes";
                type uint8;
              }
              leaf external-route {
                tailf:cli-drop-node-name;
                description
                  "Distance for external routes";
                type uint8;
              }
            }
          }
          uses ipv6-router-distribute-list-grouping;
          container eigrp {
            description
              "EIGRP specific commands";
            leaf router-id {
              description
                "router id for this EIGRP process";
              type inet:ipv4-address;
            }
          }
          list passive-interface {
            description
              "Suppress routing updates on an interface";
            tailf:cli-suppress-mode;
            key "name";
            leaf name {
              tailf:cli-show-no;
              type union {
                type string;
                type enumeration {
                  enum "default";
                }
              }
            }
          }
        }
        //ipv6 router rip *
        list rip {
          description
            "IPv6 Routing Information Protocol (RIPv6)";
          tailf:cli-mode-name "config-rtr";
          key "id";
          leaf id {
            type string;
          }
          leaf distance {
            description
              "Administrative distance";
            tailf:cli-full-command;
            type uint8 {
              range "1..254";
            }
          }
          uses ipv6-router-distribute-list-grouping;
          leaf maximum-paths {
            description
              "Forward packets over multiple paths";
            tailf:cli-full-command;
            type uint32 {
              range "1..32";
            }
          }
          leaf poison-reverse {
            description
              "Poison reverse updates";
            tailf:cli-full-command;
            type empty;
          }
          container redistribute {
            description
              "Redistribute IPv6 prefixes from another routing protocol";
            container application {
              description
                "Application Protocol";
              tailf:cli-compact-syntax;
              uses ipv6-router-rip-redistribute-grouping;
            }
            container lisp {
              description
                "Locator ID Separation Protocol (LISP)";
              tailf:cli-compact-syntax;
              uses ipv6-router-rip-redistribute-grouping;
            }
            container nd {
              description
                "Neighbor Discovery";
              tailf:cli-compact-syntax;
              uses ipv6-router-rip-redistribute-grouping;
            }
            uses default-redistribute-grouping;
          }
          leaf split-horizon {
            description
              "Split horizon updates";
            tailf:cli-full-command;
            type empty;
          }
          container timers {
            description
              "Adjust routing timers";
            tailf:cli-compact-syntax;
            tailf:cli-sequence-commands;
            leaf update {
              description
                "Update period";
              tailf:cli-drop-node-name;
              type uint16 {
                range "5..65535";
              }
            }
            leaf timeout {
              description
                "Route timeout period";
              tailf:cli-drop-node-name;
              type uint16 {
                range "1..65535";
              }
            }
            leaf holddown {
              description
                "Route holddown period";
              tailf:cli-drop-node-name;
              type uint16 {
                range "0..65535";
              }
            }
            leaf garbage-collection {
              description
                "Route garbage collection period";
              tailf:cli-drop-node-name;
              type uint16 {
                range "1..65535";
              }
            }
          }
        }
      }
      // source-route       Process packets with source routing header options
      // ipv6 source-route
      leaf source-route {
        description
          "Process packets with source routing header options";
        tailf:cli-boolean-no;
        tailf:cli-trim-default;
        type boolean;
      }


      // ipv6 prefix-list
      container prefix-list {
        description
          "Build a prefix list";
        list prefixes {
          tailf:cli-drop-node-name;
          tailf:cli-suppress-mode;
          tailf:cli-delete-when-empty;
          key "name";
          leaf name {
            type string {
              pattern "([^s].*)|(s[^e].*)|(se[^q].*)(seq[^u].*)|(sequ[^e].*)|(seque[^n].*)|(sequen[^c].*)|(sequenc[^e].*)|(sequence[^\\-].*)|(sequence\\-[^n].*)|(sequence\\-n[^u].*)|(sequence\\-nu[^m].*)|(sequence\\-num[^b].*)|(sequence\\-numb[^e].*)|(sequence\\-numbe[^r].*)|(sequence\\-number..*)";
            }
          }
          leaf description {
            description
              "Prefix-list specific description";
            tailf:cli-multi-value;
            tailf:cli-full-command;
            type string {
              length "1..80";
            }
          }
          container permit {
            description
              "Specify packets to forward";
            tailf:cli-sequence-commands;
            tailf:cli-compact-syntax;
            leaf address {
              tailf:cli-drop-node-name;
              type ios:ipv6-prefix;
            }
            leaf ge {
              description
                "Minimum prefix length to be matched";
              tailf:cli-break-sequence-commands;
              type uint8 {
                range "0..128";
              }
            }
            leaf le {
              description
                "Maximum prefix length to be matched";
              tailf:cli-full-command;
              type uint8 {
                range "0..128";
              }
            }
          }
          container deny {
            description
              "Specify packets to reject";
            tailf:cli-sequence-commands;
            tailf:cli-compact-syntax;
            leaf address {
              tailf:cli-drop-node-name;
              type ios:ipv6-prefix;
            }
            leaf ge {
              description
                "Minimum prefix length to be matched";
              tailf:cli-break-sequence-commands;
              type uint8 {
                range "0..128";
              }
            }
            leaf le {
              description
                "Maximum prefix length to be matched";
              tailf:cli-full-command;
              type uint8 {
                range "0..128";
              }
            }
          }
          list seq {
            // NOTE: the seq element is not actually mandatory
            // in the Cisco CLI. If it isn't give
            description
              "sequence number of an entry";
            tailf:cli-suppress-mode;
            tailf:cli-delete-when-empty;
            key "no";
            leaf no {
              type uint32 {
                range "1..4294967294";
              }
              tailf:key-default "10";
            }
            container deny {
              description
                "Specify packets to reject";
              tailf:cli-sequence-commands {
                tailf:cli-reset-all-siblings;
              }
              tailf:cli-compact-syntax;
              leaf ip {
                tailf:cli-drop-node-name;
                type ios:ipv6-prefix;
              }
              leaf ge {
                description
                  "Minimum prefix length to be matched";
                tailf:cli-break-sequence-commands;
                type uint16 {
                  range "1..128";
                }
              }
              leaf le {
                description
                  "Maximum prefix length to be matched";
                tailf:cli-full-command;
                type uint16 {
                  range "1..128";
                }
              }
            }
            container permit {
              description
                "Specify packets to forward";
              tailf:cli-sequence-commands {
                tailf:cli-reset-all-siblings;
              }
              tailf:cli-compact-syntax;
              leaf ip {
                tailf:cli-drop-node-name;
                type ios:ipv6-prefix;
              }
              leaf ge {
                description
                  "Minimum prefix length to be matched";
                tailf:cli-break-sequence-commands;
                type uint16 {
                  range "1..128";
                }
              }
              leaf le {
                description
                  "Maximum prefix length to be matched";
                tailf:cli-full-command;
                type uint16 {
                  range "1..128";
                }
              }
            }
          }
        }
        leaf sequence-number {
          description
            "Include/exclude sequence numbers in NVGEN";
          tailf:cli-full-command;
          type empty;
        }
      }
    }

    /// ========================================================================
    /// vlan
    /// ========================================================================
    container vlan {
      description
        "VLAN commands";
      list access-map {
        tailf:cli-mode-name "access-map-config";
        description "Create vlan access-map or enter vlan access-map command mode";
        key "name";
        leaf name {
            type string;
        }        
        leaf value {
          tailf:cli-drop-node-name;
          tailf:cli-hide-in-submode;
          type uint16{
            range "1..65535";
          }
        }
        leaf action {
          description
            "Take the action";
          type enumeration {
            enum "drop";
            enum "forward";
          }
        }
        container match {
          description
            "Match values.";
          container ipv6 {
            description
              "IPv6 based match";
            leaf-list address {
              tailf:cli-flat-list-syntax;
              type string;
            }
          }
        }
      }
      list configuration {
        description "vlan feature configuration mode";
        key "vlan-id";
        leaf vlan-id {
          description "VLAN ID List Eg. 1-10,15";
          type union {
            type uint16 {
              range "1..4096";
            }
            type string;
          }
        }
        container ip {
          description "ip root chain";
          container flow {
            description "vlan NetFlow configuration commands";
            list monitor {
              description "Apply a Flow Monitor";
              tailf:cli-diff-dependency "/ios:native/flow/monitor";
              tailf:cli-suppress-mode;
              key flow-monitor;
              leaf flow-monitor{
                description "User defined";         
                type string;
              }
              leaf input {
                type empty;
              }
              leaf output {
                type empty;
              }              
            }
          }
        }
      }
      list filter {
        tailf:cli-suppress-mode;
        description "Apply a VLAN Map";
        key "word";
        leaf word {
          tailf:cli-drop-node-name;
          type string;
        }
        leaf vlan-list {
          description "VLANs to apply filter to";
          type union {
            type uint16 {
              range "1..4094";
            }
            type string;
          }     
        }
      }    
      container accounting {
        description
          "VLAN accounting configuration";
        presence "true";
        leaf input {
          description
            "Input accounting";
          type empty;
        }
        leaf output {
          description
            "Output accounting";
          type empty;
        }
      }
      container internal {
        description
          "internal VLAN";
        container allocation {
          description
            "internal VLAN allocation";
          leaf policy {
            type enumeration {
              enum "ascending";
              enum "descending";
            }
          }
        }
      }
      container dot1q {
        description
          "dot1q parameters";
        container tag {
          description
            "tag parameters";
          leaf native {
            description
              "tag native vlan";
            type empty;
          }
        }
      }
      container access-log {
        description
          "Configure VACL logging";
        leaf maxflow {
          description
            "Set vacl logging maximum flow number";
          type uint16 {
            range "0..2048";
          }
        }
        leaf ratelimit {
          description
            "Set vacl logging rate limiter";
          type uint16 {
            range "10..5000";
          }
        }
        leaf threshold {
          description
            "Set vacl log-update threshold";
          type uint32 {
            range "0..2147483647";
          }
        }
      }
      list vlan-list {
        tailf:cli-drop-node-name;
        tailf:cli-mode-name "config-vlan";
        tailf:cli-range-list-syntax;
        tailf:cli-explicit-exit;
        key "id";
        leaf id {
          type union {
            type uint16 {
              range "1..4094";
            }
            type string;
          }
        }
        leaf remote-span {
          description 
            "Configure as Remote SPAN VLAN";
          type empty;
        }
        container private-vlan {
          description 
            "Configure a private VLAN";
          tailf:cli-diff-dependency "/ios:native/vtp/mode/transparent";
          tailf:cli-diff-dependency "/ios:native/vtp/mode/off";
          leaf primary {
            description 
              "Configure the VLAN as a primary private VLAN";
            type empty;
          }
          leaf association {
            description 
              "Configure association between private VLANs";
            type string;
          }
          leaf community {
          description 
            "Configure the VLAN as a community private VLAN";
          type empty;
          }
          leaf isolated {
            description 
              "Configure the VLAN as an isolated private VLAN";
            type empty;
          }
        }
        leaf name {
          description
            "Ascii name of the VLAN";
          tailf:cli-full-command;
          tailf:cli-multi-value;
          type string {
            length "1..32";
          }
        }
        container lldp {
          leaf run {
            type empty;
          }
        }
        leaf uni-vlan {
          description
            "Configure a UNI VLAN";
          tailf:cli-full-command;
          type enumeration {
            enum "community";
            enum "isolated";
          }
        }
      }
    }

    /// ========================================================================
    /// interface
    /// ========================================================================
    container interface {
      description
        "Configure interfaces";
      tailf:cli-diff-dependency "/ios:native/vrf";
      tailf:cli-explicit-exit;

      // interface AppNav-Compress
      list AppNav-Compress {
        description
          "Service-Context Virtual Interface Compress";
        tailf:cli-allow-join-with-key {
          tailf:cli-display-joined;
        }
        tailf:cli-mode-name "config-if";
        tailf:cli-suppress-key-abbreviation;
        key "name";
        leaf name {
          type uint16 {
            range "1..1000";
          }
        }
        uses interface-common-grouping;
      }
      // interface AppNav-UnCompress
      list AppNav-UnCompress {
        description
          "Service-Context Virtual Interface UnCompress";
        tailf:cli-allow-join-with-key {
          tailf:cli-display-joined;
        }
        tailf:cli-mode-name "config-if";
        tailf:cli-suppress-key-abbreviation;
        key "name";
        leaf name {
          type uint16 {
            range "1..1000";
          }
        }
        uses interface-common-grouping;
      }
      // interface ATM #
      list ATM {
        description
          "ATM interface";
        tailf:cli-allow-join-with-key {
          tailf:cli-display-joined;
        }
        tailf:cli-mode-name "config-if";
        tailf:cli-suppress-key-abbreviation;
        key "name";
        leaf name {
          type string {
            pattern "([0-9]/){2}([0-9]|(ima[0-9]))(:[0-9])?";
          }
        }
        uses interface-atm-grouping;
      }
      // subinterface ATM #.#
      container ATM-subinterface {
        tailf:cli-drop-node-name;
        list ATM {
          tailf:cli-allow-join-with-key {
            tailf:cli-display-joined;
          }
          tailf:cli-mode-name "config-subif";
          tailf:cli-suppress-key-abbreviation;
          key "name";
          leaf name {
            type string {
              pattern "([0-9]/){2}[0-9]\\.([0-9]/){3}[0-9]";
            }
          }
          uses interface-atm-grouping;
        }
      }
      // interface ATM-ACR #
      list ATM-ACR {
        description
          "ATM-ACR interface";
        tailf:cli-allow-join-with-key {
          tailf:cli-display-joined;
        }
        tailf:cli-mode-name "config-if";
        tailf:cli-suppress-key-abbreviation;
        key "name";
        leaf name {
          type string {
            pattern "[0-9]";
          }
        }
        uses interface-atm-grouping;
      }
      // subinterface ATM-ACR #.#
      container ATM-ACRsubinterface {
        tailf:cli-drop-node-name;
        list ATM-ACR {
          tailf:cli-allow-join-with-key {
            tailf:cli-display-joined;
          }
          tailf:cli-mode-name "config-subif";
          tailf:cli-suppress-key-abbreviation;
          key "name";
          leaf name {
            type string {
              pattern "[0-9]\\.([0-9]/){3}[0-9]";
            }
          }
          uses interface-atm-grouping;
        }
      }
      // interface BDI
      list BDI {
        description
          "Bridge-Domain interface";
        tailf:cli-allow-join-with-key {
          tailf:cli-display-joined;
        }
        tailf:cli-mode-name "config-if";
        key "name";
        leaf name {
          type string;
        }
        uses interface-common-grouping;
      }
      // interface CEM #
      list CEM {
        description
          "Circuit Emulation interface";
        tailf:cli-allow-join-with-key {
          tailf:cli-display-joined;
        }
        tailf:cli-mode-name "config-if";
        tailf:cli-suppress-key-abbreviation;
        key "name";
        leaf name {
          type string {
            pattern "([0-9]/){2}[0-9]";
          }
        }
        uses interface-atm-grouping;
      }
      // interface CEM-ACR #
      list CEM-ACR {
        description
          "Circuit Emulation interface";
        tailf:cli-allow-join-with-key {
          tailf:cli-display-joined;
        }
        tailf:cli-mode-name "config-if";
        tailf:cli-suppress-key-abbreviation;
        key "name";
        leaf name {
          type uint8 {
            range "0..255";
          }
        }
        uses interface-atm-grouping;
      }
      // interface Embedded-Service-Engine
      list Embedded-Service-Engine {
        description
          "cisco embedded service engine module";
        tailf:cli-allow-join-with-key {
          tailf:cli-display-joined;
        }
        tailf:cli-mode-name "config-if";
        key "name";
        leaf name {
          type string;
        }
        uses interface-common-grouping;
      }


      // interface FastEthernet
      list FastEthernet {
        description
          "FastEthernet IEEE 802.3";
        tailf:cli-allow-join-with-key {
          tailf:cli-display-joined;
        }
        tailf:cli-mode-name "config-if";
        key "name";
        leaf name {
          type string;
        }
        uses interface-switch-grouping;
        uses interface-ethernet-grouping;
        uses interface-common-grouping;
        uses interface-zone-member-grouping;        
      }
      // interface GigabitEthernet
      list GigabitEthernet {
        description
          "GigabitEthernet IEEE 802.3z";
        tailf:cli-allow-join-with-key {
          tailf:cli-display-joined;
        }
        tailf:cli-mode-name "config-if";
        key "name";
        leaf name {
          type string;
        }
        leaf media-type {
          description
            "Media type";
          type enumeration {
            enum "auto-select";
            enum "rj45";
            enum "sfp";
          }
        }
        leaf port-type {
          type enumeration {
            enum "nni";
          }
        }
        uses interface-switch-grouping;
        uses interface-ethernet-grouping;
        uses interface-common-grouping;
        uses interface-zone-member-grouping;        
      }
      // interface TenGigabitEthernet
      list TenGigabitEthernet {
        description
          "Ten Gigabit Ethernet";
        tailf:cli-allow-join-with-key {
          tailf:cli-display-joined;
        }
        tailf:cli-mode-name "config-if";
        key "name";
        leaf name {
          type string;
        }
        leaf media-type {
          description
            "Media type";
          type enumeration {
            enum "auto-select";
            enum "rj45";
            enum "sfp";
          }
        }
        leaf port-type {
          type enumeration {
            enum "nni";
          }
        }
        container lacp {
          description "LACP interface subcommands";
          container rate {
            description "Rate at which the LACP packets are requested to be ingressed to this interface";
            leaf fast {
              description "Request LACP packets to be ingressed at the 1 second rate for this interface";
              type empty;
            }
          }
        }
        uses interface-switch-grouping; //CATALYST
        uses interface-ethernet-grouping;
        uses interface-common-grouping;
        uses interface-zone-member-grouping;        
      }
      // interface Loopback
      list Loopback {
        description
          "Loopback interface";
        tailf:cli-allow-join-with-key {
          tailf:cli-display-joined;
        }
        tailf:cli-mode-name "config-if";
        key "name";
        leaf name {
          type uint32;
        }
        uses interface-common-grouping;
      }
      // interface LISP
      list LISP {
        description
          "Locator/ID Separation Protocol Virtual Interface";
        tailf:cli-allow-join-with-key {
          tailf:cli-display-joined;
        }
        tailf:cli-mode-name "config-if";
        key "name";
        leaf name {
          type decimal64 {
            fraction-digits 10;
            range "0..65520";
          }
        }
        uses interface-common-grouping;
      }

      list nve {
        description
          "Network virtualization endpoint interface";
        tailf:cli-allow-join-with-key {
          tailf:cli-display-joined;
        }
        tailf:cli-mode-name "config-if";
        key "name";
        leaf name {
          type uint16 {
            range "1..4096";
          }
        }
        container source-interface {
          description
            "Specify source interface for NVE";
          uses interface-grouping;
        }
        container member {
          list vni {
            description
              "Configure VNI information";
            tailf:cli-suppress-mode;
            key "vni-range";
            leaf vni-range {
              type string;
            }
            container mcast-group {
              tailf:cli-sequence-commands;
	      tailf:cli-compact-syntax;
              leaf multicast-group-min {
                tailf:cli-drop-node-name;
                description
                  "Starting Multicast Group IPv4 Address";
                type inet:ipv4-address;
              }
              leaf multicast-group-max {
                tailf:cli-drop-node-name;
                description
                  "Ending Multicast Group IPv4 Address";
                type inet:ipv4-address;
              }
            }
          }
        }
      }
      // interface overlay
      list overlay {
        description
          "Overlay interface";
        tailf:cli-allow-join-with-key {
          tailf:cli-display-joined;
        }
        tailf:cli-mode-name "config-if";
        key "name";
        leaf name {
          type uint16 {
            range "0..512";
          }
        }
        uses interface-common-grouping;
        uses interface-ethernet-grouping;
        uses interface-overlay-grouping;
      }


      // interface Port-channel
      list Port-channel {
        description
          "Ethernet Channel of interfaces";
        tailf:cli-allow-join-with-key {
          tailf:cli-display-joined;
        }
        tailf:cli-mode-name "config-if";
        key "name";
        leaf name {
          type uint32 {
            range "1..512";
          }
        }
        container lacp {
          description 
            "LACP Port Channel interface subcommands";
          leaf max-bundle {
            description 
              "LACP maximum number of ports to bundle in this port channel";
            type int8 {
              range "1..8";
            }  
          }
        }
        leaf pc-speed {
          tailf:alt-name "speed";
          description
            "Configure speed operation.";
          type enumeration {
            enum "10";
            enum "100";
            enum "1000";
            enum "nonegotiate";
            enum "auto";
          }
        }
        container port-channel {
          description "Port Channel interface subcommands";
          tailf:cli-compact-syntax;
          tailf:cli-sequence-commands;
          leaf min-links {
            description "Minimum number of bundled ports needed to bring up "
                       +"     this port channel";
            tailf:cli-full-command;
            type uint8 {
              tailf:info "<2-8> The minimum number of bundled ports needed "
                         +"before this port channel can come up";
              range "2..8";
            }
          }
          leaf standalone-disable {
            description "Ports will go to suspended mode if peer does not "
                       +"respond. Use with [no] prefix for independent mode.";
            tailf:cli-full-command;
            type empty;
          }
        }
        uses interface-switch-grouping; //CATALYST
        uses interface-common-grouping;        
        uses interface-ethernet-grouping;
      }
      // subinterface Port-channel #.#
      container Port-channel-subinterface {
        tailf:cli-drop-node-name;
        list Port-channel {
          tailf:cli-allow-join-with-key {
            tailf:cli-display-joined;
          }
          tailf:cli-mode-name "config-subif";
          tailf:cli-suppress-key-abbreviation;
          key "name";
          leaf name {
            type string;
          }
          uses interface-switch-grouping; //CATALYST
          uses interface-common-grouping;         
          uses interface-ethernet-grouping;
        }
      }

      //interface pseudowire
      list pseudowire {
        description
          "Pseudowire Interface";
        tailf:cli-mode-name "config-if";
        tailf:cli-allow-join-with-key {
          tailf:cli-display-joined;
        }
        key "name";
        leaf name {
          type uint32 {
            range "1..231072";
          }
        }
        uses pseudowire-grouping;
      }
      //interface SM
      list SM {
        description
          "SM Interface";
        tailf:cli-mode-name "config-if";
        tailf:cli-allow-join-with-key {
          tailf:cli-display-joined;
        }
        key "name";
        leaf name {
          type string {
            pattern "([0-9])+(/([0-9])+)?";
          }
        }
        uses interface-common-grouping;
      }
      //interface Cellular
      list Cellular {
        description
          "Cellular Interface";
        tailf:cli-mode-name "config-if";
        tailf:cli-allow-join-with-key {
          tailf:cli-display-joined;
        }
        key "name";
        leaf name {
          type string {
            pattern "([0-9])+(/([0-9])+)?";
          }
        }
        uses interface-common-grouping;
        uses interface-cellular-grouping;
      }


      // interface Vlan
      list Vlan {
        description
          "Catalyst Vlans";
        tailf:cli-allow-join-with-key {
          tailf:cli-display-joined;
        }
        tailf:cli-diff-dependency "/ios:native/vlan";
        key "name";
        leaf name {
          type uint16 {
            range "1..4094";
          }
        }
        // interface vlan / private-vlan
        container private-vlan {
          description 
            "Configure private VLAN SVI interface settings";
          leaf mapping {
            description 
              "Set the private VLAN SVI interface mapping";
            tailf:cli-diff-dependency "/ios:native/vlan/vlan-list/private-vlan/primary";
            tailf:cli-diff-dependency "/ios:native/vlan/vlan-list/private-vlan/community";
            tailf:cli-diff-dependency "/ios:native/vlan/vlan-list/private-vlan/isolated";
            tailf:cli-diff-dependency "/ios:native/vlan/vlan-list/private-vlan/association";  
              type string;
          }
        }
        list vrrp{
          tailf:cli-suppress-mode;
          key "number";
          leaf number {
            tailf:cli-drop-node-name;
            type uint8;
          }
          list ip {
            description
              "Enable Virtual Router Redundancy Protocol (VRRP) for IP";            
            tailf:cli-suppress-mode;
            key "ipv4";
            leaf ipv4 {
              description
                "VRRP group IP address";                
              type inet:ipv4-address;
            }
            leaf secondary {
              description
                "Make this IP address a secondary address";
              type empty;
            }
          }
        }
        container glbp {
          description "Gateway Load Balancing Protocol interface commands";
          list  range {
            tailf:cli-drop-node-name;
            tailf:cli-suppress-mode;
            key "range";
            leaf range {
              description "Group number";
              type uint16 {
                range "0..1023";
              }
            }
            container forwarder {
              description "Forwarder configuration";
              container preempt {
                description "Overthrow lower priority active forwarders";
                presence true;
                container delay {
                  description "Wait before preempting";
                  leaf minimum {
                    description "Number of seconds for minimum delay";
                    type uint16 {
                      range "0..3600";
                    }
                  }
                }
              }
            }
            container ip {
              description "Enable group and set virtual IP address";
              presence true;
              list ipv4 {
                tailf:cli-drop-node-name;
                tailf:cli-suppress-mode;
                key "ipv4";
                leaf ipv4 {
                  description "Virtual IP address";
                  type inet:ipv4-address;
                }
              }
            }
            container preempt {
              description "Overthrow lower priority designated routers";
              presence true;
              container delay {
                description "Wait before preempting";
                leaf minimum {
                  description "Number of seconds for minimum delay";
                  type uint16 {
                    range "0..3600";
                  }
                }
              }
            }
            leaf priority {
              description "Priority value";
              type uint8 {
                range "1..255";
              }
            }
            container weighting {
              description "Gateway weighting and tracking";
              list value {
                description "Weighting maximum value";
                tailf:cli-drop-node-name;
                tailf:cli-suppress-mode;  
                key value;
                leaf value {
                  tailf:cli-drop-node-name;
                  type int8;
                }
                leaf upper{
                  type int8; 
                }
                leaf lower{
                  type int8; 
                }
              }            
              container track {
                description "Interface tracking";
                list  range {
                  tailf:cli-drop-node-name;
                  tailf:cli-suppress-mode;
                  key "range";
                  leaf range {
                    description "Tracked object";
                    type uint16 {
                      range "1..1000";
                    }
                  }
                  leaf decrement {
                    description "Decrement value";
                    type uint8 {
                      range "1..255";
                    }
                  }
                }
              }
            }
            container timers {
              description "Adjust GLBP timers";
              container msec {
                description "Specify hello interval in milliseconds";
                list  range {
                  tailf:cli-drop-node-name;
                  tailf:cli-suppress-mode;
                  key "range";
                  leaf range {
                    description "Hello interval in milliseconds";
                    type uint16 {
                      range "50..60000";
                    }
                  }
                  leaf range0 {
                    description "Hold time in seconds";
                    tailf:cli-drop-node-name;
                    type uint8 {
                      range "1..180";
                    }
                  }
                }
              }
            }
            leaf name {
              description 
                "Redundancy name";
              type string;    
            }
          }
        }
        uses interface-common-grouping;
        uses interface-zone-member-grouping;
      }

      // interface Group-Async
      list Group-Async {
        description
          "Async Group interface";
        tailf:cli-allow-join-with-key {
          tailf:cli-display-joined;
        }
        key "name";
        leaf name {
          type uint16 {
            range "0..64";
          }
        }
        leaf physical-layer {
          description
            "Configure sync or async physical layer on serial interface";
          type enumeration {
            enum "async";
            enum "sync";
          }
        }
        uses interface-common-grouping;
      }
      // interface Multilink
      list Multilink {
        description
          "Multilink-group interface";
        tailf:cli-allow-join-with-key {
          tailf:cli-display-joined;
        }
        tailf:cli-mode-name "config-if";
        tailf:cli-full-command;
        key "name";
        leaf name {
          type uint16 {
            range "1..65535";
          }
        }
        uses interface-common-grouping;
        uses interface-pointtopoint-grouping;
      }
      // interface Serial
      list Serial {
        description
          "Serial interface";
        tailf:cli-allow-join-with-key {
          tailf:cli-display-joined;
        }
        tailf:cli-mode-name "config-if";
        tailf:cli-full-command;
        key "name";
        leaf name {
          type string {
            pattern "([0-9])+/([0-9])+/([0-9])+\\.([0-9])+/([0-9])+/([0-9])+/([0-9])+:([0-9])";
          }
        }
        uses interface-common-grouping;
        uses interface-pointtopoint-grouping;
      }


      // interface Tunnel #
      list Tunnel {
        description
          "Tunnel interface";
        tailf:cli-allow-join-with-key {
          tailf:cli-display-joined;
        }
        tailf:cli-mode-name "config-if";
        tailf:cli-suppress-key-abbreviation;
        key "name";
        leaf name {
          type uint32;
        }
        uses interface-common-grouping;
        // interface Tunnel* / qos
        container qos {
          description
            "Quality of Service related commands";
          leaf pre-classify {
            description
              "Enable QOS classification before packets are tunnel encapsulated";
            type empty;
          }
        }
        // interface Tunnel* / tunnel
        uses interface-tunnel-grouping;
      }

      // interface Virtual-Template
      list Virtual-Template {
        description
          "Virtual Template interface";
        tailf:cli-allow-join-with-key {
          tailf:cli-display-joined;
        }
        tailf:cli-mode-name "config-if";
        tailf:cli-explicit-exit;
        key "name";
        leaf name {
          type uint16 {
            range "1..4095";
          }
        }
        leaf type {
          description
            "type of the virtual-template";
          tailf:cli-hide-in-submode;
          type enumeration {
            enum "ethernet";
            enum "serial";
            enum "tunnel";
            enum "vpn";
          }
        }
        uses interface-switch-grouping; //CATALYST
        uses interface-ethernet-grouping;
        uses interface-common-grouping;
        uses interface-zone-member-grouping;       
        uses interface-pointtopoint-grouping;
        // interface Tunnel* / tunnel
        uses interface-tunnel-grouping;
      }
      // interface VirtualPortGroup
      list VirtualPortGroup {
        description
          "Virtual Port Group";
        tailf:cli-allow-join-with-key {
          tailf:cli-display-joined;
        }
        tailf:cli-mode-name "config-if";
        tailf:cli-full-command;
        tailf:cli-explicit-exit;
        key "name";
        leaf name {
          type uint16 {
            range "0..31";
          }
        }
        uses interface-switch-grouping;  //CATALYST
        uses interface-ethernet-grouping;
        uses interface-common-grouping;
      }
      // interface vasileft
      list vasileft {
        description
          "vasileft";
        tailf:cli-allow-join-with-key {
          tailf:cli-display-joined;
        }
        tailf:cli-mode-name "config-if";
        tailf:cli-full-command;
        tailf:cli-explicit-exit;
        key "name";
        leaf name {
          type uint16 {
            range "1..2000";
          }
        }
        uses interface-switch-grouping; //CATALYST
        uses interface-ethernet-grouping;
        uses interface-common-grouping;
      }
      // interface vasiright
      list vasiright {
        description
          "vasiright";
        tailf:cli-allow-join-with-key {
          tailf:cli-display-joined;
        }
        tailf:cli-mode-name "config-if";
        tailf:cli-full-command;
        tailf:cli-explicit-exit;
        key "name";
        leaf name {
          type uint16 {
            range "1..2000";
          }
        }
        uses interface-switch-grouping; //CATALYST
        uses interface-ethernet-grouping;
        uses interface-common-grouping;
      }

    }
    

    /// ========================================================================
    /// route-map
    /// ========================================================================
    list route-map {
      description
        "Route map tag";
      tailf:cli-compact-syntax;
      tailf:cli-incomplete-command;
      tailf:cli-sequence-commands;
      tailf:cli-suppress-mode;
      key "name";
      leaf name {
        description
          "WORD;;Route map tag";
        type string;
      }
      list route-map-seq {
        tailf:cli-drop-node-name;
        tailf:cli-mode-name "config-route-map";
        tailf:cli-compact-syntax;
        key "sequence";
        // route-map * #
        leaf sequence {
          type uint16 {
            range "0..65535";
          }
        }
      // route-map * permit
      // route-map * deny
        leaf operation {
          tailf:cli-drop-node-name;
          tailf:cli-prefix-key;
          type enumeration {
            enum "deny" {
              tailf:code-name "op_deny";
            }
            enum "permit" {
              tailf:code-name "op_permit";
            }
          }
        }
        // route-map * / description
        leaf description {
          description
            "Route-map comment";
          tailf:cli-multi-value;
          type string;
        }
        // route-map * / set
        container set {
          description
            "Set values in destination routing protocol";
          container aigp-metric {
            description
              "accumulated metric value";
            leaf value {
              description
                "manual value";
              tailf:cli-drop-node-name;
              type uint32 {
                range "0..4294967295";
              }
            }
            leaf igp-metric {
              description
                "metric value from rib";
              type empty;
            }
          }
          // route-map * / set as-path
          container as-path {
            description
              "Prepend string for a BGP AS-path attribute";
            container prepend {
              description
                "Prepend to the as-path";
              container as-container {
                tailf:cli-drop-node-name;
                leaf as-number {
                  description
                    "<1-65535>;;AS number";
                  tailf:cli-drop-node-name;
                  tailf:cli-multi-value;
                  type string;
                }
              }
              container last-as-cont {
                tailf:cli-drop-node-name;
                leaf last-as {
                  type uint16 {
                    range "1..10";
                  }
                }
              }
            }
            container tag {
              description
                "Set the tag as an AS-path attribute";
              tailf:cli-full-command;
              presence "tag";
            }
          }
          // route-map * / set automatic-tag
          leaf automatic-tag {
            description
              "Automatically compute TAG value";
            type empty;
          }
          // route-map * /set clns
          container clns {
            description
              "OSI summary address";
            uses next-hop-address-grouping;
          }
          // route-map * / set community
          container community {
            description
              "BGP community attribute";
            tailf:cli-compact-syntax;
            choice community-well-known-choice {
              leaf none {
                description
                  "No community attribute";
                type empty;
              }
              container community-well-known {
                tailf:cli-drop-node-name;
                tailf:cli-compact-syntax;
                tailf:cli-sequence-commands;
                leaf-list community-list {
                  tailf:cli-drop-node-name;
                  tailf:cli-optional-in-sequence;
                  tailf:cli-flat-list-syntax;
                  type union {
                    type community-number-type;
                    type community-well-known-type;
                  }
                }
                leaf additive {
                  description
                    "Add to the existing community";
                  type empty;
                }
              }
            }
          }
          // route-map * / set comm-list
          container comm-list {
            description
              "set BGP community list (for deletion)";
            tailf:cli-sequence-commands;
	    tailf:cli-compact-syntax;
            choice comm-list-choice {
              leaf comm-list-standard {
                tailf:cli-drop-node-name;
                tailf:cli-incomplete-command;
                type uint16 {
                  range "1..99";
                }
              }
              leaf comm-list-expanded {
                tailf:cli-drop-node-name;
                tailf:cli-incomplete-command;
                type uint16 {
                  range "100..500";
                }
              }
              leaf comm-list-name {
                tailf:cli-drop-node-name;
                tailf:cli-incomplete-command;
                type string;
              }
            }
            leaf delete {
              tailf:cli-full-command;
              description
                "Delete matching communities";
              type empty;
            }
          }
          container dampening {
            description
              "Set BGP route flap dampening parameters";
            list dampening-list {
              tailf:cli-drop-node-name;
              tailf:cli-suppress-mode;
              key "half-life-penalty restart-penalty suppress-penalty max-suppress-penalty";
              leaf half-life-penalty {
                description
                  "half-life time for the penalty";
                tailf:cli-drop-node-name;
                type uint8 {
                  range "1..45";
                }
              }
              leaf restart-penalty {
                description
                  "penalty to start reusing a route";
                tailf:cli-drop-node-name;
                type uint16 {
                  range "1..20000";
                }
              }
              leaf suppress-penalty {
                description
                  "penalty to start suppressing a route";
                tailf:cli-drop-node-name;
                type uint16 {
                  range "1..20000";
                }
              }
              leaf max-suppress-penalty {
                description
                  "Maximum duration to suppress a stable route";
                tailf:cli-drop-node-name;
                type uint8 {
                  range "1..255";
                }
              }
            }
          }
          container default {
            container interface {
              description
                "SPAN source interface";
              tailf:cli-diff-dependency "/ios:native/interface";
              uses interface-grouping;
            }
          }
          container extcomm-list {
            description
              "Set BGP/VPN extended community list (for deletion)";
            list ext-range {
              tailf:cli-drop-node-name;
              tailf:cli-suppress-mode;
              key "comm-list-num";
              leaf comm-list-num {
                description
                  "Extended community-list number (expanded)";
                type uint16 {
                  range "1..500";
                }
              }
              leaf delete {
                description
                  "Delete matching extended communities";
                type empty;
              }
            }
            list excomm-list-name {
              tailf:cli-drop-node-name;
              tailf:cli-suppress-mode;
              key "name";
              leaf name {
                description
                  "extcommunity-list name";
                type string;
              }
              leaf delete {
                type empty;
              }
            }
          }
          // route-map * / set extcommunity
          container extcommunity {
            description
              "BGP extended community attribute";
            container cost {
              description
                "Cost extended community";
              uses route-map-community-grouping;
              container igp {
                description
                  "Compare following IGP cost comparison";
                uses route-map-community-grouping;
              }
              container pre-bestpath {
                description
                  "Compare before all other steps in bestpath calculation";
                uses route-map-community-grouping;
              }
            }
            container rt {
              description
                "Route Target extended community";
              tailf:cli-compact-syntax;
              leaf-list asn-nn {
                tailf:cli-drop-node-name;
                tailf:cli-flat-list-syntax;
                type asn-ip-type;
              }
              leaf additive {
                type empty;
              }
              container range {
                description
                  "Specify a range of extended community";
                tailf:cli-sequence-commands;
		tailf:cli-compact-syntax;
                leaf lower-limit {
                  description
                    "VPN extended community lower limit";
                  type asn-ip-type;
                }
                leaf high-limit {
                  description
                    "VPN extended community high limit";
                  type asn-ip-type;
                }
                leaf additive {
                  description
                    "Add to the existing extcommunity";
                  type empty;
                }
              }
            }
            container soo {
              description
                "Site-of-Origin extended community";
              leaf asn-nn {
                tailf:cli-drop-node-name;
                tailf:cli-diff-dependency "../../rt/asn-nn";
                tailf:cli-diff-dependency "../../rt/additive";
                type asn-ip-type;
              }
            }
            container vpn-distinguisher {
              description
                "VPN Distinguisher";
              leaf asn-nn {
                tailf:cli-drop-node-name;
                type asn-ip-type;
              }
              container range {
                description
                  "Specify a range of extended community";
                tailf:cli-sequence-commands;
		tailf:cli-compact-syntax;
                leaf lower-limit {
                  description
                    "VPN extended community lower limit";
                  type asn-ip-type;
                }
                leaf high-limit {
                  description
                    "VPN extended community high limit";
                  type asn-ip-type;
                }
                leaf additive {
                  description
                    "Add to the existing extcommunity";
                  type empty;
                }
              }
            }
          }
          // route-map * / set global
          leaf global {
            type empty;
          }
          // route-map * / set interface
          container interface {
            tailf:cli-diff-dependency "/ios:native/interface";
            uses interface-grouping;
          }
          // route-map * / set ip
          container ip {
            description
              "IP specific information";
            container address {
              description
                "Specify IP address";
              leaf prefix-list {
                description
                  "Specify prefix-list";
                type string;
              }
            }
            container default {
              description
                "Set default information";
              container global {
                description
                  "global routing table";
                uses next-hop-address-grouping;
              }
              uses next-hop-address-grouping;
              container vrf {
                description
                  "VRF name";
                list vrfs {
                  tailf:cli-drop-node-name;
                  tailf:cli-suppress-mode;
                  key "vrf";
                  leaf vrf {
                    description
                      "WORD;;VRF name";
                    type string;
                  }
                  uses next-hop-address-grouping;
                }
              }
            }
            leaf df {
              type uint8 {
                range "0..1";
              }
            }
            container global {
              description
                "global routing table";
              uses next-hop-address-grouping;
            }
            container next-hop {
              description
                "Next hop address";
              choice next-hop-choice {
                leaf address {
                  tailf:cli-drop-node-name;
                  type inet:ipv4-address;
                }
                container dynamic {
                  description
                    "application dynamically sets next hop";
                  leaf dhcp {
                    description
                      "DHCP learned next hop";
                    type empty;
                  }
                }
                container encapsulate {
                  description
                    "Encapsulation profile for VPN nexthop";
                  leaf l3vpn {
                    description
                      "L3VPN";
                    type string;
                  }
                }
                leaf peer-address {
                  description
                    "Use peer address (for BGP only)";
                  type empty;
                }
                container recursive {
                  description
                    "Recursive next-hop";
                  leaf ipv4 {
                    description
                      "IP address of recursive next hop";
                    tailf:cli-drop-node-name;
                    type inet:ipv4-address;
                  }
                  leaf global {
                    description
                      "IP address of recursive next hop";
                    type inet:ipv4-address;
                  }
                  container vrf {
                    description
                      "VRF name";
                    list vrfs {
                      tailf:cli-drop-node-name;
                      tailf:cli-suppress-mode;
                      key "vrf";
                      leaf vrf {
                        description
                          "VRF name";
                        type string;
                      }
                      leaf ipv4 {
                        description
                          "IP address of recursive next hop";
                        tailf:cli-drop-node-name;
                        type inet:ipv4-address;
                      }
                    }
                  }
                }
                leaf self {
                  description
                    "Use self address (for BGP only)";
                  type empty;
                }
                container verify-availability {
                  description
                    "Verify if nexthop is reachable";
                  presence "true";
                  list ipv4 {
                    tailf:cli-drop-node-name;
                    tailf:cli-suppress-mode;
                    key "ipv4";
                    leaf ipv4 {
                      description
                        "IP address of next hop";
                      type inet:ipv4-address;
                    }
                    leaf range {
                      tailf:cli-drop-node-name;
                      type uint16 {
                        range "1..65535";
                      }
                    }
                  }
                }
              }
            }
            container precedence {
              description
                "Set precedence field";
              presence "true";
              leaf precedence-value {
                tailf:cli-drop-node-name;
                type uint8 {
                  range "0..7";
                }
              }
              leaf precedence-fields {
                tailf:cli-drop-node-name;
                type enumeration {
                  enum "critical";
                  enum "flash";
                  enum "flash-override";
                  enum "immediate";
                  enum "internet";
                  enum "network";
                  enum "priority";
                  enum "routine";
                }
              }
            }
            container qos-group {
              description
                "Set QOS Group ID";
              presence "true";
              leaf qos-id {
                tailf:cli-drop-node-name;
                type uint8 {
                  range "0..99";
                }
              }
            }
            container tos {
              description
                "Set type of service field";
              presence "true";
              leaf service-value {
                tailf:cli-drop-node-name;
                type uint8 {
                  range "0..15";
                }
              }
              leaf tos-fields {
                tailf:cli-drop-node-name;
                type enumeration {
                  enum "max-reliability";
                  enum "max-throughput";
                  enum "min-delay";
                  enum "min-monetary-cost";
                  enum "normal";
                }
              }
            }
            container vrf {
              description
                "VRF name";
              list vrfs {
                tailf:cli-drop-node-name;
                tailf:cli-suppress-mode;
                key "vrf";
                leaf vrf {
                  description
                    "WORD;;VRF name";
                  type string;
                }
                uses next-hop-address-grouping;
              }
            }
          }
          // route-map * / set ipv6
          container ipv6 {
            description
              "IPv6 specific information";
            container address {
              description
                "IPv6 address";
              leaf-list prefix-list {
                description
                  "IPv6 prefix-list";
                tailf:cli-flat-list-syntax;
                type string;
              }
            }
            container default {
              description
                "Set default information";
              container global {
                description
                  "global routing table";
                leaf next-hop {
                  description
                    "Next hop along path";
                  type inet:ipv6-address;
                }
              }
              container next-hop {
                description
                  "Next hop along path";
                list ipv6s {
                  tailf:cli-drop-node-name;
                  tailf:cli-suppress-mode;
                  key "ipv6";
                  leaf ipv6 {
                    description
                      "Default next hop IPv6 address";
                    type inet:ipv6-address;
                  }
                }
                leaf next-hop-address {
                  tailf:cli-drop-node-name;
                  type inet:ipv6-address;
                }
              }
              list dvrf {
                tailf:cli-drop-node-name;
                tailf:cli-suppress-mode;
                key "dvrf";
                leaf dvrf {
                  description
                    "VRF name";
                  type string;
                }
                list dvrf0 {
                  tailf:cli-drop-node-name;
                  tailf:cli-suppress-mode;
                  key "dvrf0";
                  leaf dvrf0 {
                    description
                      "VRF name";
                    type string;
                  }
                  leaf next-hop {
                    description
                      "Next hop along path";
                    type empty;
                  }
                }
              }
            }
            container global {
              description
                "global routing table";
              container next-hop {
                description
                  "IPv6 Next hop";
                list nh-ipv6 {
                  tailf:cli-drop-node-name;
                  tailf:cli-suppress-mode;
                  key "nh-ipv6";
                  leaf nh-ipv6 {
                    description
                      "Next hop address";
                    type inet:ipv6-address;
                  }
                  leaf nh-ipv60 {
                    description
                      "Next hop address";
                    tailf:cli-drop-node-name;
                    type inet:ipv6-address;
                  }
                }
                leaf verify-availability {
                  description
                    "Next hop address";
                  type inet:ipv6-address;
                }
              }
            }
            container next-hop {
              description
                "IPv6 Next hop";
              list nha-ipv6 {
                tailf:cli-drop-node-name;
                tailf:cli-suppress-mode;
                key "nha-ipv6";
                leaf nha-ipv6 {
                  description
                    "Next hop address";
                  type inet:ipv6-address;
                }
                list nha-ipv60 {
                  tailf:cli-drop-node-name;
                  tailf:cli-suppress-mode;
                  key "nha-ipv60";
                  leaf nha-ipv60 {
                    description
                      "Next hop address";
                    type inet:ipv6-address;
                  }
                  leaf nh-ipv6 {
                    description
                      "Next hop address";
                    tailf:cli-drop-node-name;
                    type inet:ipv6-address;
                  }
                }
              }
              container encapsulate {
                description
                  "Encapsulation profile for VPN nexthop";
                leaf l3vpn {
                  description
                    "Encapsulation profile name";
                  type string;
                }
              }
              leaf peer-address {
                description
                  "Use peer address (for BGP only)";
                type empty;
              }
              leaf recursive {
                description
                  "IPv6 address of recursive next-hop";
                type inet:ipv6-address;
              }
              container verify-availability {
                description
                  "Verify if nexthop is reachable";
                list va-ipv6 {
                  tailf:cli-drop-node-name;
                  tailf:cli-suppress-mode;
                  key "va-ipv6";
                  leaf va-ipv6 {
                    description
                      "Next hop address";
                    type inet:ipv6-address;
                  }
                  leaf seq-nh {
                    description
                      "Sequence to insert into next-hop list";
                    tailf:cli-drop-node-name;
                    type uint16 {
                      range "1..65535";
                    }
                  }
                }
              }
            }
            leaf precedence {
              description
                "Precedence value";
              type uint8 {
                range "0..7";
              }
            }
            list bvrf {
              tailf:cli-drop-node-name;
              tailf:cli-suppress-mode;
              key "bvrf";
              leaf bvrf {
                description
                  "VRF name";
                type string;
              }
              list bvrf0 {
                tailf:cli-drop-node-name;
                tailf:cli-suppress-mode;
                key "bvrf0";
                leaf bvrf0 {
                  description
                    "VRF name";
                  type string;
                }
                container next-hop {
                  description
                    "IPv6 Next hop";
                  leaf bipv6 {
                    description
                      "Next hop address";
                    tailf:cli-drop-node-name;
                    type inet:ipv6-address;
                  }
                  leaf verify-availability {
                    description
                      "Verify if nexthop is reachable";
                    type empty;
                  }
                }
              }
            }
          }
          // route-map * / set level
          container level {
            description
              "Where to import route";
            leaf level-1 {
              description
                "Import into a level-1 area";
              type empty;
            }
            leaf level-1-2 {
              description
                "Import into level-1 and level-2";
              type empty;
            }
            leaf level-2 {
              description
                "Import into level-2 sub-domain";
              type empty;
            }
            leaf nssa-only {
              description
                "Import only into OSPF NSSA areas and don't propagate";
              type empty;
            }
          }
          // route-map * / set lisp
          container lisp {
            description
              "Locator ID Separation Protocol specific information";
            leaf locator-set {
              description
                "The name of the locator set";
              type string;
            }
          }
          leaf local-preference {
            description
              "Preference value";
            type uint32 {
              range "0..4294967295";
            }
          }
          // route-map * / set metric
          leaf metric {
            description
              "Metric value for destination routing protocol";
            type string;
          }
          leaf metric-type {
            description
              "Type of metric for destination routing protocol";
            type enumeration {
              enum "external";
              enum "internal";
              enum "type-1";
              enum "type-2";
            }
          }
          leaf mpls-label {
            description
              "Set MPLS label for prefix";
            type empty;
          }
          // route-map * / set weight
          leaf weight {
            description
              "BGP weight for routing table";
            type uint32 {
              range "0..65535";
            }
          }
          // route-map * / set origin
          container origin {
            description
              "BGP origin code";
            leaf origin-value {
              tailf:cli-drop-node-name;
              type enumeration {
                enum "igp" {
                  tailf:code-name "origin_igp";
                }
                enum "incomplete" {
                  tailf:code-name "origin_incomplete";
                }
              }
            }
            leaf egp {
              description
                "remote EGP";
              type uint32 {
                range "0..65535";
              }
            }
          }
          container tag {
            description
              "Tag value for destination routing protocol";
            leaf tag-val {
              description
                "Tag value";
              tailf:cli-drop-node-name;
              type uint32 {
                range "0..4294967295";
              }
            }
            leaf tag-ipv4 {
              description
                "Tag value(dotted decimal format)";
              tailf:cli-drop-node-name;
              type inet:ipv4-address;
            }
          }
          leaf traffic-index {
            description
              "Bucket number";
            type uint8 {
              range "1..64";
            }
          }
          leaf vrf {
            description
              "VPN Routing/Forwarding instance name";
            type string;
          }
        }
        // route-map * / match
        container match {
          description
            "Match values from routing table";
          container additional-paths {
            description
              "BGP Add-Path match policies";
            container advertise-set {
              description
                "BGP Add-Path advertise-set policy";
              container all {
                description
                  "BGP Add-Path advertise all paths";
                presence "true";
                leaf best {
                  description
                    "BGP Add-Path best n paths to advertise";
                  type uint8 {
                    range "1..3";
                  }
                }
                leaf best-range {
                  description
                    "BGP Add-Path best paths to advertise (lower limit)";
                  type uint8 {
                    range "1..3";
                  }
                }
                container group-best {
                  description
                    "BGP Add-Path advertise group-best path";
                  presence "true";
                  leaf best {
                    description
                      "BGP Add-Path advertise best n paths";
                    type empty;
                  }
                  leaf best-range {
                    description
                      "BGP Add-Path advertise best paths (range m to n)";
                    type empty;
                  }
                }
              }
              container best {
                description
                  "BGP Add-Path advertise best n paths";
                list best-range {
                  tailf:cli-drop-node-name;
                  tailf:cli-suppress-mode;
                  key "best-range";
                  leaf best-range {
                    description
                      "BGP Add-Path best n paths to advertise";
                    type uint8 {
                      range "1..3";
                    }
                  }
                  leaf all {
                    description
                      "BGP Add-Path advertise all paths";
                    type empty;
                  }
                  leaf group-best {
                    description
                      "BGP Add-Path advertise group-best path";
                    type empty;
                  }
                }
              }
              container best-range {
                description
                  "BGP Add-Path advertise best paths (range m to n)";
                list adv-path {
                  tailf:cli-drop-node-name;
                  tailf:cli-suppress-mode;
                  key "adv-path";
                  leaf adv-path {
                    description
                      "BGP Add-Path best paths to advertise (lower limit)";
                    type uint8 {
                      range "1..3";
                    }
                  }
                  leaf adv-path0 {
                    description
                      "BGP Add-Path best paths to advertise (upper limit)";
                    tailf:cli-drop-node-name;
                    type uint8 {
                      range "1..3";
                    }
                  }
                }
              }
              container group-best {
                description
                  "BGP Add-Path advertise group-best path";
                presence "true";
                leaf all {
                  description
                    "BGP Add-Path advertise all paths";
                  type empty;
                }
                leaf best {
                  description
                    "BGP Add-Path best n paths to advertise";
                  type uint8 {
                    range "1..3";
                  }
                }
                leaf best-range {
                  description
                    "BGP Add-Path best paths to advertise (lower limit)";
                  type uint8 {
                    range "1..3";
                  }
                }
              }
            }
          }
          container as-path {
            description
              "Match BGP AS path list";
            leaf-list access-list {
              description
                "AS path access-list";
              tailf:cli-drop-node-name;
              tailf:cli-flat-list-syntax;
              type uint16 {
                range "1..500";
              }
            }
          }
          // route-map * / match clns
          container clns {
            description
              "CLNS information";
            leaf-list name {
              description
                "Named clna list";
              tailf:cli-drop-node-name;
              tailf:cli-flat-list-syntax;
              type string;
            }
          }
          // route-map * / match community
          container community {
            description
              "Match BGP community list";
            leaf-list name {
              description
                "Named Access List";
              tailf:cli-drop-node-name;
              tailf:cli-flat-list-syntax;
              type string;
            }
          }
          // route-map * / match extcommunity
          container extcommunity {
            description
              "Match BGP/VPN extended community list";
            leaf-list name {
              description
                "Named Access List";
              tailf:cli-drop-node-name;
              tailf:cli-flat-list-syntax;
              type string;
            }
          }
          // route-map * / match interface
          container interface {
            description
              "SPAN source interface";
            tailf:cli-diff-dependency "/ios:native/interface";
            leaf-list interface {
              tailf:cli-drop-node-name;
              tailf:cli-flat-list-syntax;
              tailf:cli-full-command;
              type string;
            }
          }
          // route-map * / match ip
          container ip {
            description
              "IP specific information";
            container address {
              description
                "Match address of route or match packet";
              uses ip-access-list-grouping;
            }
            container flowspec {
              description
                "Match address of route";
              container dest-pfx {
                description
                  "Match dest prefix component of flowspec prefix";
                uses ip-access-list-grouping;
              }
              container src-pfx {
                description
                  "Match source prefix component of flowspec prefix";
                uses ip-access-list-grouping;
              }
            }
            container next-hop {
              description
                "Match next-hop address of route";
              uses ip-access-list-grouping;
            }
            container redistribution-source {
              description
                "route redistribution source (EIGRP only)";
              uses ip-access-list-grouping;
            }
            container route-source {
              description
                "Match advertising source address of route";
              uses ip-access-list-grouping;
            }
          }
          // route-map * / match ipv6
          container ipv6 {
            description
              "IPv6 specific information";
                //next-hop
                //route-source
            container address {
              description
                "Match address of route";
              uses ipv6-access-list-grouping;
            }
            container flowspec {
              description
                "Match address of route";
              container dest-pfx {
                description
                  "Match dest prefix component of flowspec prefix";
                uses ipv6-access-list-grouping;
              }
              container src-pfx {
                description
                  "Match source prefix component of flowspec prefix";
                uses ipv6-access-list-grouping;
              }
            }
            container next-hop {
              description
                "Match next-hop address of route";
              uses ipv6-access-list-grouping;
            }
            container route-source {
              description
                "Match advertising source address of route";
              uses ipv6-access-list-grouping;
            }
          }
          //route-map * / match length
          container length {
            description
              "Packet length";
            list lengths {
              tailf:cli-drop-node-name;
              tailf:cli-suppress-mode;
              key "min-len max-len";
              leaf min-len {
                description
                  "Minimum packet length";
                tailf:cli-drop-node-name;
                type uint32 {
                  range "0..2147483647";
                }
              }
              leaf max-len {
                description
                  "Maximum packet length";
                tailf:cli-drop-node-name;
                type uint32 {
                  range "0..2147483647";
                }
              }
            }
          }
          container local-preference {
            description
              "Local preference for route";
            leaf-list values {
              tailf:cli-drop-node-name;
              type string;
            }
          }
          container mdt-group {
            description
              "Match routes corresponding to MDT group";
            leaf-list name {
              description
                "IP Access List";
              tailf:cli-drop-node-name;
              tailf:cli-flat-list-syntax;
              type string;
            }
          }
          // route-map * / match metric
          container metric {
            description
              "Match metric of route";
            leaf metric-value {
              tailf:cli-drop-node-name;
              type string;
            }
            leaf external {
              description
                "match route using external protocol metric";
              type string;
            }
          }
          leaf mpls-label {
            description
              "Match routes which have MPLS labels";
            type empty;
          }
          container policy-list {
            description
              "Match IP policy list";
            leaf-list policy-map-names {
              description
                "IP Policy map name";
              tailf:cli-drop-node-name;
              tailf:cli-flat-list-syntax;
              type string;
            }
          }
          container route-type {
            description
              "Match route-type of route";
            container external {
              description
                "external route (BGP, EIGRP and OSPF type 1/2)";
              presence "true";
              leaf type-1 {
                description
                  "OSPF external type 1 route";
                type empty;
              }
              leaf type-2 {
                description
                  "OSPF external type 2 route";
                type empty;
              }
            }
            leaf internal {
              description
                "internal route (including OSPF intra/inter area)";
              type empty;
            }
            leaf level-1 {
              description
                "IS-IS level-1 route";
              type empty;
            }
            leaf level-2 {
              description
                "IS-IS level-2 route";
              type empty;
            }
            leaf local {
              description
                "locally generated route";
              type empty;
            }
            container nssa-external {
              description
                "nssa-external route (OSPF type 1/2)";
              presence "true";
              leaf type-1 {
                description
                  "OSPF external type 1 route";
                type empty;
              }
              leaf type-2 {
                description
                  "OSPF external type 2 route";
                type empty;
              }
            }
          }
          container rpki {
            description
              "Match RPKI state of route";
            leaf invalid {
              description
                "RPKI Invalid State";
              type empty;
            }
            leaf not-found {
              description
                "RPKI Not Found State";
              type empty;
            }
            leaf valid {
              description
                "RPKI Valid State";
              type empty;
            }
          }
          container source-protocol {
            description
              "Match source-protocol of route";
            presence "true";
            leaf-list bgp {
              description
                "Border Gateway Protocol (BGP)";
              tailf:cli-flat-list-syntax;
              type bgp-as-number-type;
            }
            leaf connected {
              description
                "Connected";
              type empty;
            }
            leaf-list eigrp {
              description
                "Border Gateway Protocol (BGP)";
              tailf:cli-flat-list-syntax;
              type string;
            }
            leaf isis {
              description
                "ISO IS-IS";
              type empty;
            }
            leaf lisp {
              description
                "Locator ID Separation Protocol (LISP)";
              type empty;
            }
            leaf mobile {
              description
                "Mobile routes";
              type empty;
            }
            leaf-list ospf {
              description
                "Open Shortest Path First (OSPF)";
              tailf:cli-flat-list-syntax;
              type string;
            }
            leaf-list ospfv3 {
              description
                "OSPFv3";
              tailf:cli-flat-list-syntax;
              type string;
            }
            leaf rip {
              description
                "Routing Information Protocol (RIP)";
              type empty;
            }
            leaf static {
              description
                "Static routes";
              type empty;
            }
          }
          container tag {
            description
              "Match tag of route";
            leaf-list tag_value {
              description
                "Tag value";
              tailf:cli-flat-list-syntax;
              tailf:cli-drop-node-name;
              type uint32 {
                range "0..4294967295";
              }
            }
            leaf-list ipv4-address {
              description
                "<A.B.C.D>;;Tag value(dotted decimal format)";
              tailf:cli-drop-node-name;
              tailf:cli-flat-list-syntax;
              type inet:ipv4-address;
            }
            container list {
              description
                "Route Tag List";
              leaf-list tag-names {
                tailf:cli-drop-node-name;
                tailf:cli-list-syntax;
                description
                  "Tag list name";
                type string;
              }
            }
          }
          leaf track {
            description
              "tracking object";
            type uint16 {
              range "1..1000";
            }
          }
        }
      }
    }

    /// ========================================================================
    /// route-tag 
    /// ========================================================================
    container route-tag {
      container list {
        list rt-name {
          tailf:cli-drop-node-name;
          tailf:cli-suppress-mode;
          key "rt-name";
          leaf rt-name {
            type string;
          }
          container deny {
            list ipv4 {
              tailf:cli-drop-node-name;
              tailf:cli-suppress-mode;
              key "ipv4";
              leaf ipv4 {
                type inet:ipv4-address;
              }
              leaf mask {
                tailf:cli-drop-node-name;
                type inet:ipv4-address;
              }
            }
          }
          container permit {
            list ipv4 {
              tailf:cli-drop-node-name;
              tailf:cli-suppress-mode;
              key "ipv4";
              leaf ipv4 {
                type inet:ipv4-address;
              }
              leaf mask {
                tailf:cli-drop-node-name;
                type inet:ipv4-address;
              }
            }
          }
          container seq {
            list seq-num {
              tailf:cli-drop-node-name;
              tailf:cli-suppress-mode;
              key "seq-num";
              leaf seq-num {
                type uint32 {
                  range "1..4294967294";
                }
              }
              container deny {
                tailf:cli-compact-syntax;
                leaf ipv4 {
                  tailf:cli-drop-node-name;
                  type inet:ipv4-address;
                }
                leaf mask {
                  tailf:cli-drop-node-name;
                  type inet:ipv4-address;
                }
              }
              container permit {
                tailf:cli-compact-syntax;
                leaf ipv4 {
                  tailf:cli-drop-node-name;
                  type inet:ipv4-address;
                }
                leaf mask {
                  tailf:cli-drop-node-name;
                  type inet:ipv4-address;
                }
              }
            }
          }
        }
      }
      container notation {
        leaf dotted-decimal {
          type empty;
        }
      }
    }


    /// ========================================================================
    /// authentication
    /// ========================================================================
    container authentication {
      description
        "Auth Manager Global Configuration Commands";
      container command{
        description "Allow the following CoA commands to be ignored by the switch";
        container bounce-port { 
          description "CoA bounce-port command";
          leaf ignore {
            description "ignore disable-port CoA command";
            type empty;
          }
        }
        container disable-port {
          description "CoA disable-port command";
          leaf ignore {
            description "";
            type empty;
          }
        }
      }    
      container critical {
        description
          "Set Critical Authentication parameters";
        container recovery {
          description
            "Set Critical Authentication Recovery parameters";
          leaf delay {
            description
              "Set Critical Authentication Recovery Delay period";
            type uint32 {
              range "1..10000";
            }
          }
        }
      }
      container mac-move {
        description
          "Set required action when a MAC move is detected";
        leaf permit {
          description
            "PERMIT MAC moves (clears existing session)";
          type empty;
        }
      }
    }

    /// ========================================================================
    /// banner
    /// ========================================================================
    container banner {
      description
        "Define a login banner";
      container exec {
        description
          "Set EXEC process creation banner";
        tailf:cli-sequence-commands {
          tailf:cli-reset-siblings;
        }
        tailf:cli-compact-syntax;
        leaf start-marker {
          tailf:cli-drop-node-name;
          type string;
        }
        leaf message {
          tailf:cli-drop-node-name;
          type string;
        }
        leaf end-marker {
          tailf:cli-drop-node-name;
          type string;
          must "../end-marker = ../start-marker" {
            tailf:dependency "../start-marker";
          }
        }
      }
      container login {
        description
          "Set login banner";
        tailf:cli-sequence-commands {
          tailf:cli-reset-siblings;
        }
        tailf:cli-compact-syntax;
        leaf start-marker {
          tailf:cli-drop-node-name;
          type string;
        }
        leaf message {
          tailf:cli-drop-node-name;
          type string;
        }
        leaf end-marker {
          tailf:cli-drop-node-name;
          type string;
          must "../end-marker = ../start-marker" {
            tailf:dependency "../start-marker";
          }
        }
      }
      container prompt-timeout {
        description
          "Set Message for login authentication timeout";
        tailf:cli-sequence-commands {
          tailf:cli-reset-siblings;
        }
        tailf:cli-compact-syntax;
        leaf start-marker {
          tailf:cli-drop-node-name;
          type string;
        }
        leaf message {
          tailf:cli-drop-node-name;
          type string;
        }
        leaf end-marker {
          tailf:cli-drop-node-name;
          type string;
          must "../end-marker = ../start-marker" {
            tailf:dependency "../start-marker";
          }
        }
      }
      container motd {
        description
          "Set Message of the Day banner";
        tailf:cli-sequence-commands {
          tailf:cli-reset-siblings;
        }
        tailf:cli-compact-syntax;
        leaf start-marker {
          tailf:cli-drop-node-name;
          type string;
        }
        leaf message {
          tailf:cli-drop-node-name;
          type string;
        }
        leaf end-marker {
          tailf:cli-drop-node-name;
          type string;
          must "../end-marker = ../start-marker" {
            tailf:dependency "../start-marker";
          }
        }
      }
    }

    /// ========================================================================
    /// table-map
    /// ========================================================================
    // Note: Must come before policer aggregate
    list table-map {
      description
        "Configure Table Map";
      tailf:cli-mode-name "config-tablemap";
      key "name";
      leaf name {
        type string;
      }
      leaf default {
        description
          "the default behavior for setting value not found in the table map";
        type union {
          type uint8 {
            range "0..63";
          }
          type enumeration {
            enum "copy";
            enum "ignore";
          }
        }
      }
      // table-map * / map from * to *
      list map {
        description
          "map to_value from from_value";
        tailf:cli-compact-syntax;
        tailf:cli-reset-container;
        tailf:cli-suppress-mode;
        tailf:cli-delete-when-empty;
        key "from to";
        leaf from {
          description
            "map from value";
          tailf:cli-expose-key-name;
          type uint8 {
            range "0..63";
          }
        }
        leaf to {
          description
            "map to value";
          tailf:cli-expose-key-name;
          type uint8 {
            range "0..63";
          }
        }
      }
    }

    /// ========================================================================
    /// sdm
    /// ========================================================================
    container sdm {
      description
        "Switch database management";
      container prefer {
        description
          "Config TCAM and ASIC RAM size. Warning: need to reset switch for configuration to take effect";
        tailf:cli-delete-when-empty;
        presence "true";
        choice sdm-prefer-choice {
          leaf default {
            type empty;
          }
          leaf qos {
            type empty;
          }
        }
      }
    }

    /// =======================================================================
    /// diagnostic
    /// ========================================================================
    container diagnostic {
      description
        "Configure diagnostic information";
      container bootup {
        description
          "Configure diagnostic for bootup";
        leaf level {
          description 
            "Select diagnostic level";
          type enumeration {
	    enum "complete";
	    enum "minimal";
	  }
        }
      }
      container event-log {
        description
          "Configure diagnostic event log";
        leaf size {
          description
            "Configure event log size
            Number of entries <1-10000>";
          type uint16 {
            range "1..10000";
          }
        }
      }
      container monitor {
        description
          "Configure diagnostic monitoring tests";
        container interval {
          description
            "Configure diagnostic monitoring tests interval";
          container switch {
            description
              "Configure diagnostic monitoring tests interval on selected switch";
	    list switch {
	      description
	        "Configure diagnostic monitoring tests on selected switch";
	      tailf:cli-sequence-commands;
	      tailf:cli-compact-syntax;
	      key "number";
	      leaf number {
                description
                  "switch number";
	        type uint8 {
	    	  range "1..9";
	        } 
	      }	
              container test {
                description
                  "Diagnostic test selection
                   Diagnostics test suite attributes:
                   M/C/* - Minimal bootup level test / Complete bootup level test / NA
                   B/* - Basic ondemand test / NA
                   P/V/* - Per port test / Per device test / NA
                   D/N/* - Disruptive test / Non-disruptive test / NA
                   S/* - Only applicable to standby unit / NA
                   X/* - Not a health monitoring test / NA
                   F/* - Fixed monitoring interval test / NA
                   E/* - Always enabled monitoring test / NA
                   A/I - Monitoring is active / Monitoring is inactive

                                                                          Test Interval   Thre-
   		   ID   Test Name                          Attributes     day hh:mm:ss.ms shold
 		   ==== ================================  ============   =============== =====
 		   1) DiagGoldPktTest ----------------->  *BPN*X**I       not configured    n/a
  		   2) DiagThermalTest ----------------->  *B*N****A       000 00:01:30.00   5
		   3) DiagFanTest --------------------->  *B*N****A       000 00:01:30.00   5
  		   4) DiagPhyLoopbackTest ------------->  *BPD*X**I       not configured    n/a
 		   5) DiagScratchRegisterTest --------->  *B*N****A       000 00:01:30.00   5
 		   6) DiagPoETest --------------------->  ***D*X**I       not configured    n/a
		   7) DiagStackCableTest -------------->  ***D*X**I       not configured    n/a
   		   8) DiagMemoryTest ------------------>  *B*D*X**I       not configured    n/a ";
                                       
                list test-ids { 
                  tailf:cli-drop-node-name; 
		  tailf:cli-suppress-mode;
		  tailf:cli-sequence-commands;
		  tailf:cli-compact-syntax;
		  key "id";	
	          leaf id {
                    description
                      "Test ID list (e.g. 1,3-6) or Test Name";
                    type string;
 		  }
                  leaf hh-mm-ss {
                    tailf:cli-drop-node-name;
                    description
                      "Monitoring interval in hh:mm:ss format";
                    type hhmmss-type;
                  }
                  leaf milli-seconds {
                    tailf:cli-drop-node-name;
                    description
                      "Number of milli-seconds [0-999]";
                    type uint16 {
                      range "0..999";
                    } 
                  }
                  leaf number-of-days {
                    tailf:cli-drop-node-name;
		    tailf:cli-full-command;
                    description
                      "Number of days [0-20]";
                    type uint16 {
                      range "0..20";
                    }
                  }
	        }
                container all {
                  description 
                    "Select all test ID ";
                  tailf:cli-sequence-commands;
                  tailf:cli-compact-syntax;
                  leaf hh-mm-ss {
                    tailf:cli-drop-node-name;
                    description
                      "Monitoring interval in hh:mm:ss format";
                    type hhmmss-type;
                  }
                  leaf milli-seconds {
                    tailf:cli-drop-node-name;
                    description
                      "Number of milli-seconds [0-999]";
                    type uint16 {
                      range "0..999";
                    } 
                  }
                  leaf number-of-days {
                    tailf:cli-drop-node-name;
		    tailf:cli-full-command;
                    description
                      "Number of days [0-20]";
                    type uint16 {
                      range "0..20";
                    }
                  }
                }// container all
              }   /// container test 
            }   ///  number 1
          }  //switch 
        } //interval
        list switch {
          description
            "Configure diagnostic monitoring tests on selected switch";
          tailf:cli-sequence-commands;
          tailf:cli-compact-syntax;
	  key "number";
	  leaf number{
            description
              "switch number";
            type uint8 {
   	      range "1..9";
	    }
	  }    
          container test {
            description
              "Diagnostic test selection
               Diagnostics test suite attributes:
               M/C/* - Minimal bootup level test / Complete bootup level test / NA
               B/* - Basic ondemand test / NA
               P/V/* - Per port test / Per device test / NA
               D/N/* - Disruptive test / Non-disruptive test / NA
               S/* - Only applicable to standby unit / NA
               X/* - Not a health monitoring test / NA
               F/* - Fixed monitoring interval test / NA
               E/* - Always enabled monitoring test / NA
               A/I - Monitoring is active / Monitoring is inactive
             
               Test                                                      Test Interval  Thre-
   	        ID   Test Name                          Attributes      day hh:mm:ss.ms shold
 	       ==== ================================== ============    =============== =====
 	        1) DiagGoldPktTest -----------------> *BPN*X**I       not configured    n/a
  	        2) DiagThermalTest -----------------> *B*N****A       000 00:01:30.00   5
	        3) DiagFanTest ---------------------> *B*N****A       000 00:01:30.00   5
  	        4) DiagPhyLoopbackTest -------------> *BPD*X**I       not configured    n/a
 	        5) DiagScratchRegisterTest ---------> *B*N****A       000 00:01:30.00   5
 	        6) DiagPoETest ---------------------> ***D*X**I       not configured    n/a
	        7) DiagStackCableTest --------------> ***D*X**I       not configured    n/a
   	        8) DiagMemoryTest ------------------> *B*D*X**I       not configured    n/a ";

	     choice test-id {  
	       leaf id {
	         tailf:cli-drop-node-name;
               description
                 "Test ID list (e.g. 1,3-6) or Test Name";
               type string;
 	     }
             leaf all {
               description 
                 "Select all test ID ";
               type empty;
             }
	   }
         }  /// container test 
       } ///switch
       leaf syslog {	
         description                  
           "Configure diagnostic monitoring syslog";
	 type empty;
       }
       container threshold {
         description
	   "Configure diagnostic monitoring failure threshold";
         list switch {
           description
	     "Configure diagnostic monitoring tests threshold on selected switch";  
	   tailf:cli-sequence-commands;
	   tailf:cli-compact-syntax;
	   key "number";
	   leaf number {
             description
               "switch number";
	     type uint8 {
	       range "1..9";
	     }	
	   }
           container test {
             description
               "Diagnostic test selection
                Diagnostics test suite attributes:
                M/C/* - Minimal bootup level test / Complete bootup level test / NA
                B/* - Basic ondemand test / NA
                P/V/* - Per port test / Per device test / NA
                D/N/* - Disruptive test / Non-disruptive test / NA
                S/* - Only applicable to standby unit / NA
                X/* - Not a health monitoring test / NA
                F/* - Fixed monitoring interval test / NA
                E/* - Always enabled monitoring test / NA
                A/I - Monitoring is active / Monitoring is inactive
 
                                                                       Test Interval  Thres-
   		ID   Test Name                          Attributes    day hh:mm:ss.ms shold
 	       ==== ================================== ============   =============== =====
 		1) DiagGoldPktTest ----------------->  *BPN*X**I       not configured  n/a
  		2) DiagThermalTest ----------------->  *B*N****A       000 00:01:30.00 5
		3) DiagFanTest --------------------->  *B*N****A       000 00:01:30.00 5
  		4) DiagPhyLoopbackTest ------------->  *BPD*X**I       not configured  n/a
 		5) DiagScratchRegisterTest --------->  *B*N****A       000 00:01:30.00 5
 		6) DiagPoETest --------------------->  ***D*X**I       not configured  n/a
		7) DiagStackCableTest -------------->  ***D*X**I       not configured  n/a
   		8) DiagMemoryTest ------------------>  *B*D*X**I       not configured  n/a ";

	      list test-ids { 
                tailf:cli-drop-node-name; 
		tailf:cli-sequence-commands;
		tailf:cli-compact-syntax;
		key "id";	
		leaf id {
                  description
                    "Test ID list (e.g. 1,3-6) or Test Name";
                  type string;
		}
		container failure {
                  description
		    "Setting failure threshold";
                  list count {
                    description
		      "Setting failure threshold count";
		    tailf:cli-sequence-commands;
		    tailf:cli-compact-syntax;
		    key "range";
                    leaf range {                                            
   		      description
			"Number of allowable failures [1-1000]";
                      type uint16 {
                        range "1..1000";
                      }
                    }
                    leaf days {
                      description
			"Set failure history window in days <1-1000000>";
                      type uint32 {
                        range "1..1000000";
                      }
                    }
                    leaf hours {
                      description
			"Set failure history window in hours <1-1000000>";
		      type uint32 {
                        range "1..1000000";
                      }
		    }
                    leaf milli-seconds {
                      description
			"Set failure history window in milli-seconds <15-1000000>";
		      type uint32 {
                        range "15..1000000";
                      }
                    }
                    leaf minutes {
                      description
		        "Set failure history window in minutes";
                      type uint32 {
                        range "1..1000000";
                      }
		    }
                    leaf runs {
                      description
			"Set failure history window in test-run count";
                      type uint16 {
                        range "1..5000";
                      }
		    }
                    leaf seconds {
                      description
			"Set failure history window in seconds";
                      type uint32 {
                        range "1..1000000";
                      } // type
		    } //leaf seconds
		  }// count
		} // failure
 	      } /// test ids
	      container all {
                description 
                  "Select all test ID ";
                tailf:cli-sequence-commands;
                tailf:cli-compact-syntax;
		container failure {
                  description
		    "Setting failure threshold";
                  list count {
                    description
		      "Setting failure threshold count";
		    tailf:cli-sequence-commands;
		    tailf:cli-compact-syntax;
		    key "range";
                    leaf range {                                             
   		      description
			"Number of allowable failures [1-1000]";
                      type uint16 {
                        range "1..1000";
                      }
                    }
                    leaf days {
                      description
			"Set failure history window in days";
                      type uint32 {
                        range "1..1000000";
                      }
		    }
                    leaf hours {
                      description
			"Set failure history window in hours";
		      type uint32 {
                        range "1..1000000";
                      }
                    }
                    leaf milli-seconds {
                      description
			"Set failure history window in milli-seconds";
		      type uint32 {
                        range "15..1000000";
                      }
		    }
                    leaf minutes {
                      description
			"Set failure history window in minutes";
                      type uint32 {
                        range "1..1000000";
                      }
                    }
                    leaf runs {
                      description
			"Set failure history window in test-run count";
		      type uint16 {
                        range "1..5000";
                      }
		    }
		    leaf seconds {
                      description
			"Set failure history window in seconds";
                      type uint32 {
                        range "1..1000000";
                      }
		    }
		  } // list count
		} // failure
	      }// container all
	    }// test
          } // list switch
	} /// threshold
      } /// monitor
      //// diagnostic schedule
      container schedule {
        description
          "Configure diagnostic schedule for a card";
        list switch {
          description
            "Configure diagnostic monitoring tests interval on selected switch";
	  tailf:cli-sequence-commands;
	  tailf:cli-compact-syntax;
          key "switch-number";
          leaf switch-number {
            description
              "switch number";
	    type uint8 {
	      range "1..9";
	    }
	  }
          container test {
            description
              "Diagnostic test selection
               Diagnostics test suite attributes:
               M/C/* - Minimal bootup level test / Complete bootup level test / NA
               B/* - Basic ondemand test / NA
               P/V/* - Per port test / Per device test / NA
               D/N/* - Disruptive test / Non-disruptive test / NA
               S/* - Only applicable to standby unit / NA
               X/* - Not a health monitoring test / NA
               F/* - Fixed monitoring interval test / NA
               E/* - Always enabled monitoring test / NA
               A/I - Monitoring is active / Monitoring is inactive
                                                                       Test Interval   Thre-
  	       ID   Test Name                          Attributes      day hh:mm:ss.ms shold
 	      ==== ================================== ============    ===============  =====
	       1)   DiagGoldPktTest -----------------> *BPN*X**I       not configured   n/a
 	       2)   DiagThermalTest -----------------> *B*N****A       000 00:01:30.0   5
 	       3)   DiagFanTest ---------------------> *B*N****A       000 00:01:30.00  5
	       4)   DiagPhyLoopbackTest -------------> *BPD*X**I       not configured   n/a
  	       5)   DiagScratchRegisterTest ---------> *B*N****A       000 00:01:30.00  5
   	       6)   DiagPoETest ---------------------> ***D*X**I       not configured   n/a
  	       7)   DiagStackCableTest --------------> ***D*X**I       not configured   n/a
   	       8)   DiagMemoryTest ------------------> *B*D*X**I       not configured   n/a " ;
                                
            list test-ids { 
              tailf:cli-drop-node-name; 
	      tailf:cli-sequence-commands;
	      tailf:cli-compact-syntax;    
 	      key "id";	
	      leaf id {
                description
                  "Test ID list (e.g. 1,3-6) or Test Name";
                type string;
	      }
	      uses diagnostic-daily-on-weekly;
	      uses diagnostic-schedule-port;
	    } // list test id over
	    container all {
	      description 
                "Select all test ID ";   
	      uses diagnostic-daily-on-weekly;
	      uses diagnostic-schedule-port;
	    }  // container all
	    container basic {
	      description
	        "Select the Basic ondemand test suite [Attribute = B]";
	      uses diagnostic-daily-on-weekly;
	      uses diagnostic-schedule-port;		        
	    }  // container basic
	    container complete {
	      description
	        "Select the Complete bootup test suite [Attribute = C]";	
	      uses diagnostic-daily-on-weekly;			  
	    }  // complete 
	    container minimal {
	      description
	        "Select the Minimal bootup test suite [Attribute = M]";
	      uses diagnostic-daily-on-weekly;
	    }  // minimal
	    container non-disruptive {
	      description
	        "Select the Non-Disruptive test suite [Attribute = N]";
	      uses diagnostic-daily-on-weekly;
	      uses diagnostic-schedule-port;
	    }  // non-disruptive
	    container per-port {
	      description
	        "Select the Per-Port test suite [Attribute = P]";
	      uses diagnostic-daily-on-weekly;
	      uses diagnostic-schedule-port;
	    } // per-port
	  }   // test
        }     // list switch
      }       // container schedule
    }         // diagnostic 

    /// ========================================================================
    /// switch
    /// ========================================================================
    list switch {
      description
        "Config commands for the switches in the stack";
      tailf:cli-suppress-mode;
      key "number";
      leaf number {
        type uint8 {
          range "1..9";
        }
      }
      leaf provision {
        description
          "Configure Switch provision / offline config";
        type enumeration {
          enum "ws-c2960x-24pd-l";
          enum "ws-c3650-48ps";
          enum "ws-c3650-24ps";
          enum "ws-c3850-48p";
          enum "ws-c3850-24p";
          enum "ws-c3850-48t";
          enum "ws-c3850-24t";
          enum "ws-c3850-48f";
          enum "ws-c3850-48u";
          enum "ws-c3850-24u";
          enum "ws-c3850-12x48u";
          enum "ws-c3850-24xu";
          enum "ws-c3850-24ux";
          enum "ws-c3850-12s";
          enum "ws-c3850-24s";
          enum "ws-c3850-12xs";
          enum "ws-c3850-24xs";
          enum "ws-c3850-48xs";
          enum "ws-c3650-12x48fd";
          enum "ws-c3650-12x48uq";
          enum "ws-c3650-12x48ur";
          enum "ws-c3650-12x48uz";
          enum "ws-c3650-24pd";
          enum "ws-c3650-24pdm";
          enum "ws-c3650-24td";
          enum "ws-c3650-24ts";
          enum "ws-c3650-48fqm";
          enum "ws-c3650-48pd";
          enum "ws-c3650-48pq";
          enum "ws-c3650-48td";
          enum "ws-c3650-48tq";
          enum "ws-c3650-48ts";
          enum "ws-c3650-8x24pd";
          enum "ws-c3650-8x24uq";
          enum "ws-c3750x-24p";
          enum "ws-c3750x-12s";
          enum "ws-c3850-12x48au";
          enum "ws-c3850x-24p";
          enum "ws-c3850x-24t";
          enum "ws-c3850x-24u";
          enum "ws-c3850x-48p";
          enum "ws-c3850x-48t";
          enum "ws-c3850x-48u";
        }
      }
    }
    list switch-virtual {
      tailf:alt-name "switch";
      key "domain";
      leaf domain {
        type uint32;
      }
      leaf virtual {
        tailf:alt-name "virtual domain";
        tailf:cli-prefix-key;
        type empty;
      }
      container switch {
        description "Configure switch command";
        tailf:cli-compact-syntax;
        leaf switch-number{
          description "Virtual switch number";
          tailf:cli-drop-node-name;
          type uint32 {
            range "1..2";
          }
        }
        leaf priority {
          description "Virtual switch priority value";
          type uint32;
        }
        leaf mode {
          type enumeration {
            enum "virtual";
          }
        }
      }
      container mac-address {
        leaf use-virtual {
          type empty;
        }
      }
      container dual-active {
        description "Virtual switch dual-active config";
        container recovery {
          description "Recovery IP address";
          tailf:cli-sequence-commands;
          tailf:cli-compact-syntax;
          leaf switch {
            description "Switch ID for recovery IP address";
            type uint8 {
              range "1..2";
            }
          }
          container ip {
            description "Recovery IP address";
            tailf:cli-sequence-commands;
            tailf:cli-compact-syntax;
            leaf address {
              description "Recovery IP address";
              type inet:ipv4-address;
            }
            leaf mask {
              description "IP address mask";
              tailf:cli-drop-node-name;
              type inet:ipv4-address;
            }
          }
        }
        container detection {
          description "Dual-active detection enable";
          container pagp  {
            description "Dual-active detection using PAgP";
            presence true;
            container trust {
              description "Trusted channels for PAgP dual-active detection";
              leaf channel-group {
                description "Etherchannel/port bundle to be used for pagp dual-active detection";
                type uint8 {
                  range "1..254";
                }
              }
            }
          }
        }
      }
    }

    /// ========================================================================
    /// stack-mac
    /// ========================================================================
    container stack-mac {
      description
        "Global stack mac-address feature configurations";
      container persistent {
        description
          "persistent stack mac-address";
        leaf timer {
          description
            "use stack mac-address timer after master failure( 0 means still using the current MAC)";
          type uint8 {
            range "0..60";
          }
        }
      }
    }

    /// ========================================================================
    /// acr
    /// ========================================================================
    list acr {
      description
        "ACR";
      tailf:cli-suppress-mode;
      key "number";
      leaf number {
        type uint8;
      }
      leaf type {
        tailf:cli-hide-in-submode;
        type enumeration {
          enum "CH-OC3";
        }
      }
    }

    /// ========================================================================
    /// mls
    /// ========================================================================
    // Note: must come before class-map and policy-map.
    container mls {
      description
        "mls global commands";
      tailf:cli-incomplete-no;
      container acl {
        description
          "MLS ACL operation";
        container tcam {
          description
            "ACL TCAM";
          leaf default-result {
            description
              "Default result to be used during tcam programming";
            type enumeration {
              enum "bridge";
              enum "deny";
              enum "permit";
            }
          }
          container log-update {
            description
              "Log TCAM updates";
            presence "true";
            leaf rate-limit-msg {
              description
                "Enable/Disable syslog ratelimiting";
              type enumeration {
                enum "disable";
                enum "enable";
              }
            }
          }
          leaf share-global {
            description
              "share global deny or permit any entries";
            tailf:cli-boolean-no;
            tailf:cli-trim-default;
            type boolean;
          }
        }
      }
      //  aging       L3 aging
      // mls cef
      container cef {
        description
          "cef keyword";
        container error {
          leaf action {
            type enumeration {
              enum "reset";
            }
          }
        }
        //  maximum-routes  Configure route allocation for protocols
        //  tunnel          Allow tunnel fragmentation
      }
      //  erm         FIB Exception Recovery Manager
      //  exclude     exclude keyword

      // mls flow
      container flow {
        description
          "flowmask keyword";
        leaf ip {
          description
            "flowmask ip keyword";
          type enumeration {
            enum "interface-destination";
            enum "interface-destination-source";
            enum "interface-full";
            enum "interface-source";
          }
        }
      }
      // mls ip
      container ip {
        description
          "ip keyword";
        container multicast {
          description
            "multicast keyword";
              //  cef        cef keyword
              //  inspect    inspect

              // mls ip multicast
          tailf:cli-display-separated;
          presence "true";
          //  bidir              Bidir commands
          //  connected          Enable download of interface/mask entry
          container consistency-check {
            description
              "Set consistency checking characteristics";
            presence "true";
            leaf settle-time {
              description
                "Settle time for entry/oif for consistancy-checker";
              type uint16 {
                range "2..3600";
              }
            }
            //  type         Set consistency checker type
          }
          //  egress             Set egress replication options
          leaf flow-stat-timer {
            description
              "timer for flow statistic used by mls-msc and mlsm";
            type uint8 {
              range "1..100";
            }
          }
          //  met-optimization   Enable or disable met optimisation
          //  non-rpf            Enable rate-limiting of non-RPF traffic
          //  replication-mode   Disable auto-detection mode for egress
          //  sso                Stateful switchover parameters
          //  threshold          Threshold rate for installing h/w shortcuts
        }
        //  nat        nat keyword
        //  slb        Server Load Balancing
      }
      //  nde         netflow data export (nde) keyword
      //  netflow     netflow keyword

      // mls qos
      container mls-qos-conf {
        tailf:cli-no-keyword;
        tailf:cli-drop-node-name;
        leaf qos {
          type empty;
        }
      }
      // mls qos
      container qos {
        description
          "QoS parameters";
        tailf:cli-incomplete-command;
        tailf:cli-incomplete-no;
        // mls qos aggregate-policer *
        list aggregate-policer {
          description
            "Assign aggregate policer";
          tailf:cli-suppress-mode;
          tailf:cli-delete-when-empty;
          tailf:cli-compact-syntax;
          tailf:cli-sequence-commands {
            tailf:cli-reset-all-siblings;
          }
          key "name";
          leaf name {
            type string;
          }
          leaf target-bit-rate {
            tailf:cli-drop-node-name;
            type uint64 {
              range "32000..60000000000";
            }
          }
          leaf burst-normal {
            tailf:cli-drop-node-name;
            tailf:cli-optional-in-sequence;
            type uint32 {
              range "1000..31250000";
            }
          }
          leaf burst-max {
            tailf:cli-drop-node-name;
            tailf:cli-optional-in-sequence;
            when "../burst-normal" {
               tailf:dependency "../burst-normal";
            }
            type uint32 {
              range "1000..31250000";
            }
          }
          leaf pir {
            description
              "PIR";
            tailf:cli-optional-in-sequence;
            type uint64 {
              range "32000..60000000000";
            }
          }
          container conform-action {
            description
              "action when rate is not exceeded";
            tailf:cli-optional-in-sequence;
            tailf:cli-compact-syntax;
            tailf:cli-flatten-container;
            choice action-choice {
              leaf drop {
                description
                  "drop packet";
                type empty;
              }
              leaf set-dscp-transmit {
                description
                  "set dscp and send it";
                type dscp-type;
              }
              leaf set-mpls-exp-imposition-transmit {
                description
                  "set exp at tag imposition and send it";
                type uint8 {
                  range "0..7";
                }
              }
              leaf set-prec-transmit {
                description
                  "rewrite packet precedence and send it";
                type uint8 {
                  range "0..7";
                }
              }
              leaf transmit {
                description
                  "transmit packet";
                type empty;
              }
            }
          }
          leaf exceed-action {
            description
              "action when rate is exceeded";
            tailf:cli-optional-in-sequence;
            type enumeration {
              enum "drop";
              enum "policed-dscp-transmit";
              enum "transmit";
            }
          }
          leaf violate-action {
            description
              "action when rate violated";
            type enumeration {
              enum "drop";
              enum "policed-dscp-transmit";
              enum "transmit";
            }
          }
        }
        //  map                Define QoS mapping
        //  mls qos map
        container map {
          description
            "qos map keyword";
          leaf-list cos-dscp {
            description
              "cos-dscp map: eight dscp values for cos 0-7";
            tailf:cli-flat-list-syntax;
            //max-elements 8;
            type uint8 {
              range "0..63";
            }
          }
          leaf-list policed-dscp {
            description
              "policed-dscp map keyword";
            ordered-by user;
            tailf:cli-flat-list-syntax;
            type union {
              type uint8 {
                range "0..63";
              }
              type enumeration {
                enum "to";
              }
            }
          }
        }
        //  marking            marking keyword
        //  police             police keyword
        //  protocol           protocol keyword
        //  queueing-only      queueing-only (no QoS rewrite,  no policing)
        //  recirc             recirculate path

        // mls qos rewrite
        container rewrite {
          description
            "packet qos rewrite enable/disable";
          container ip {
            description
              "ip packet qos rewrite enable/disable";
            container dscp {
              description
                "packet ip dscp rewrite enable/disable";
              presence "true";
              leaf slot {
                description
                  "slot number";
                type string;
              }
            }
          }
        }
        // mls qos queue-set
        container queue-set {
          description
            "Choose a queue set for this queue";
          list output {
            description
              "Direction the command applies for this command";
            tailf:cli-suppress-mode;
            key queue-set-id;
            leaf queue-set-id {
              type uint8 {
                range "1..2";
              }
            }
            list threshold {
              description
                "Assign threshold values to a queue";
              tailf:cli-suppress-mode;
              tailf:cli-compact-syntax;
              tailf:cli-sequence-commands;
              key "queue-id";
              leaf queue-id {
                type uint8 {
                  range "1..4";
                }
              }
              leaf drop1 {
                tailf:cli-drop-node-name;
                description
                  "drop threshold1 1-3200";
                type uint32 {
                  range "1..3200";
                }
              }
              leaf drop2 {
                tailf:cli-drop-node-name;
                description
                  "drop threshold2 1-3200";
                type uint32 {
                  range "1..3200";
                }
              }
              leaf reserved {
                tailf:cli-drop-node-name;
                description
                  "reserved threshold 1-100";
                type uint32 {
                  range "1..3200";
                }
              }
              leaf maximum {
                tailf:cli-drop-node-name;
                description
                  "maximum threshold1 1-3200";
                type uint32 {
                  range "1..3200";
                }
              }
            }
            leaf-list buffers {
              description
                "assign buffers to each egress queue";
              tailf:cli-flat-list-syntax;
              ordered-by user;
              type uint16 {
                range "0..100";
              }
            }
          }
        }
        // mls qos srr-queue
        container srr-queue {
          description
            "Configure SRR receive queues";
          container input {
            description
              "input keyword";
            leaf-list bandwidth {
              description
                "Configure SRR bandwidth";
              tailf:cli-flat-list-syntax;
              ordered-by user;
              type uint8 {
                range "1..100";
              }
            }
            list threshold {
              description
                "Configure queue tail-drop thresholds";
              tailf:cli-suppress-mode;
              key "queue-id";
              leaf queue-id {
                type uint8 {
                  range "1..2";
                }
              }
              leaf-list queue-size-percent {
                tailf:cli-drop-node-name;
                tailf:cli-flat-list-syntax;
                type uint8 {
                  range "1..100";
                }
              }
            }
            list priority-queue {
              description
                "Configure priority scheduling";
              tailf:cli-suppress-mode;
              key "queue-number";
              leaf queue-number {
                type uint8;
              }
              leaf bandwidth {
                description
                  "ingress priority queue bandwidth % of stack ring";
                type uint8 {
                  range "0..40";
                }
              }
            }
            list cos-map {
              description
                "Configure cos-map for a queue id";
              tailf:cli-suppress-mode;
              key "queue threshold";
              leaf queue {
                description
                  "Assign COS values to a queue";
                tailf:cli-expose-key-name;
                type uint8 {
                  range "1..4";
                }
              }
              leaf threshold {
                description
                  "Assign COS values to a queue threshold";
                tailf:cli-expose-key-name;
                type uint8 {
                  range "1..3";
                }
              }
              leaf-list cos {
                tailf:cli-drop-node-name;
                tailf:cli-flat-list-syntax;
                max-elements "8";
                type uint8 {
                  range "0..7";
                }
              }
            }
            list dscp-map {
              description
                "Configure dscp-map for a queue id";
              tailf:cli-suppress-mode;
              key "queue threshold";
              leaf queue {
                description
                  "Assign DSCP values to a queue";
                tailf:cli-expose-key-name;
                type uint8 {
                  range "1..4";
                }
              }
              leaf threshold {
                description
                  "Assign DSCP values to a queue threshold";
                tailf:cli-expose-key-name;
                type uint8 {
                  range "1..3";
                }
              }
              leaf-list dscp {
                tailf:cli-drop-node-name;
                tailf:cli-flat-list-syntax;
                tailf:cli-list-syntax;
                type uint8 {
                  range "0..63";
                }
              }
            }
          }
          container output {
            description
              "output keyword";
            list cos-map {
              description
                "Configure cos-map for a queue id";
              tailf:cli-suppress-mode;
              key "queue threshold";
              leaf queue {
                description
                  "Assign COS values to a queue";
                tailf:cli-expose-key-name;
                type uint8 {
                  range "1..4";
                }
              }
              leaf threshold {
                description
                  "Assign COS values to a queue threshold";
                tailf:cli-expose-key-name;
                type uint8 {
                  range "1..3";
                }
              }
              leaf-list cos {
                tailf:cli-drop-node-name;
                tailf:cli-flat-list-syntax;
                max-elements "8";
                type uint8 {
                  range "0..7";
                }
              }
            }
            list dscp-map {
              description
                "Configure dscp-map for a queue id";
              tailf:cli-suppress-mode;
              key "queue threshold";
              leaf queue {
                description
                  "Assign DSCP values to a queue";
                tailf:cli-expose-key-name;
                type uint8 {
                  range "1..4";
                }
              }
              leaf threshold {
                description
                  "Assign DSCP values to a queue threshold";
                tailf:cli-expose-key-name;
                type uint8 {
                  range "1..3";
                }
              }
              leaf-list dscp {
                tailf:cli-drop-node-name;
                tailf:cli-flat-list-syntax;
                tailf:cli-list-syntax;
                type uint8 {
                  range "0..63";
                }
              }
            }
          }
        }
      }
      //  statistics-export  qos statistics data export

      // mls rate-limit
      container rate-limit {
        description
          "Rate limit different behaviors";
        //  all        Rate Limiting for both Unicast and Multicast packets
        container layer2 {
          description
            "layer2 protocol cases";
          //  ip-admission   IP admission on Layer2 ports
          container l2pt {
            tailf:cli-compact-syntax;
            tailf:cli-sequence-commands {
              tailf:cli-reset-siblings;
            }
            leaf packets-per-second {
              description
                "layer2 protocol tunnelling packets";
              tailf:cli-drop-node-name;
              type uint32 {
                range "10..1000000";
              }
            }
            leaf packets-in-burst {
              tailf:cli-drop-node-name;
              type uint32 {
                range "1..255";
              }
            }
          }
          //  mac-security   Mac security traffics
          container pdu {
            description
              "layer2 protocol data unit packets";
            tailf:cli-compact-syntax;
            tailf:cli-sequence-commands {
              tailf:cli-reset-siblings;
            }
            leaf packets-per-second {
              tailf:cli-drop-node-name;
              type uint32 {
                range "10..1000000";
              }
            }
            leaf packets-in-burst {
              tailf:cli-drop-node-name;
              type uint32 {
                range "1..255";
              }
            }
          }
          //  port-security  Port security traffics
        }
        //  multicast  Rate limiting for Multicast packets
        //  unicast    Rate limiting for Unicast packets
      }
      //  rp          rp
      //  sampling    sampling keyword

      // mls verify
      container verify {
        description
          "enable hardware packet parsing error checks";
        container ip {
          description
            "check on IP packets";
          leaf checksum {
            description
              "check for packet checksum errors";
            tailf:cli-boolean-no;
            tailf:cli-trim-default;
            type boolean;
          }
          container length {
            description
              "check for packet length errors";
            leaf consistent {
              description
                "check length in header against physical frame length";
              tailf:cli-boolean-no;
              tailf:cli-trim-default;
              type boolean;
            }
            leaf minimum {
              description
                "check for minimum packet length";
              tailf:cli-boolean-no;
              tailf:cli-trim-default;
              type boolean;
            }
          }
          leaf same-address {
            description
              "check for packet having equal source and destination IP addresses";
            type empty;
          }
          leaf syslog {
            description
              "syslog packet parse errors";
            type empty;
          }
        }
      }
    }
    
    /// ========================================================================
    /// object-group
    /// ========================================================================
    container object-group {
      description
        "Configure Object Group";
      list network {
        description
          "network group";
        tailf:cli-mode-name "config-network-group";
        key "name";
        leaf name {
          description
            "WORD;;object-group name";
          type string;
        }
        container obj-Mode-config-network-group {
          tailf:cli-drop-node-name;
          list network_address {
            tailf:cli-drop-node-name;
            tailf:cli-suppress-mode;
            key "ipv4_addr ipv4_mask";
            leaf ipv4_addr {
              description
                "A.B.C.D;;Network address of the group members";
              type inet:ipv4-address;
            }
            leaf ipv4_mask {
              description
                "A.B.C.D;;Network mask";
              type inet:ipv4-address;
            }
          }
          leaf description {
            description
              "Network object group description";
            tailf:cli-multi-value;
            type string {
              length "1..200";
            }
          }
          leaf group-object {
            description
              "Nested object group";
            type string;
          }
          leaf host {
            description
              "Host address of the object-group member";
            type inet:host;
          }
          container range {
            tailf:cli-incomplete-command;
            tailf:cli-sequence-commands;
	    tailf:cli-compact-syntax;
            leaf ip-addr-min {
              tailf:cli-drop-node-name;
              description
                "Starting IPv4 Address";
              type inet:ipv4-address;
            }
            leaf ip-addr-max {
              tailf:cli-drop-node-name;
              description
                "Ending IPv4 Address";
              type inet:ipv4-address;
            }
          }
        }
      }
      list security {
        description
          "security group";
        tailf:cli-mode-name "config-security-group";
        key "name";
        leaf name {
          type string;
        }
        container security-group {
          tailf:cli-drop-node-name;
          leaf description {
            description
              "Network object group description";
            tailf:cli-multi-value;
            type string {
              length "1..200";
            }
          }
          leaf group-object {
            description
              "Nested object group";
            type string;
          }
          container security-group {
            description
              "Security Group Tag";
            leaf tag {
              type uint16 {
                range "1..65535";
              }
            }
          }
        }
      }
      list service {
        description
          "service group";
        tailf:cli-mode-name "config-service-group";
        key "name";
        leaf name {
          type string;
        }
        uses object-group-service-grouping;
      }
    }

    /// ========================================================================
    /// policer
    /// ========================================================================
    // Note: must come before class-map and policy-map.
    container policer {
      description
        "Switch policer";
      // policer aggregate *
      list aggregate {
        description
          "Named aggregate policer";
        tailf:cli-suppress-mode;
        tailf:cli-delete-when-empty;
        tailf:cli-compact-syntax;
        tailf:cli-reset-container;
        tailf:cli-sequence-commands {
          tailf:cli-reset-siblings;
        }
        key "name";
        leaf name {
          type string;
        }
        // cir <cir-bps>
        leaf cir {
          description
            "Committed information rate";
          type uint32 {
            range "8000..1000000000";
          }
        }
        // bc <burst>
        leaf bc {
          description
            "Conform burst";
          tailf:cli-optional-in-sequence;
          type uint32 {
            range "8000..1000000000";
          }
        }
        leaf conform-action {
          description
            "action when rate is within conform and conform + exceed burst";
          tailf:cli-optional-in-sequence;
          type empty;
        }
        leaf set-qos-transmit {
          description
            "set qos-group and send it";
          tailf:cli-optional-in-sequence;
          when "../conform-action";
          type uint8 {
            range "0..99";
          }
        }
        leaf set-dot1ad-dei-transmit {
          description
            "set dei and send it";
          tailf:cli-optional-in-sequence;
          when "../conform-action";
          type uint8 {
            range "0..1";
          }
        }
        leaf set-prec-transmit {
          description
            "rewrite packet precedence and send it";
          tailf:cli-optional-in-sequence;
          when "../conform-action";
          type prec_value-type;
        }
        container set-prec-transmit-table {
          when "../set-prec-transmit";
          tailf:cli-no-keyword;
          tailf:cli-drop-node-name;
          tailf:cli-optional-in-sequence;
          tailf:cli-flatten-container;
          leaf table {
            description
              "Set packet cos from cos based on table map";
            tailf:cli-optional-in-sequence;
            type string;
            tailf:non-strict-leafref {
              path "/ios:native/table-map/name";
            }
          }
        }
        leaf set-dscp-transmit {
          description
            "set dscp and send it";
          tailf:cli-optional-in-sequence;
          when "../conform-action";
          type dscp-type;
        }
        container set-dscp-transmit-table {
          when "../set-dscp-transmit";
          tailf:cli-no-keyword;
          tailf:cli-drop-node-name;
          tailf:cli-optional-in-sequence;
          tailf:cli-flatten-container;
          leaf table {
            description
              "Set packet cos from cos based on table map";
            tailf:cli-optional-in-sequence;
            type string;
            tailf:non-strict-leafref {
              path "/ios:native/table-map/name";
            }
          }
        }
        leaf set-cos-transmit {
          description
            "set cos and send it";
          tailf:cli-optional-in-sequence;
          when "../conform-action";
          type cos_value-type;
        }
        container set-cos-transmit-table {
          when "../set-cos-transmit";
          tailf:cli-no-keyword;
          tailf:cli-drop-node-name;
          tailf:cli-optional-in-sequence;
          tailf:cli-flatten-container;
          leaf table {
            description
              "Set packet cos from cos based on table map";
            tailf:cli-optional-in-sequence;
            type string;
            tailf:non-strict-leafref {
              path "/ios:native/table-map/name";
            }
          }
        }
        leaf transmit {
          description
            "transmit packet";
          tailf:cli-optional-in-sequence;
          when "../conform-action";
          type empty;
        }
        leaf exceed-action {
          description
            "action when rate is within conform and conform + exceed burst";
          type empty;
        }
        leaf drop {
          description
            "drop packet";
          tailf:cli-optional-in-sequence;
          tailf:cli-full-command;
          when "../exceed-action";
          type empty;
        }
        container exceed-transmit {
          tailf:cli-no-keyword;
          tailf:cli-drop-node-name;
          tailf:cli-optional-in-sequence;
          tailf:cli-flatten-container;
          leaf transmit {
            description
              "transmit packet";
            tailf:cli-optional-in-sequence;
            when "../../exceed-action";
            type empty;
          }
        }
      }
    }
    
    /// ========================================================================
    /// class-map
    /// ========================================================================
    list class-map {
      description
        "Configure QoS Class Map";
      tailf:cli-mode-name "config-cmap";
      tailf:cli-suppress-list-no;
      tailf:cli-delete-when-empty;
      tailf:cli-no-key-completion;
      key "name";
      leaf name {
        type string;
        tailf:cli-disallow-value "type";
      }
      // class-map * type inspect
      leaf type {
        description
          "type of the class-map";
        tailf:cli-prefix-key;
        type enumeration {
          enum "access-control";
          enum "appnav";
          enum "control";
          enum "inspect";
          enum "multicast-flows";
          enum "stack";
          enum "traffic";
        }
      }
      leaf subscriber {
        tailf:cli-prefix-key;
        type empty;
      }
      // class-map * <protocol>
      leaf protocol {
        tailf:cli-drop-node-name;
        tailf:cli-prefix-key;
        when "../type = 'inspect'";
        type enumeration {
          enum "aol";
          enum "edonkey";
          enum "fasttrack";
          enum "gnutella";
          enum "http";
          enum "imap";
          enum "kazaa2";
          enum "msnmsgr";
          enum "pop3";
          enum "smtp";
          enum "sunrpc";
          enum "ymsgr";
        }
      }
      // class-map * <match-any|match-all>
      leaf prematch {
        tailf:cli-no-keyword;
        tailf:cli-prefix-key;
        tailf:cli-drop-node-name;
        type enumeration {
          enum "match-all";
          enum "match-any";
          enum "match-none";
        }
        //mandatory true;
      }
      // class-map * / description
      leaf description {
        description
          "Class-Map description";
        tailf:cli-multi-value;
        type string;
      }
      // class-map * / match
      container match {
        description
          "classification criteria";
        uses class-map-match-grouping;
        uses class-map-appnav-match-grouping;
        uses class-map-control-filter-grouping;
        container not {
          description
            "Negate this match result";
          uses class-map-match-grouping;
          uses class-map-appnav-not-match-grouping;
        }
      }
      container no-match{
        description "no-match filter";
        uses class-map-control-filter-grouping;        
      } 
    }
    
    /// ========================================================================
    /// policy-map
    /// ========================================================================
    list policy-map {
      description
        "Configure QoS Policy Map";
      tailf:cli-mode-name "config-pmap";
      tailf:cli-diff-dependency "/ios:native/class-map";
      tailf:cli-diff-dependency "/ios:native/table-map";
      tailf:cli-diff-dependency "/ios:native/mls/qos/aggregate-policer";
      tailf:cli-diff-dependency "/ios:native/policer/aggregate";
      key "name";
      leaf name {
        type string;
        tailf:cli-disallow-value "(type)|(http)|(im)|(imap)|(p2p)|(pop3)|(smtp)|(sunrpc)";
      }
      leaf type {
        description
          "type of the policy-map";
        tailf:cli-prefix-key;
        type enumeration {
          enum "access-control";
          enum "appnav";
          enum "inspect";
          enum "control";
          enum "packet-service";
          enum "performance-monitor";
          enum "service";
          enum "service-chain";
        }
      }
      leaf subscriber{
        tailf:cli-prefix-key;
        type empty;
      }
      leaf protocol {
        tailf:cli-drop-node-name;
        tailf:cli-prefix-key;
        when "../type = 'inspect'";
        type enumeration {
          enum "http";
          enum "im";
          enum "imap";
          enum "p2p";
          enum "pop3";
          enum "smtp";
          enum "sunrpc";
        }
      }
      // policy-map * / event *
      list event {
        description
          "The event type this control class-map triggers upon";
        tailf:cli-mode-name "config-class-control-policymap";  
        key "event-type";
        leaf event-type {
          type enumeration {
            enum "aaa-available";
            enum "absolute-timeout";
            enum "agent-found";                    
            enum "authentication-failure";
            enum "authentication-success";
            enum "authorization-failure";
            enum "authorization-success";
            enum "identity-update";
            enum "inactivity-timeout";
            enum "remote-authentication-failure";
            enum "remote-authentication-success";
            enum "session-disconnected";
            enum "session-started";
            enum "tag-added";
            enum "tag-removed";
            enum "template-activated";
            enum "template-activation-failed";
            enum "template-deactivated";
            enum "template-deactivation-failed";
            enum "timer-expiry";
            enum "violation";
          }
        }
        leaf match-type {
          tailf:cli-drop-node-name;
          tailf:cli-hide-in-submode;
          type enumeration {
            enum "match-all";
            enum "match-first";
          }
        }
        list class-number {
          tailf:cli-drop-node-name;
          description "class number, 1 for 1st class, 2 for 2nd...";
          key "number";
          leaf number {
            type uint8 {
              range "1..254";
            }
          }
          leaf class {
            description "The class type this control policy-map triggers upon";
            tailf:cli-hide-in-submode;
            tailf:cli-incomplete-command;
            type union {
              type enumeration {
                enum "always";
              }
              type string;       
            }
          }
          leaf execution-type {
            tailf:cli-drop-node-name;
            tailf:cli-hide-in-submode;
            type enumeration {
              enum "do-all";
              enum "do-until-failure";
              enum "do-until-success";
             }
          }
          list action-number {
            tailf:cli-drop-node-name;
            description "action number, 1 for 1st class, 2 for 2nd...";
            tailf:cli-suppress-mode;
            key "number";
            leaf number {
              type uint8 {
                range "1..254";
              }
            }
            container terminate {
              description "terminate auth method";
              leaf dot1x {
                description "dot1x method";
                type empty;
              }
              leaf mab {
                description "mab method"; 
                type empty;
              }
              leaf webauth {
                description "webauth method";
                type empty;
              }
            }
            leaf clear-session {
              description "clears an active session";
              type empty;
            }
            container resume {
              description "resume operation to be specified";
              leaf reauthentication {
                description "resume reauthentication";
                type empty;
              }
            }                
            leaf authentication-restart {
              description "restarts the auth sequence after the specified number of sec";
              type uint16 {
                range "1..65535";
              }
            }
            container pause {
              description "pause operation to be specified";
              leaf reauthentication {
                description "pause reauthentication";
                type empty;
              }
            }
            leaf authorize {
              description "authorize session";
              type empty;
            }
            container activate  {
              description "activate template or policy";
              leaf service-template {
                description "activate service template";
                type string;
              }
            }
            container authenticate {
              description "authenticate a session";
              container using {
                description "authenticate a session";
                tailf:cli-sequence-commands;
                tailf:cli-compact-syntax;
                leaf method {
                  tailf:cli-drop-node-name;
                  type enumeration {
                    enum "dot1x";
                    enum "mab";
                    enum "webauth";
                  }
                }
                leaf both {
                  description "Enabling Dot1x Authenticator & Supplicant";
                  tailf:cli-optional-in-sequence;
                  tailf:cli-break-sequence-commands;
                  type empty;
                }
                leaf retries {
                  description "Number of times to retry failed authentications";
                  type uint8 {
                    range "1..5";
                  }
                }
                leaf retry-time {
                  description "Time interval between retries";
                  type uint16 {
                    range "0..65535";
                  }
                }
                leaf priority {
                  description "Method priority";
                  type uint8 {
                    range "1..254";
                  }
                }
              } 
            }
          }
        }
      }
      // policy-map * / class *
      list class {
        description
          "policy criteria";
        tailf:cli-mode-name "config-pmap-c";
        key "name";
        leaf name {
          tailf:cli-disallow-value "type";
          tailf:cli-diff-dependency "/ios:native/class-map/name";
          type class-name-type;
        }
        // policy-map * / class * / type
        leaf type {
          description
            "type of the class-map";
          tailf:cli-prefix-key;
          type enumeration {
            enum "inspect";
          }
        }
        leaf insert-before {
          description
            "Insert the class before a specified class";
          tailf:cli-hide-in-submode;
          when "../../type = 'appnav'";
          type string;
        }
        // policy-map * / class * / appnav policy
        container appnav-policy {
          when "../../type = 'appnav'";
          tailf:cli-drop-node-name;
          list distribute {
            description
              "Distribute action";
            tailf:cli-suppress-mode;
            key "service-node-group";
            leaf service-node-group {
              description
                "Distribute to service-node-group";
              tailf:cli-expose-key-name;
              type string;
            }
            leaf insert-before {
              description
                "Insert before specific node";
              tailf:cli-optional-in-sequence;
              type string;
            }
          }
          leaf monitor-load {
            description
              "Monitor AO";
            when "../distribute";
            type enumeration {
              enum "MS-port-mapper";
              enum "cifs";
              enum "http";
              enum "ica";
              enum "mapi";
              enum "nfs";
              enum "ssl";
              enum "video";
            }
          }
          leaf pass-through {
            description
              "pass-through action";
            type empty;
          }
        }
        // policy-map * / class * / inspect policy
        container policy {
          when "../../type = 'inspect'";
          tailf:cli-drop-node-name;
          tailf:cli-compact-syntax;
          tailf:cli-sequence-commands {
            tailf:cli-reset-siblings;
          }
          leaf action {
            tailf:cli-drop-node-name;
            tailf:cli-remove-before-change;
            type enumeration {
              enum "cxsc";
              enum "drop";
              enum "inspect";
              enum "pass";
              enum "service-policy";
            }
          }
          leaf log {
            description
              "Send logging message for drop or pass";
            when "../action = 'drop'or ../action = 'pass'";
            type empty;
          }
          leaf parameter-map {
            tailf:cli-drop-node-name;
            when "../action = 'inspect' or ../action = 'cxsc'";
            type string;
            tailf:non-strict-leafref {
              path "/ios:native/parameter-map/name";
            }
          }
          container dpi {
            tailf:cli-drop-node-name;
            when "../action = 'service-policy'";
            tailf:cli-sequence-commands;
            tailf:cli-compact-syntax;
            leaf type {
              tailf:cli-drop-node-name;
              type enumeration {
                enum "gtpv0";
                enum "gtpv1";
                enum "imap";
                enum "pop3";
                enum "smtp";
                enum "sunrpc";
              }
            }
            leaf policy-map {
              tailf:cli-drop-node-name;
              type string;
            }
          }
        }
        // policy-map * / class * / performance-monitor policy
        container pm-policy {
          when "../../type = 'performance-monitor'";
          tailf:cli-drop-node-name;
          container flow {
            description
              "Flow subcommands";
            leaf monitor {
              description
                "Apply a Flow Monitor";
              type string;
            }
          }
          container monitor {
            description
              "Monitor related parameters";
            container metric {
              description
                "Monitor metric";
              container rtp {
                description
                  "RTP metrics parameters";
                tailf:cli-add-mode;
                tailf:cli-mode-name "config-pmap-c-mrtp";
                list clock-rate {
                  description
                    "RTP timestamp field's sampling frequency";
                  tailf:cli-suppress-mode;
                  tailf:cli-sequence-commands;
                  tailf:cli-compact-syntax;
                  key "number";
                  leaf number {
                    type union {
                      type uint8 {
                        range "0..127";
                      }
                      type enumeration {
                        enum "celb";
                        enum "cn";
                        enum "default";
                        enum "dvi4";
                        enum "dvi4-2";
                        enum "dvi4-3";
                        enum "dvi4-4";
                        enum "g722";
                        enum "g723";
                        enum "g728";
                        enum "g729";
                        enum "gsm";
                        enum "h261";
                        enum "h263";
                        enum "jpeg";
                        enum "l16";
                        enum "l16-2";
                        enum "lpc";
                        enum "mp2t";
                        enum "mpa";
                        enum "mpv";
                        enum "nv";
                        enum "pcma";
                        enum "pcmu";
                        enum "qcelp";
                      }
                    }
                  }
                  leaf frequency {
                    tailf:cli-drop-node-name;
                    type uint32 {
                      range "1000..192000";
                    }
                  }
                }
              }
            }
          }
          list react {
            description
              "Configure threshold crossing actions";
            tailf:cli-mode-name "config-pmap-c-react";
            key "id";
            leaf id {
              type uint16;
            }
            leaf mode {
              tailf:cli-drop-node-name;
              tailf:cli-hide-in-submode;
              type enumeration {
                enum "media-stop";
                enum "mrv";
                enum "rtp-jitter-average";
                enum "transport-packets-lost-rate";
              }
            }
            leaf description {
              description
                "Description for the instance";
              tailf:cli-multi-value;
              type string;
            }
            container action {
              description
                "Config react action";
              leaf snmp {
                description
                  "SNMP is notified of the event";
                tailf:cli-full-command;
                type empty;
              }
              leaf syslog {
                description
                  "The threshold-crossing event is logged to syslog";
                tailf:cli-full-command;
                type empty;
              }
            }
            container alarm {
              description
                "Config react alarm";
              leaf severity {
                description
                  "Alarm severity - default level none";
                type enumeration {
                  enum "alert";
                  enum "critical";
                  enum "emergency";
                  enum "error";
                  enum "info";
                }
              }
              container type {
                description
                  "Alarm raised type - for each flow or a group";
                leaf discrete {
                  description
                    "Alert for each flow within the class";
                  tailf:cli-full-command;
                  type empty;
                }
                container grouped {
                  description
                    "Alert if more than one flow cross the threshold";
                  leaf count {
                    description
                      "Number of flows in the group cross the threshold";
                    tailf:cli-full-command;
                    type uint16;
                  }
                  leaf percent {
                    description
                      "Percent of flows in the group cross the threshold";
                    tailf:cli-full-command;
                    type uint8 {
                      range "1..100";
                    }
                  }
                }
              }
            }
            container threshold {
              description
                "Config react threshold";
              container value {
                description
                  "Range of percentage loss that would trigger the alarm";
                leaf ge {
                  description
                    "greater and equal to";
                  tailf:cli-full-command;
                  type string;
                }
                leaf gt {
                  description
                    "greater than";
                  tailf:cli-full-command;
                  type string;
                }
                leaf le {
                  description
                    "less and equal to";
                  tailf:cli-full-command;
                  type string;
                }
                leaf lt {
                  description
                    "less than";
                  tailf:cli-full-command;
                  type string;
                }
                container range {
                  description
                    "threshold within the range of";
                  tailf:cli-sequence-commands;
                  tailf:cli-compact-syntax;
                  leaf low {
                    tailf:cli-drop-node-name;
                    type string;
                  }
                  leaf high {
                    tailf:cli-drop-node-name;
                    type string;
                  }
                }
              }
            }
          }
        }
        // policy-map * / class * / inspect-police
        container inspect-police {
          when "../policy/action = 'inspect'";
          tailf:cli-drop-node-name;
          container police {
            description
              "Police";
            tailf:cli-sequence-commands {
              tailf:cli-reset-siblings;
            }
            tailf:cli-compact-syntax;
            leaf rate {
              description
                "Specify police rate";
              type uint32 {
                range "8000..2000000000";
              }
            }
            leaf burst {
              description
                "Specify 'burst' parameter";
              type uint32 {
                range "1000..512000000";
              }
            }
          }
        }
        list action-list {
          tailf:cli-drop-node-name;
          tailf:cli-suppress-mode;
          key "action-type";
          ordered-by user;
          leaf action-type {
            type policy-action-type;
          }
          choice action-param {
            // policy-map * / class * / bandwidth
            case bandwidth-case {
              container bandwidth {
                tailf:cli-drop-node-name;
                when "../action-type = 'bandwidth'";
                leaf bits {
                  tailf:cli-drop-node-name;
                  type uint32 {
                    range "8..2000000";
                  }
                }
                leaf percent {
                  description
                    "% of total Bandwidth";
                  type percentage-type;
                }
                container remaining {
                  description
                    "% of the remaining bandwidth";
                  leaf percent {
                    description
                      "% of the remaining bandwidth";
                    type percentage-type;
                  }
                  leaf ratio {
                    description
                      "ratio for sharing excess bandwidth";
                    type uint16;
                  }
                }
              }
            }
            case compression-case {
              // policy-map * / class * / compression
              container compression {
                tailf:cli-drop-node-name;
                when "../action-type = 'compression'";
                container header {
                  description
                    "configure header compression";
                  presence "configure header compression";
                  leaf ip {
                    description
                      "configure ip header compression";
                    type enumeration {
                      enum "rtp" {
                        tailf:code-name "header_rtp";
                      }
                      enum "tcp";
                    }
                  }
                }
              }
            }
            //case drop-case {
              // policy-map * / class * / drop
              //leaf drop {
                //tailf:info "Drop all packets";
               // tailf:cli-full-command;
                //type empty;
              //}
            //}
            case estimate-case {
              // policy-map * / class * / estimate
              container estimate {
                tailf:cli-drop-node-name;
                when "../action-type = 'estimate'";
                container bandwidth {
                  presence "bandwidth required to service this class";
                  description
                    "bandwidth required to service this class";
                  tailf:cli-sequence-commands;
                  tailf:cli-compact-syntax;
                  container delay-one-in {
                    description
                      "specify QoS target delay";
                    tailf:cli-compact-syntax;
                    tailf:cli-sequence-commands;
                    leaf doi {
                      tailf:cli-drop-node-name;
                      tailf:cli-incomplete-command;
                      type uint32 {
                        range "50..1000000";
                      }
                    }
                    leaf milliseconds {
                      type uint32 {
                        range "8..1000";
                      }
                    }
                  }
                  leaf drop-one-in {
                    description
                      "specify QoS target loss rate";
                    type uint32;
                  }
                }
              }
            }
            case forward-case {
              //policy-map * / class * / forward service-path
              container forward {
                tailf:cli-reset-container;
                tailf:cli-drop-node-name;
                tailf:cli-compact-syntax;
                tailf:cli-sequence-commands;
                when "../action-type = 'forward'";
                leaf service-path {
                  description
                    "Service Path Entries";
                  type uint32 {
                    range "0..16777215";
                  }
                }
                leaf service-index {
                  description
                    "Service Index";
                  type uint8 {
                    range "2..255";
                  }
                }
              }
            }
            case fair-queue-case {
              // policy-map * / class * / fair-queue
              // class-default: fair-queue [number-of-dynamic-queues]
              // DWFQ: fair-queue
              // policy-map: fair-queue [queue-limit queue-value]
              // NOT SUPPORTED:
              // air-queue [congestive-discard-threshold [dynamic-q [reservable-q]]]
              container fair-queue {
                tailf:cli-reset-container;
                tailf:cli-drop-node-name;
                when "../action-type = 'fair-queue'";
                leaf dynamic-queues {
                  tailf:cli-drop-node-name;
                  tailf:cli-full-command;
                  type uint32 {
                    range "16|32|64|128|256|512|1024|2048|4096";
                  }
                }
                leaf queue-limit {
                  description
                    "per flow queue limit";
                  tailf:cli-full-command;
                  type uint16 {
                    range "1..32768";
                  }
                }
              }
            }
            case netflow-sampler-case {
              // policy-map * / class * / netflow-sampler
              leaf netflow-sampler {
                tailf:cli-drop-node-name;
                tailf:cli-full-command;
                when "../action-type = 'netflow-sampler'";
                // should be leafref to sampler
                type string;
              }
            }
            case police-case {
              choice police-choice {
                // policy-map * / class * / police aggregate
                case police-aggregate-case {
                  container police-aggregate {
                    tailf:cli-no-keyword;
                    tailf:cli-drop-node-name;
                    container police {
                      tailf:cli-drop-node-name;
                      when "../../action-type = 'police'" {
                        tailf:dependency "../../action-type";
                      }
                      leaf aggregate {
                        description
                          "Choose aggregate policer for current class";
                        type string;
                      }
                    }
                  }
                }
                // police (policy-map)
                // police cir <bps> [[bc <burst-normal>] [be <burst-max>]]
                //        [pir <bps> [be <burst-bytes>]] ACTIONS
                // NOTE: cir, bc & be keywords are mandatory in this model.
                //       Java code will add missing cir,bc and be in show().
                case police-policy-map-case {
                  container police-policy-map {
                    tailf:cli-no-keyword;
                    tailf:cli-drop-node-name;
                    container police {
                      tailf:cli-add-mode;
                      tailf:cli-mode-name "config-pmap-c-police";
                      tailf:cli-flatten-container;
                      tailf:cli-sequence-commands {
                        tailf:cli-reset-siblings;
                      }
                      tailf:cli-drop-node-name;
                      when "../../action-type = 'police'" {
                        tailf:dependency "../../action-type";
                      }
                      leaf cir {
                        description
                          "Committed information rate";
                        tailf:cli-hide-in-submode;
                        type police-bps-type;
                      }
                      leaf bc {
                        description
                          "Conform burst";
                        tailf:cli-optional-in-sequence;
                        tailf:cli-hide-in-submode;
                        type police-burst-type;
                      }
                      leaf be {
                        description
                          "Excess burst";
                        tailf:cli-optional-in-sequence;
                        tailf:cli-hide-in-submode;
                        when "../bc";
                        type police-burst-type;
                      }
                      leaf pir {
                        description
                          "Peak Information Rate";
                        tailf:cli-optional-in-sequence;
                        tailf:cli-hide-in-submode;
                        type police-bps-type;
                      }
                      container pir-be {
                        when "../pir";
                        tailf:cli-no-keyword;
                        tailf:cli-drop-node-name;
                        tailf:cli-optional-in-sequence;
                        tailf:cli-flatten-container;
                        tailf:cli-hide-in-submode;
                        leaf be {
                          description
                            "Excess burst";
                          type police-burst-type;
                        }
                      }
                      // conform-action | exceed-action | violate-action
                      uses police-action-grouping;
                    }
                  }
                }
                // police cir percent (combo of percent & policy-map versions)
                // police cir percent <percentage>
                //    [bc] <burst> ms] [be [<burst> ms]
                //    [pir percent <percentage> [be <burst> ms]] ACTIONS
                case police-cir-percent-case {
                  container police-cir-percent {
                    tailf:cli-no-keyword;
                    tailf:cli-drop-node-name;
                    container police {
                      tailf:cli-drop-node-name;
                      when "../../action-type = 'police'" {
                        tailf:dependency "../../action-type";
                      }
                      container cir {
                        description
                          "Committed information rate";
                        container percent {
                          description
                            "% of interface bandwidth for Committed information rate";
                          tailf:cli-add-mode;
                          tailf:cli-mode-name "config-pmap-c-police";
                          tailf:cli-incomplete-command;
                          tailf:cli-flatten-container;
                          tailf:cli-sequence-commands {
                            tailf:cli-reset-siblings;
                          }
                          leaf percentage {
                            tailf:cli-drop-node-name;
                            tailf:cli-hide-in-submode;
                            type percentage-type;
                          }
                          leaf bc {
                            description
                              "Conform burst";
                            tailf:cli-optional-in-sequence;
                            tailf:cli-hide-in-submode;
                            type uint16;
                          }
                          container bc-ms {
                            when "../bc";
                            tailf:cli-no-keyword;
                            tailf:cli-drop-node-name;
                            tailf:cli-optional-in-sequence;
                            tailf:cli-hide-in-submode;
                            tailf:cli-compact-syntax;
                            tailf:cli-flatten-container;
                            leaf ms {
                              description
                                "Milli seconds";
                              tailf:cli-no-keyword;
                              type empty;
                            }
                          }
                          leaf be {
                            tailf:cli-optional-in-sequence;
                            tailf:cli-hide-in-submode;
                            when "../bc-ms/ms" {
                              tailf:dependency "../bc-ms/ms";
                            }
                            type uint16;
                          }
                          container be-ms {
                            when "../be";
                            tailf:cli-no-keyword;
                            tailf:cli-drop-node-name;
                            tailf:cli-hide-in-submode;
                            tailf:cli-compact-syntax;
                            tailf:cli-flatten-container;
                            leaf ms {
                              description
                                "Milli seconds";
                              tailf:cli-no-keyword;
                              type empty;
                            }
                          }
                          // [pir percent <percentage> [be <burst> ms]]
                          container pir {
                            description
                              "Peak Information Rate";
                            tailf:cli-compact-syntax;
                            tailf:cli-flatten-container;
                            tailf:cli-hide-in-submode;
                            tailf:cli-optional-in-sequence;
                            leaf percent {
                              description
                                "% of interface bandwidth for Peak Information Rate";
                              type percentage-type;
                            }
                          }
                          container pir-be {
                            when "../pir";
                            tailf:cli-no-keyword;
                            tailf:cli-drop-node-name;
                            tailf:cli-optional-in-sequence;
                            tailf:cli-flatten-container;
                            tailf:cli-hide-in-submode;
                            leaf be {
                              description
                                "Excess burst";
                              type uint16;
                            }
                          }
                          container pir-be-ms {
                            when "../pir-be/be" {
                              tailf:dependency "../pir-be/be";
                            }
                            tailf:cli-no-keyword;
                            tailf:cli-drop-node-name;
                            tailf:cli-optional-in-sequence;
                            tailf:cli-hide-in-submode;
                            tailf:cli-flatten-container;
                            leaf ms {
                              description
                                "Milli seconds";
                              tailf:cli-no-keyword;
                              type empty;
                            }
                          }
                          // conform-action | exceed-action | violate-action
                          uses police-action-grouping;
                        }
                      }
                    }
                  }
                }
                // police rate (control-plane)
                // police rate <units> <pps|bps> [burst <burst-in-x> <packets|bytes>]
                //   [peak-rate <peak-rate-in-xps> <pps|bps>]
                //   [peak-burst <peak-burst-in-x> <packets|bytes>]
                //   [conform-action <action>]
                case police-rate-unit-case {
                  container police-rate-unit {
                    tailf:cli-no-keyword;
                    tailf:cli-drop-node-name;
                    container police {
                      tailf:cli-drop-node-name;
                      when "../../action-type = 'police'" {
                        tailf:dependency "../../action-type";
                      }
                      container rate {
                        description
                          "Specify police rate";
                        tailf:cli-add-mode;
                        tailf:cli-mode-name "config-pmap-c-police";
                        tailf:cli-flatten-container;
                        tailf:cli-sequence-commands {
                          tailf:cli-reset-siblings;
                        }
                        leaf units {
                          tailf:cli-drop-node-name;
                          tailf:cli-hide-in-submode;
                          type uint64;
                        }
                        leaf xps {
                          tailf:cli-no-keyword;
                          tailf:cli-drop-node-name;
                          tailf:cli-hide-in-submode;
                          type police-pps-bps-type;
                        }
                        // [burst <burst-in-x> <packets|bytes>]
                        container burst {
                          description
                            "Specify 'burst' parameter";
                          tailf:cli-optional-in-sequence;
                          tailf:cli-compact-syntax;
                          tailf:cli-hide-in-submode;
                          tailf:cli-flatten-container;
                          tailf:cli-sequence-commands;
                          leaf burst-value {
                            tailf:cli-no-keyword;
                            tailf:cli-drop-node-name;
                            tailf:cli-incomplete-command;
                            type uint32;
                          }
                          leaf burst-type {
                            tailf:cli-no-keyword;
                            tailf:cli-drop-node-name;
                            tailf:cli-hide-in-submode;
                            type police-packets-bytes-type;
                          }
                        }
                        // [peak-rate <peak-rate-in-xps> <pps|bps>]
                        container peak-rate {
                          description
                            "Specify peak rate";
                          tailf:cli-optional-in-sequence;
                          tailf:cli-compact-syntax;
                          tailf:cli-flatten-container;
                          tailf:cli-hide-in-submode;
                          tailf:cli-sequence-commands;
                          leaf peak-rate-value {
                            tailf:cli-no-keyword;
                            tailf:cli-drop-node-name;
                            tailf:cli-incomplete-command;
                            type uint32 {
                              range "1..512000000";
                            }
                          }
                          leaf xps {
                            tailf:cli-no-keyword;
                            tailf:cli-drop-node-name;
                            type police-pps-bps-type;
                          }
                        }
                        // [peak-burst <peak-burst-in-x> <packets|bytes>]
                        container peak-burst {
                          description
                            "Specify 'peak-burst' parameter for peak-rate";
                          tailf:cli-optional-in-sequence;
                          tailf:cli-compact-syntax;
                          tailf:cli-flatten-container;
                          tailf:cli-hide-in-submode;
                          tailf:cli-sequence-commands;
                          leaf burst-value {
                            tailf:cli-no-keyword;
                            tailf:cli-drop-node-name;
                            tailf:cli-incomplete-command;
                            type uint32;
                          }
                          leaf burst-type {
                            tailf:cli-no-keyword;
                            tailf:cli-drop-node-name;
                            type police-packets-bytes-type;
                          }
                        }
                        // conform-action | exceed-action | violate-action
                        uses police-action-grouping;
                      }
                    }
                  }
                }
                // police rate percent (control-plane)
                // police rate percent <percentage> [burst <ms> ms]
                //    [peak-rate percent <percentage>] [peak-burst <ms> ms]
                case police-rate-percent-case {
                  container police-rate-percent {
                    tailf:cli-no-keyword;
                    tailf:cli-drop-node-name;
                    container police {
                      tailf:cli-drop-node-name;
                      when "../../action-type = 'police'" {
                        tailf:dependency "../../action-type";
                      }
                      container rate {
                        description
                          "Specify police rate";
                        container percent {
                          description
                            "% of interface bandwidth for rate";
                          tailf:cli-add-mode;
                          tailf:cli-mode-name "config-pmap-c-police";
                          tailf:cli-flatten-container;
                          tailf:cli-sequence-commands {
                            tailf:cli-reset-siblings;
                          }
                          leaf percentage {
                            tailf:cli-drop-node-name;
                            tailf:cli-hide-in-submode;
                            type percentage-type;
                          }
                          leaf burst {
                            description
                              "Specify 'burst' parameter";
                            tailf:cli-optional-in-sequence;
                            tailf:cli-hide-in-submode;
                            type uint16;
                          }
                          leaf ms {
                            description
                              "Treat 'burst' value in milliseconds";
                            tailf:cli-hide-in-submode;
                            when "../burst";
                            type empty;
                          }
                          container peak-rate {
                            description
                              "Specify peak rate";
                            tailf:cli-hide-in-submode;
                            tailf:cli-optional-in-sequence;
                            tailf:cli-flatten-container;
                            leaf percent {
                              description
                                "% of interface bandwidth for peak-rate";
                              type percentage-type;
                            }
                          }
                          leaf peak-burst {
                            description
                              "Specify 'peak-burst' parameter for 'peak-rate'";
                            tailf:cli-hide-in-submode;
                            tailf:cli-optional-in-sequence;
                            type uint16;
                          }
                          container peak-burst-ms {
                            when "../peak-burst";
                            tailf:cli-no-keyword;
                            tailf:cli-drop-node-name;
                            tailf:cli-optional-in-sequence;
                            tailf:cli-hide-in-submode;
                            tailf:cli-flatten-container;
                            leaf ms {
                              description
                                "Milli seconds";
                              tailf:cli-no-keyword;
                              type empty;
                            }
                          }
                          uses police-action-grouping;
                        }
                      }
                    }
                  }
                }
                // police rate pdp
                // police rate pdp [burst <bytes>]
                //    [peak-rate pdp [peak-burst <bytes>]] ACTIONS
                case police-rate-pdp-case {
                  container police-rate-pdp {
                    tailf:cli-no-keyword;
                    tailf:cli-drop-node-name;
                    container police {
                      tailf:cli-drop-node-name;
                      when "../../action-type = 'police'" {
                        tailf:dependency "../../action-type";
                      }
                      container rate {
                        description
                          "Specify police rate";
                        container pdp {
                          description
                            "% of interface bandwidth for rate";
                          tailf:cli-add-mode;
                          tailf:cli-mode-name "config-pmap-c-police";
                          tailf:cli-flatten-container;
                          tailf:cli-sequence-commands {
                            tailf:cli-reset-siblings;
                          }
                          leaf burst {
                            description
                              "Conform burst";
                            tailf:cli-hide-in-submode;
                            tailf:cli-optional-in-sequence;
                            type police-burst-type;
                          }
                          leaf peak-rate {
                            description
                              "Specify peak rate";
                            tailf:cli-hide-in-submode;
                            tailf:cli-optional-in-sequence;
                            type enumeration {
                              enum "pdp";
                            }
                          }
                          leaf peak-burst {
                            description
                              "Specify 'peak-burst' parameter for 'peak-rate'";
                            tailf:cli-hide-in-submode;
                            tailf:cli-optional-in-sequence;
                            when "../peak-rate";
                            type police-burst-type;
                          }
                          uses police-action-grouping;
                        }
                      }
                    }
                  }
                }
                // police target-bit-rate  <bits per second>
                case police-target-bitrate-case {
                  container police-target-bitrate {
                    tailf:cli-no-keyword;
                    tailf:cli-drop-node-name;
                    container police {
                      tailf:cli-drop-node-name;
                      when "../../action-type = 'police'" {
                        tailf:dependency "../../action-type";
                      }
                      tailf:cli-add-mode;
                      tailf:cli-mode-name "config-pmap-c-police";
                      leaf bit-rate {
                        description
                          "Target bit rate (bits per second) (postfix k, m, g optional),decimal point allowed";
                        tailf:cli-no-keyword;
                        tailf:cli-drop-node-name;
                        tailf:cli-hide-in-submode;
                        type uint64 {
                          range "8000..10000000000";
                        }
                      }
                      leaf burst-byte {
                        description 
                          "Burst Byte";
                        tailf:cli-no-keyword;
                        tailf:cli-drop-node-name;
                        tailf:cli-hide-in-submode;
                        type uint64 {
                          range "64..2596929536";
                        }      
                      }
                      leaf conform-action {
                        description 
                          "action when rate is less than conform burst";
                        tailf:cli-no-keyword;
                        tailf:cli-hide-in-submode;
                        type empty;
                      }
                      leaf transmit {
                        description 
                          "transmit packet";
                        tailf:cli-no-keyword;
                        tailf:cli-hide-in-submode;
                        type empty;
                      }
                      leaf exceed-action {
                        description 
                          "action when rate is within conform and conform + exceed burst";
                        tailf:cli-no-keyword;
                        tailf:cli-hide-in-submode;
                        type empty;
                      }
                      leaf drop {
                        description 
                          "drop packet";
                        tailf:cli-no-keyword;
                        tailf:cli-hide-in-submode;
                        type empty;
                      }
                      leaf set-dscp-transmit {
                        description 
                          "set dscp and send it";
                        tailf:cli-no-keyword;
                        tailf:cli-hide-in-submode;
                        type empty;
                      }
                      leaf dscp {
                        description 
                          "Set packet dscp from dscp";
                        tailf:cli-no-keyword;
                        tailf:cli-hide-in-submode;
                        type empty;
                      }
                      leaf table  {
                        description 
                          "Specify table-map";
                        tailf:cli-no-keyword;
                        tailf:cli-hide-in-submode;
                        type string;
                      }
                      container actions {
                        tailf:cli-no-keyword;
                        tailf:cli-drop-node-name;
                        tailf:cli-flatten-container;
                        // policy-map * / class * / police ? / conform-action
                        uses police-conform-action-grouping;
                        // policy-map * / class * / police ? / exceed-action
                        uses police-exceed-action-grouping;
                        // policy-map * / class * / police ? / violate-action
                        uses police-violate-action-grouping;
                      }
                    }
                  }
                }
                // police flow (policy-map)
                // police flow [mask {dest-only | full-flow | src-only}]
                //    <bps> [<burst-normal>] ACTIONS
                case police-flow-case {
                  container police-flow {
                    tailf:cli-no-keyword;
                    tailf:cli-drop-node-name;
                    container police {
                      tailf:cli-drop-node-name;
                      when "../../action-type = 'police'" {
                        tailf:dependency "../../action-type";
                      }
                      container flow {
                        description
                          "police each flow";
                        tailf:cli-add-mode;
                        tailf:cli-mode-name "config-pmap-c-police";
                        tailf:cli-flatten-container;
                        tailf:cli-sequence-commands {
                          tailf:cli-reset-siblings;
                        }
                        leaf mask {
                          description
                            "flow mask to be used for policing";
                          tailf:cli-hide-in-submode;
                          tailf:cli-optional-in-sequence;
                          type enumeration {
                            enum "dest-only";
                            enum "full-flow";
                            enum "src-only";
                          }
                        }
                        leaf bps {
                          tailf:cli-drop-node-name;
                          tailf:cli-hide-in-submode;
                          type police-bps-type;
                        }
                        leaf burst-normal {
                          tailf:cli-drop-node-name;
                          tailf:cli-hide-in-submode;
                          tailf:cli-optional-in-sequence;
                          type police-burst-type;
                          when "../bps";
                        }
                        uses police-action-grouping;
                      }
                    }
                  }
                }
                // police (Catalyst 4500)
                // police <bps> bps <byte> byte ACTIONS
                case police-catalyst-case {
                  container police-catalyst {
                    tailf:cli-no-keyword;
                    tailf:cli-drop-node-name;
                    container police {
                      tailf:cli-add-mode;
                      tailf:cli-mode-name "config-pmap-c-police";
                      tailf:cli-flatten-container;
                      tailf:cli-drop-node-name;
                      when "../../action-type = 'police'" {
                        tailf:dependency "../../action-type";
                      }
                      tailf:cli-sequence-commands {
                        tailf:cli-reset-siblings;
                      }
                      leaf bps-value {
                        tailf:cli-no-keyword;
                        tailf:cli-drop-node-name;
                        tailf:cli-hide-in-submode;
                        tailf:cli-incomplete-command;
                        type string;
                      }
                      leaf bps {
                        tailf:cli-hide-in-submode;
                        tailf:cli-incomplete-command;
                        type empty;
                      }
                      leaf byte-value {
                        tailf:cli-no-keyword;
                        tailf:cli-drop-node-name;
                        tailf:cli-hide-in-submode;
                        tailf:cli-incomplete-command;
                        type string;
                      }
                      leaf byte {
                        tailf:cli-hide-in-submode;
                        type empty;
                      }
                      container actions {
                        tailf:cli-no-keyword;
                        tailf:cli-break-sequence-commands;
                        tailf:cli-drop-node-name;
                        tailf:cli-flatten-container;
                        tailf:cli-hide-in-submode;
                        // policy-map * / class * / police ? / conform-action
                        uses police-conform-action-grouping;
                        // policy-map * / class * / police ? / exceed-action
                        uses police-exceed-action-grouping;
                        // policy-map * / class * / police ? / violate-action
                        uses police-violate-action-grouping;
                      }
                    }
                  }
                }
                // police (Catalyst C3550)
                // police <bps> <burst> exceed-action {drop | policed-dscp-transmit}]
                case police-switch-case {
                  container police-switch {
                    tailf:cli-no-keyword;
                    tailf:cli-drop-node-name;
                    container police {
                      tailf:cli-compact-syntax;
                      tailf:cli-drop-node-name;
                      when "../../action-type = 'police'" {
                        tailf:dependency "../../action-type";
                      }
                      tailf:cli-sequence-commands {
                        tailf:cli-reset-siblings;
                      }
                      leaf cir {
                        tailf:cli-incomplete-command;
                        tailf:cli-drop-node-name;
                        type uint32 {
                          range "8000..1000000000";
                        }
                      }
                      leaf bc {
                        tailf:cli-drop-node-name;
                        type uint32 {
                          range "8000..2000000";
                        }
                      }
                      leaf exceed-action {
                        description
                          "action when rate is exceeded";
                        type enumeration {
                          enum "drop";
                          enum "policed-dscp-transmit";
                        }
                      }
                    }
                  }
                }
              }
            }
            case priority-case {
              // policy-map * / class * / priority
              container priority {
                tailf:cli-compact-syntax;
                tailf:cli-sequence-commands;
                tailf:cli-drop-node-name;
                when "../action-type = 'priority'";
                leaf level {
                  description
                    "Multi-Level Priority Queue";
                  tailf:cli-optional-in-sequence;
                  type uint8 {
                    range "1..2";
                  }
                }
                choice priority-type {
                  leaf kilo-bits {
                    tailf:cli-drop-node-name;
                    type uint32 {
                      range "8..2000000";
                    }
                  }
                  leaf percent {
                    description
                      "% of total bandwidth";
                    type uint16 {
                      range "1..100";
                    }
                  }
                }
                leaf burst {
                  tailf:cli-drop-node-name;
                  type uint32 {
                    range "32..64000000";
                  }
                }
              }
            }
            case queue-buffers-case {
              // policy-map * / class * / queue-buffers
              container queue-buffers {
                tailf:cli-drop-node-name;
                when "../action-type = 'queue-buffers'";
                leaf ratio {
                  description
                    "Relative buffer size for queue";
                  type uint8 {
                    range "0..100";
                  }
                }
              }
            }
            case queue-limit-case {
              // policy-map * / class * / queue-limit
              container queue-limit {
                tailf:cli-compact-syntax;
                tailf:cli-sequence-commands {
                  tailf:cli-reset-siblings;
                }
                tailf:cli-drop-node-name;
                when "../action-type = 'queue-limit'";
                leaf queue-limit-value {
                  tailf:cli-drop-node-name;
                  type uint32 {
                    range "1..8192000";
                  }
                }
                leaf queue-limit-type {
                  tailf:cli-drop-node-name;
                  type enumeration {
                    enum "bytes";
                    enum "ms";
                    enum "packets";
                    enum "us";
                  }
                }
              }
              container queue-limit-dscp {
                tailf:cli-drop-node-name;
                when "../action-type = 'queue-limit'";
                list dscp {
                  description
                    "parameters for each dscp value";
                  tailf:cli-suppress-mode;
                  tailf:cli-compact-syntax;
                  key dscp-val;
                  leaf dscp-val {
                    type dscp-type;
                  }
                  leaf values {
                    description
                      "dscp values";
                    tailf:cli-prefix-key;
                    type empty;
                  }
                  leaf dscp-val1 {
                    tailf:cli-drop-node-name;
                    type dscp-type;
                  }
                  leaf percent {
                    description
                      "% of threshold";
                    type uint8 {
                      range "0..100";
                    }
                  }
                }
              }
            }
            case random-detect {
              // policy-map * / class * / random-detect
              container random-detect {
                tailf:cli-drop-node-name;
                when "../action-type = 'random-detect'";
                container aggregate {
                  description
                    "aggregate subclasses";
                  tailf:cli-compact-syntax;
                  tailf:cli-sequence-commands {
                    tailf:cli-reset-siblings;
                  }
                  presence "true";
                  leaf minimum-thresh {
                    description
                      "minimum threshold for red aggregate";
                    type uint32 {
                      range "0..1000000";
                    }
                  }
                  leaf maximum-thresh {
                    description
                      "maximum threshold for red aggregate";
                    type uint32 {
                      range "0..1000000";
                    }
                  }
                  leaf mark-probability {
                    description
                      "mark-probability for red aggregate";
                    type empty;
                  }
                  leaf denominator {
                    tailf:cli-drop-node-name;
                    type uint32 {
                      range "0..65535";
                    }
                  }
                }
                container discard-class {
                  description
                    "parameters for each discard-class value";
                  tailf:cli-compact-syntax;
                  tailf:cli-sequence-commands;
                  leaf dclass {
                    tailf:cli-drop-node-name;
                    tailf:cli-incomplete-command;
                    type uint16 {
                      range "0..7";
                    }
                  }
                  uses random-detect-grouping;
                }
                leaf discard-class-based {
                  description
                    "Enable discard-class-based WRED as drop policy";
                  tailf:cli-full-command;
                  type empty;
                }
                leaf dscp-based {
                  description
                    "Enable dscp-based WRED as drop policy";
                  tailf:cli-full-command;
                  type empty;
                }
                list dscp {
                  description
                    "parameters for each dscp value";
                  tailf:cli-suppress-mode;
                  tailf:cli-sequence-commands;
                  tailf:cli-compact-syntax;
                  key "dscp-val";
                  leaf dscp-val {
                    type dscp-type;
                  }
                  uses random-detect-grouping;
                }
                leaf ecn {
                  description
                    "explicit congestion notification";
                  tailf:cli-full-command;
                  type empty;
                }
                leaf exponential-weighting-constant {
                  description
                    "weight for mean queue depth calculation";
                  tailf:cli-full-command;
                  type uint16 {
                    range "1..16";
                  }
                }
                leaf prec-based {
                  description
                    "Enable precedence-based WRED as drop policy";
                  tailf:cli-full-command;
                  type empty;
                }
                container precedence {
                  description
                    "parameters for each precedence value";
                  tailf:cli-sequence-commands;
                  tailf:cli-compact-syntax;
                  leaf prec {
                    tailf:cli-drop-node-name;
                    tailf:cli-incomplete-command;
                    type precedence-type2;
                  }
                  uses random-detect-grouping;
                }
              }
            }
            case service-policy-case {
              // policy-map * / class * / service-policy
              leaf service-policy {
                tailf:cli-full-command;
                tailf:cli-drop-node-name;
                type string;
                tailf:non-strict-leafref {
                  path "/ios:native/policy-map/name";
                }
              }
            }
            case set-case {
              // policy-map * / class * / set
              container set {
                tailf:cli-drop-node-name;
                when "../action-type = 'set'";
                // policy-map * / class * / set atm-clp
                leaf atm-clp {
                  description
                    "Set ATM CLP bit to 1";
                  tailf:cli-full-command;
                  type empty;
                }
                // policy-map * / class * / set cos
                container cos {
                  description
                    "Set IEEE 802.1Q/ISL class of service/user priority";
                  tailf:cli-compact-syntax;
                  tailf:cli-sequence-commands;
                  choice cos-type {
                    case a {
                      leaf val {
                        tailf:cli-drop-node-name;
                        type uint16 {
                          range "0..7";
                        }
                      }
                    }
                    case b {
                      leaf pack {
                        tailf:cli-drop-node-name;
                        type enumeration {
                          enum "dscp" {
                            tailf:code-name "pack_dscp";
                          }
                          enum "precedence" {
                            tailf:code-name "pack_precedence";
                          }
                          enum "cos";
                          enum "qos-group";
                          enum "wlan";
                        }
                      }
                      leaf user-priority {
                        description
                          "Set value from WLAN user-priority";
                        when "../pack = 'wlan'";
                        type empty;
                      }
                      leaf table {
                        description
                          "Set codepoint value based on tablemap.";
                        tailf:cli-optional-in-sequence;
                        type string;
                        tailf:non-strict-leafref {
                          path "/ios:native/table-map/name";
                        }
                      }
                    }
                  }
                }
                // policy-map * / class * / set discard-class
                leaf discard-class {
                  description
                    "Discard behavior identifier";
                  tailf:cli-full-command;
                  type uint16 {
                    range "0..7";
                  }
                }
                // policy-map * / class * / set dscp
                container dscp {
                  description
                    "Set DSCP in IP(v4) and IPv6 packets";
                  tailf:cli-compact-syntax;
                  container dscp {
                    description 
                      "Set packet dscp from dscp";
                    presence true;
                    leaf table {
                      description 
                        "Set packet dscp from dscp based on table map.";
                      type string;    
                    }
                  }
                  leaf tunnel {
                    description
                      "set tunnel packet dscp";
                    type empty;
                  }
                  leaf dscp-val {
                    tailf:cli-drop-node-name;
                    type dscp-type;
                  }
                }
                // policy-map * / class * / set fr-de
                leaf fr-de {
                  description
                    "Set FR DE bit to 1";
                  tailf:cli-full-command;
                  type empty;
                }
                // policy-map * / class * / set ip
                container ip {
                  description
                    "Set IP specific values";
                  choice ip-choice {
                    container dscp {
                      description
                        "Set IP DSCP (DiffServ CodePointint)";
                      tailf:cli-compact-syntax;
                      leaf tunnel {
                        description
                          "set tunnel packet dscp";
                        type empty;
                      }
                      leaf dscp-val {
                        tailf:cli-drop-node-name;
                        type dscp-type;
                      }
                    }
                    container precedence {
                      description
                        "Set IP precedence";
                      presence "Set IP precedence";
                      leaf precedence-val {
                        tailf:cli-drop-node-name;
                        type precedence-type;
                      }
                    }
                  }
                }
                // policy-map * / class * / set mpls
                container mpls {
                  description
                    "Set MPLS specific values";
                  container experimental {
                    description
                      "Set Experimental value";
                    container imposition {
                      description
                        "Set Experimental value at tag imposition";
                      leaf exp-value {
                        tailf:cli-drop-node-name;
                        tailf:cli-full-command;
                        type uint8 {
                          range "0..7";
                        }
                      }
                      // dscp
                      // precedence
                    }
                    container topmost {
                      description
                        "Set Experimental value  on topmost label";
                      leaf exp-value {
                        tailf:cli-drop-node-name;
                        tailf:cli-full-command;
                        type uint8 {
                          range "0..7";
                        }
                      }
                    }
                  }
                }
                // policy-map * / class * / set qos-group
                container qos-group {
                  description
                    "Set QoS Group";
                  leaf qos-group-value {
                    tailf:cli-drop-node-name;
                    tailf:cli-full-command;
                    type uint8 {
                      range "0..99";
                    }
                  }
                  // dscp
                  // mpls
                  // precedence
                }
              }
            }
            case shape-case {
              // policy-map * / class * / shape
              container shape {
                tailf:cli-drop-node-name;
                when "../action-type = 'shape'";
                // policy-map * / class * / shape adaptive
                leaf adaptive {
                  description
                    "Enable Traffic Shaping adaptation to BECN";
                  tailf:cli-full-command;
                  type uint32 {
                    range "8000..154400000";
                  }
                }
                // policy-map * / class * / shape average
                container average {
                  description
                    "configure token bucket: CIR (bps) [Bc (bits) [Be (bits)]], send out Bc only per interval";
                  tailf:cli-sequence-commands;
                  tailf:cli-compact-syntax;
                  choice average-choice {
                    case a {
                      leaf bit-rate {
                        tailf:cli-drop-node-name;
                        type uint64;
                        //range "8000..154400000";
                      }
                      leaf bits-per-interval-sustained {
                        tailf:cli-drop-node-name;
                        type uint32 {
                          range "256..154400000";
                        }
                      }
                      leaf bits-per-interval-excess {
                        tailf:cli-drop-node-name;
                        type uint32 {
                          range "0..154400000";
                        }
                      }
                    }
                    case b {
                      leaf percent {
                        description
                          "% of interface bandwidth for Committed information rate";
                        type percentage-type;
                      }
                      leaf burst-size-sustained {
                        tailf:cli-incomplete-command;
                        tailf:cli-drop-node-name;
                        type uint16 {
                          range "10..2000";
                        }
                      }
                      leaf ms {
                        description
                          "milliseconds";
                        type empty;
                      }
                      container bse {
                        tailf:cli-drop-node-name;
                        tailf:cli-flatten-container;
                        tailf:cli-sequence-commands;
                        tailf:cli-compact-syntax;
                        leaf burst-size-excess {
                          tailf:cli-incomplete-command;
                          type uint16 {
                            range "10..2000";
                          }
                        }
                        leaf ms {
                          description
                            "milliseconds";
                          type empty;
                        }
                      }
                    }
                  }
                }
                // policy-map * / class * / shape fecn-adapt
                leaf fecn-adapt {
                  description
                    "Enable Traffic Shaping reflection of FECN as BECN";
                  tailf:cli-full-command;
                  type empty;
                }
                // policy-map * / class * / shape fr-voice-adapt
                container fr-voice-adapt {
                  description
                    "Enable rate adjustment depending on voice presence";
                  presence "Enable rate adjustment depending on voice presence";
                  leaf deactivation {
                    type uint16 {
                      range "1..10000";
                    }
                  }
                }
                // policy-map * / class * / shape max-buffers
                leaf max-buffers {
                  tailf:cli-full-command;
                  description
                    "Set Maximum Buffer Limit";
                  type uint16 {
                    range "1..4096";
                  }
                }
              }
            }
            case trust-case {
              // policy-map * / class * / trust
              leaf trust {
                tailf:cli-drop-node-name;
                when "../action-type = 'trust'";
                type enumeration {
                  enum "cos";
                  enum "dscp";
                  enum "ip-precedence";
                }
              }
            }
          }
        }
      }
      // policy-map * / description
      leaf description {
        description
          "Policy-Map description";
        tailf:cli-multi-value;
        type string {
          length "1..200";
        }
      }
      // policy-map * /sequence-interval
      leaf sequence-interval {
        description
          "Enable sequence number capability";
        when "../type = 'appnav'";
        type uint16;
      }
    }
    

    /// ========================================================================
    /// pseudowire-class
    /// ========================================================================
    list pseudowire-class {
      description
        "Pseudowire-class configuration";
      tailf:cli-mode-name "config-pw-class";
      tailf:cli-full-command;
      key "name";
      leaf name {
        type string;
      }
      uses pseudowire-grouping;
    }


    /// ========================================================================
    /// control-plane
    /// ========================================================================
    container control-plane {
      description
        "Configure control plane services";
      tailf:cli-add-mode;
      tailf:cli-mode-name "config-cp";
      presence "true";
      container service-policy {
        leaf input {
          description
            "Assign policy-map to the input of an interface";
          type string;
          tailf:non-strict-leafref {
            path "/ios:native/policy-map/name";
          }
        }
        leaf output {
          description
            "Assign policy-map to the output of an interface";
          type string;
          tailf:non-strict-leafref {
            path "/ios:native/policy-map/name";
          }
        }
      }
    }

    /// ========================================================================
    /// config-register
    /// ========================================================================

    leaf config-register {
      description "Define the configuration register";
      type string {
        tailf:info "<0x0-0xFFFF>  Config register number";
        pattern "[0-9xXa-fA-F].*";
      }
    }


    /// ========================================================================
    /// clock
    /// ========================================================================
    container clock {
      description
        "Configure time-of-day clock";
      container calendar-valid {
        description
          "Calendar time is authoritative";
        presence "true";
      }
      container summer-time {
        description
          "Configure summer (daylight savings) time";
        tailf:cli-compact-syntax;
        tailf:cli-sequence-commands {
          tailf:cli-reset-siblings;
        }
        leaf zone {
          tailf:cli-drop-node-name;
          tailf:cli-incomplete-command;
          tailf:cli-disallow-value "date|recurring";
          type string;
        }
        choice summer-choice {
          case date-case {
            leaf date {
              description
                "Configure absolute summer time";
              type empty;
            }
            leaf start-day {
              tailf:cli-drop-node-name;
              tailf:cli-incomplete-command;
              tailf:cli-break-sequence-commands;
              type uint8 {
                range "1..31";
              }
            }
            leaf start-month {
              tailf:cli-drop-node-name;
              tailf:cli-incomplete-command;
              tailf:cli-break-sequence-commands;
              type month-type;
            }
            leaf start-year {
              tailf:cli-drop-node-name;
              tailf:cli-incomplete-command;
              type uint32 {
                range "1993..2035";
              }
            }
            leaf start-time {
              tailf:cli-drop-node-name;
              tailf:cli-incomplete-command;
              type hhmm-type;
            }
            leaf date-end-day {
              tailf:cli-drop-node-name;
              tailf:cli-incomplete-command;
              type uint8 {
                range "1..31";
              }
            }
            leaf date-end-month {
              tailf:cli-drop-node-name;
              tailf:cli-incomplete-command;
              type month-type;
            }
            leaf date-end-year {
              tailf:cli-drop-node-name;
              tailf:cli-incomplete-command;
              type uint32 {
                range "1993..2035";
              }
            }
            leaf date-end-time {
              tailf:cli-drop-node-name;
              type hhmm-type;
            }
            leaf offset {
              tailf:cli-drop-node-name;
              tailf:cli-optional-in-sequence;
              type uint16 {
                range "1..1440";
              }
            }
          }
          case recurring-case {
            leaf recurring {
              description
                "Configure recurring summer time";
              type empty;
            }
            leaf recurring-start {
              tailf:cli-drop-node-name;
              tailf:cli-incomplete-command;
              type union {
                type uint8 {
                  range "1..4";
                }
                type enumeration {
                  enum "first";
                  enum "last";
                }
              }
            }
            leaf recurring-start-day {
              tailf:cli-drop-node-name;
              tailf:cli-incomplete-command;
              type weekday-type;
            }
            leaf recurring-start-month {
              tailf:cli-drop-node-name;
              tailf:cli-incomplete-command;
              type month-type;
            }
            leaf recurring-start-time {
              tailf:cli-drop-node-name;
              tailf:cli-incomplete-command;
              type hhmm-type;
            }
            leaf recurring-end {
              tailf:cli-drop-node-name;
              tailf:cli-incomplete-command;
              type union {
                type uint8 {
                  range "1..4";
                }
                type enumeration {
                  enum "first";
                  enum "last";
                }
              }
            }
            leaf recurring-end-day {
              tailf:cli-drop-node-name;
              tailf:cli-incomplete-command;
              type weekday-type;
            }
            leaf recurring-end-month {
              tailf:cli-drop-node-name;
              tailf:cli-incomplete-command;
              type month-type;
            }
            leaf recurring-end-time {
              tailf:cli-drop-node-name;
              type hhmm-type;
            }
            leaf recurring-offset {
              tailf:cli-drop-node-name;
              tailf:cli-optional-in-sequence;
              type uint16 {
                range "1..1440";
              }
            }
          }
        }
      }
      container timezone {
        description
          "Configure time zone";
        tailf:cli-compact-syntax;
        tailf:cli-sequence-commands {
          tailf:cli-reset-siblings;
        }
        leaf zone {
          tailf:cli-drop-node-name;
          tailf:cli-incomplete-command;
          type string;
        }
        leaf offset {
          tailf:cli-drop-node-name;
          tailf:cli-optional-in-sequence;
          tailf:cli-incomplete-command;
          type enumeration {
            enum "+";
            enum "-";
          }
        }
        leaf hours {
          tailf:cli-drop-node-name;
          type int8 {
            range "-23..23";
          }
        }
        leaf minutes {
          tailf:cli-drop-node-name;
          type int8 {
            range "0..59";
          }
        }
      }
    }
    

    /// ========================================================================
    /// gatekeeper
    /// ========================================================================
    container gatekeeper {
      description
        "Enter gatekeeper configuration mode";
      tailf:cli-add-mode;
      tailf:cli-mode-name "config-gk";
      leaf shutdown {
        description
          "Shutdown Gatekeeper";
        type empty;
      }
    }


    /// ========================================================================
    /// line
    /// ========================================================================
    container line {
      description
        "Configure a terminal line";
      /// line  0-17 >
      list line-list {
        tailf:cli-drop-node-name;
        tailf:cli-mode-name "config-line";
        key "first-number";
        leaf first-number {
          description
            "First Line number";
          type uint8 {
            range "0..17";
          }
        }
        leaf last-number {
          tailf:cli-drop-node-name;
          tailf:cli-hide-in-submode;
          type uint16 {
            range "1..17";
          }
        }
        uses line-grouping;
      }
      list aux {
        description
          "Auxiliary line";
        tailf:cli-full-command;
        tailf:cli-mode-name "config-line";
        key "first";
        max-elements "1";
        leaf first {
          type enumeration {
            enum "0";
          }
        }
        uses line-grouping;
      }
      list console {
        description
          "Primary terminal line";
        tailf:cli-full-command;
        tailf:cli-mode-name "config-line";
        tailf:cli-allow-key-abbreviation;
        key "first";
        max-elements "1";
        leaf first {
          type enumeration {
            enum "0";
          }
        }
        uses line-grouping;
      }
      list vty {
        description
          "Virtual terminal";
        tailf:cli-mode-name "config-line";
        key "first";
        leaf first {
          type uint16 {
            range "0..1869";
          }
        }
        leaf last {
          tailf:cli-drop-node-name;
          tailf:cli-hide-in-submode;
          type uint16 {
            range "1..1869";
          }
        }
        uses line-grouping;
      }
    }

    /// ========================================================================
    /// logging
    /// ========================================================================
    container logging {
      description
        "Modify message logging facilities";
      leaf hostip {
        tailf:cli-drop-node-name;
        type inet:host;
      }
      list discriminator {
        description
          "Create or modify a message discriminator";
        tailf:cli-suppress-mode;
        key "name";
        leaf name {
          type string;
        }
        container msg-body {
          description
            "Msg-body pattern for messsage filtering";
          leaf includes {
            description
              "To deliver messages including the specified regular expression string";
            type string;
          }
        }
      }
      container persistent {
        description
          "Set persistent logging parameters";
        presence "true";
        container file {
          tailf:cli-reset-container;
          tailf:cli-compact-syntax;
          tailf:cli-drop-node-name;
          leaf url {
            description
              "URL to store logging messages";
            type string;
          }
          leaf size {
            description
              "Set disk space for writing log messages";
            type string;
          }
          leaf threshold {
            description
              "Set threshold for logging persistent";
            type string;
          }
          leaf protected {
            description
              "Eliminates manipulation on logging-persistent files";
            type empty;
          }
        }
      }
      // <no> logging monitor
      container monitor-conf {
        tailf:cli-no-keyword;
        tailf:cli-drop-node-name;
        leaf monitor {
          tailf:cli-boolean-no;
          type boolean;
        }
      }
      // logging monitor
      container monitor {
        description
          "Set terminal line (monitor) logging parameters";
        tailf:cli-reset-container;
        tailf:cli-compact-syntax;
        presence "true";
        leaf severity {
          tailf:cli-drop-node-name;
          tailf:cli-disallow-value "discriminator";
          tailf:cli-full-command;
          type logging-level-type;
        }
        list discriminator {
          description
            "Establish MD-Console association";
          tailf:cli-suppress-mode;
          key "name";
          leaf name {
            type string;
          }
          leaf severity {
            tailf:cli-drop-node-name;
            tailf:cli-full-command;
            type logging-level-type;
          }
        }
      }
      leaf alarm {
        description
          "Configure syslog for alarms";
        tailf:cli-full-command;
        tailf:cli-no-value-on-delete;
        type union {
          type uint8 {
            range "1..4";
          }
          type enumeration {
            enum "critical";
            enum "informational";
            enum "major";
            enum "minor";
          }
        }
      }
      container buffered-conf {
        tailf:cli-no-keyword;
        tailf:cli-drop-node-name;
        leaf buffered {
          description
            "Set buffered logging parameters";
          tailf:cli-boolean-no;
          type boolean;
        }
      }
      container buffered {
        description
          "Set buffered logging parameters";
        tailf:cli-display-separated;
        tailf:cli-incomplete-no;
        list discriminator {
          tailf:cli-suppress-mode;
          key "name";
          leaf name {
            type string;
          }
          leaf severity {
            tailf:cli-drop-node-name;
            tailf:cli-full-command;
            type logging-level-type;
          }
        }
        leaf size {
          tailf:cli-drop-node-name;
          type uint32 {
            range "4096..2147483647";
          }
        }
        leaf severity {
          tailf:cli-drop-node-name;
          tailf:cli-full-command;
          type logging-level-type;
        }
        leaf xxml {
          tailf:alt-name "xml";
          description
            "Enable logging in XML to XML logging buffer";
          tailf:cli-full-command;
          type uint32 {
            range "4096..2147483647";
          }
        }
      }
      container console-conf {
        tailf:cli-no-keyword;
        tailf:cli-drop-node-name;
        leaf console {
          description
            "Set console logging parameters";
          tailf:cli-boolean-no;
          type boolean;
        }
      }
      container console {
        description
          "Set console logging parameters";
        tailf:cli-reset-container;
        tailf:cli-compact-syntax;
        presence "true";
        list discriminator {
          description
            "Establish MD-Console association";
          tailf:cli-suppress-mode;
          key "name";
          leaf name {
            type string;
          }
          leaf severity {
            tailf:cli-drop-node-name;
            tailf:cli-full-command;
            type logging-level-type;
          }
        }
        leaf filtered {
          description
            "Enable filtered logging";
          type empty;
        }
        leaf guaranteed {
          description
            "Guarantee console messages";
          tailf:cli-full-command;
          type empty;
        }
        leaf xxml {
          description
            "Enable logging in XML";
          tailf:cli-full-command;
          type logging-level-type;
        }
        leaf severity {
          tailf:cli-drop-node-name;
          tailf:cli-full-command;
          type logging-level-type;
        }
      }
      container event {
        description
          "Global interface events";
        container link-status {
          description
            "Globally enable/disable link UPDOWN message";
          leaf boot {
            description
              "Supress/Allow link UPDOWN messages during boot";
            type empty;
          }
          leaf global {
            type empty;
          }
          leaf default {
            description
              "Link UPDOWN messages for all interfaces";
            type empty;
          }
        }
      }
      container esm {
        description
          "Set ESM filter restrictions";
        leaf config {
          description
            "Permit/Deny configuration changes from ESM filters";
          tailf:cli-full-command;
          type empty;
        }
      }
      leaf facility {
        description
          "Facility parameter for syslog messages";
        type enumeration {
          enum "auth";
          enum "cron";
          enum "daemon";
          enum "kern";
          enum "local0";
          enum "local1";
          enum "local2";
          enum "local3";
          enum "local4";
          enum "local5";
          enum "local6";
          enum "local7";
          enum "lpr";
          enum "mail";
          enum "news";
          enum "sys10";
          enum "sys11";
          enum "sys12";
          enum "sys13";
          enum "sys14";
          enum "sys9";
          enum "syslog";
          enum "user";
          enum "uucp";
        }
      }
      container history {
        description
          "Configure syslog history table";
        leaf size {
          description
            "Set history table size";
          type uint16;
        }
        leaf severity-level {
          tailf:cli-drop-node-name;
          type union {
            type uint8 {
              range "0..7";
            }
            type enumeration {
              enum "alerts";
              enum "critical";
              enum "debugging";
              enum "emergencies";
              enum "errors";
              enum "informational";
              enum "notifications";
              enum "warnings";
            }
          }
        }
      }
      // logging hostname 
      list hostname {
        description
          "Hostname or A.B.C.D;;IP address of the logging host";
        tailf:cli-drop-node-name;
        tailf:cli-suppress-mode;
        tailf:cli-delete-when-empty;
        key "host";
        leaf host {
          tailf:cli-disallow-value "esm|alarm|buffered|facility|history|rate-limit|source-interface|host|console|discriminator|monitor";
          tailf:cli-full-command;
          type inet:host;
        }
      }
      // logging host *
      list host {
        description
          "Set syslog server IP address and parameters";
        tailf:cli-suppress-mode;
        tailf:cli-delete-when-empty;
        tailf:cli-compact-syntax;
        key "host";
        leaf host {
          tailf:cli-disallow-value "esm|alarm|buffered|facility|history|rate-limit|source-interface|host";
          tailf:cli-full-command;
          type inet:host;
        }
        leaf vrf {
          description
            "Set VRF option";
          type string;
        }
        leaf discriminator {
          description
            "Specify a message discriminator identifier for this logging session";
          type string;
        }
        //  filtered              Enable filtered logging
        //  sequence-num-session  Include session sequence number tag in
        //                        syslog message
        //  session-id            Specify syslog message session ID tagging
        //  transport             Specify the transport protocol (default=UDP)
        //  xml                   Enable logging in XML
      }
      // <no> logging rate-limit
      container rate-limit-conf {
        tailf:cli-no-keyword;
        tailf:cli-drop-node-name;
        leaf rate-limit {
          tailf:cli-boolean-no;
          type boolean;
        }
      }
      // logging rate-limit
      container rate-limit {
        description
          "Set messages per second limit";
        tailf:cli-sequence-commands;
        tailf:cli-compact-syntax;
        tailf:cli-reset-container;
        tailf:cli-show-no;
        tailf:cli-delete-when-empty;
        presence true;
        container console {
                description
                     "Rate limit only console messages";
                list range {
                    tailf:cli-drop-node-name;
                    tailf:cli-suppress-mode;
                    key "range";
                    leaf range {
                        description
                             "Messages per second";
                        type uint16 {
                            range "1..10000";
                        }
                    }
                    container except {
                        description
                             "Messages of this severity or higher";
                        presence true;
                        leaf range {
                            description
                                 "Logging severity level";
                            tailf:cli-drop-node-name;
                            type uint8 {
                                range "0..7";
                            }
                        }
                        leaf alerts {
                            description
                                 "Immediate action needed           (severity=1)";
                            tailf:cli-full-command;
                            type empty;
                        }
                        leaf critical {
                            description
                                 "Critical conditions               (severity=2)";
                            tailf:cli-full-command;
                            type empty;
                        }
                        leaf debugging {
                            description
                                 "Debugging messages                (severity=7)";
                            tailf:cli-full-command;
                            type empty;
                        }
                        leaf emergencies {
                            description
                                 "System is unusable                (severity=0)";
                            tailf:cli-full-command;
                            type empty;
                        }
                        leaf errors {
                            description
                                 "Error conditions                  (severity=3)";
                            tailf:cli-full-command;
                            type empty;
                        }
                        leaf informational {
                            description
                                 "Informational messages            (severity=6)";
                            tailf:cli-full-command;
                            type empty;
                        }
                        leaf notifications {
                            description
                              "Normal but significant conditions (severity=5)";
                            tailf:cli-full-command;
                            type empty;
                        }
                        leaf warnings {
                            description
                               "Warning conditions (severity=4)";
                            tailf:cli-full-command;
                            type empty;
                        }
                    }
                }
       container all {
                    description
                       "Rate limit all messages, including debug messages";
                    list range {
                        tailf:cli-drop-node-name;
                        tailf:cli-suppress-mode;
                        key "range";
                        leaf range {
                            description
                                 "Messages per second";
                            type uint16 {
                                range "1..10000";
                            }
                        }
                        container except {
                            description
                                 "Messages of this severity or higher";
                            presence true;
                            leaf range {
                                description
                                     "Logging severity level";
                                tailf:cli-drop-node-name;
                                type uint8 {
                                    range "0..7";
                                }
                            }
                            leaf alerts {
                                description
                                  "Immediate action needed (severity=1)";
                                  tailf:cli-full-command;
                                type empty;
                            }
                            leaf critical {
                                description
                                  "Critical conditions  (severity=2)";
                                  tailf:cli-full-command;
                                type empty;
                            }
                            leaf debugging {
                                description
                                  "Debugging messages (severity=7)";
                                  tailf:cli-full-command;
                                type empty;
                            }
                            leaf emergencies {
                                description
                                  "System is unusable (severity=0)";
                                  tailf:cli-full-command;
                                type empty;
                            }
                            leaf errors {
                                description
                                  "Error conditions (severity=3)";
                                  tailf:cli-full-command;
                                type boolean;
                            }
                            leaf informational {
                                description
                                   "Informational messages (severity=6)";
                                   tailf:cli-full-command;
                                type empty;
                            }
                            leaf notifications {
                                description
                                   "Normal but significant conditions (severity=5)";
                                   tailf:cli-full-command;
                                type empty;
                            }
                            leaf warnings {
                                description
                                  "Warning conditions (severity=4)";
                                  tailf:cli-full-command;
                                type empty;
                            }
                        }
                    }
                }
            } /*ENd Console */ 
      }/*ENd rate-limit*/
      // logging source-interface
      container source-interface {
        description
          "Specify interface for source address in logging transactions";
        tailf:cli-diff-dependency "/ios:native/interface";
        uses interface-grouping;
        leaf vrf {
          description
            "Specify the vrf of source interface for logging transactions";
          type string;
        }
      }
      // logging snmp-trap
      container snmp-trap {
        description
          "Set SNMP trap logging level";
        leaf alerts {
          description
            "Immediate action needed           (severity=1)";
          tailf:cli-full-command;
          type empty;
        }
        leaf critical {
          description
            "Critical conditions               (severity=2)";
          tailf:cli-full-command;
          type empty;
        }
        leaf debugging {
          description
            "Debugging messages                (severity=7)";
          tailf:cli-full-command;
          type empty;
        }
        leaf emergencies {
          description
            "System is unusable                (severity=0)";
          tailf:cli-full-command;
          type empty;
        }
        leaf errors {
          description
            "Error conditions                  (severity=3)";
          tailf:cli-full-command;
          type empty;
        }
        leaf informational {
          description
            "Informational messages            (severity=6)";
          tailf:cli-full-command;
          type empty;
        }
        leaf notifications {
          description
            "Normal but significant conditions (severity=5)";
          tailf:cli-full-command;
          type empty;
        }
        leaf warnings {
          description
            "Warning conditions                (severity=4)";
          tailf:cli-full-command;
          type empty;
        }
      }
      leaf trap {
        description
          "Set trap server logging level";
        tailf:cli-full-command;
        type union {
          type uint8 {
            range "0..7";
          }
          type enumeration {
            enum "alerts";
            enum "critical";
            enum "debugging";
            enum "emergencies";
            enum "errors";
            enum "informational";
            enum "notifications";
            enum "warnings";
          }
        }
      }
      container file {
        description
          "Set logging file parameters";
        tailf:cli-sequence-commands {
          tailf:cli-reset-all-siblings;
        }
        tailf:cli-compact-syntax;
        tailf:cli-incomplete-command;
        leaf name {
          tailf:cli-drop-node-name;
          type string;
        }
        leaf max-size {
          tailf:cli-drop-node-name;
          tailf:cli-optional-in-sequence;
          type uint32;
        }
        leaf min-size {
          tailf:cli-drop-node-name;
          tailf:cli-optional-in-sequence;
          type uint32;
        }
        leaf severity {
          tailf:cli-drop-node-name;
          tailf:cli-full-command;
          type logging-level-type;
        }
      }
    }
    
    /// ========================================================================
    /// login
    /// ========================================================================
    container login {
      description
        "Enable secure login checking";
      container on-failure {
        description
          "Set options for failed login attempt";
        presence "true";
        container log {
          description
            "Generate syslogs on failure logins";
          presence "true";
          leaf every {
            description
              "Periodicity for logs generated";
            type uint16 {
              range "1..65535";
            }
          }
        }
      }
      container on-success {
        description
          "Set options for successful login attempt";
        presence "true";
        container log {
          description
            "Generate syslogs on successful logins";
          presence "true";
          leaf every {
            description
              "Periodicity for logs generated";
            type uint16 {
              range "1..65535";
            }
          }
        }
      }
    }

    /// ========================================================================
    /// mgcp
    /// ========================================================================
    container mgcp {
      description
        "Enable Media Gateway Control Protocol";
      container behavior {
        leaf rsip-range {
          type enumeration {
            enum "tgcp-only";
          }
        }
        leaf comedia-role {
          type enumeration {
            enum "none";
          }
        }
        leaf comedia-check-media-src {
          type enumeration {
            enum "disable";
          }
        }
        leaf comedia-sdp-force {
          type enumeration {
            enum "disable";
          }
        }
      }
      container fax {
        description
          "Configure MGCP Fax Parameters";
        container t38 {
          description
            "Configure MGCP Fax T.38 Parameters";
          leaf ecm {
            description
              "Enable Error Correction Mode (ECM)";
            tailf:cli-full-command;
            type empty;
          }
        }
      }
      container profile {
        description
          "MGCP profile configuration mode";
        leaf default {
          description
            "Configure MGCP default profile";
          type empty;
        }
      }
    }

    /// ========================================================================
    /// multilink
    /// ========================================================================
    container multilink {
      description
        "PPP multilink global configuration";
      leaf bundle-name {
        description
          "Select method for naming multilink bundles";
        tailf:cli-full-command;
        type enumeration {
          enum "authenticated";
          enum "both";
          enum "endpoint";
          enum "rfc";
        }
      }
      leaf virtual-template {
        description
          "virtual-template interface";
        tailf:cli-full-command;
        type uint16 {
          range "1..4095";
        }
      }
    }

    /// ========================================================================
    /// ntp
    /// ========================================================================
    container ntp {
      description
        "Configure NTP";
      tailf:cli-diff-dependency "/ios:native/interface";
      container access-group {
        description
          "Control NTP access";
        container ipv4 {
          description
            "ipv4 access lists";
          uses ntp-access-group-grouping;
        }
        container ipv6 {
          description
            "ipv6 access lists";
          uses ntp-access-group-grouping;
        }
        uses ntp-access-group-grouping;
      }
      container allow {
        description
          "Allow processing of packets";
        container mode {
          description
            "Allow processing of particular mode packets";
          container control {
            description
              "Allow processing control mode packets";
            presence "true";
            leaf delay {
              tailf:cli-drop-node-name;
              description
                "Rate limiting delay (s)";
              type uint8 {
                range "3..15";
              }
            }
          }
          leaf private {
            description
              "Allow processing private mode packets";
            tailf:cli-full-command;
            type empty;
          }
        }
      }
      leaf authenticate {
        description
          "Authenticate time sources";
        type empty;
      }
      list authentication-key {
        description
          "Authentication key for trusted time sources";
        tailf:cli-suppress-mode;
        tailf:cli-compact-syntax;
        tailf:cli-sequence-commands;
        key "number";
        leaf number {
          type uint32;
        }
        leaf md5 {
          description
            "MD5 authentication";
          type string;
        }
        leaf encryption-type {
          tailf:cli-drop-node-name;
          tailf:cli-optional-in-sequence;
          type uint32;
        }
      }
      leaf broadcastdelay {
        description
          "Estimated round-trip delay in microseconds";
        tailf:cli-full-command;
        type uint32 {
          range "1..999999";
        }
      }
      leaf clock-period {
        description
          "Length of hardware clock tick";
        type uint32;
      }
      // authenticate  Authenticate time sources
      // authentication-key Authentication key for trusted time sources
      // broadcastdelay  Estimated round-trip delay

      // should be ignored, stripped by the java code
      // leaf clock-period {
      //   tailf:info "Length of hardware clock tick";
      //   type uint32 {
      //     tailf:info "<0-4294967295>;;Clock period in 2^-32 seconds";
      //   }
      // }
      
      // logging Enable NTP message logging
      // ntp logging
      leaf logging {
        description
          "Enable NTP message logging";
        tailf:cli-full-command;
        type empty;
      }
      // master Act as NTP master clock
      // ntp master
      container master {
        description
          "Act as NTP master clock";
        presence "true";
        leaf stratum-number {
          tailf:cli-drop-node-name;
          type uint8 {
            range "1..15";
          }
        }
      }
      // max-associations Set maximum number of associations
      // ntp max-associations
      leaf max-associations {
        description
          "Set maximum number of associations";
        tailf:cli-full-command;
        type uint32;
      }
      leaf maxdistance {
        description
          "Maximum Distance for synchronization";
        tailf:cli-full-command;
        type uint8 {
          range "1..16";
        }
      }
      leaf mindistance {
        description
          "Minimum distance to consider for clockhop";
        tailf:cli-full-command;
        type uint16 {
          range "1..500";
        }
      }
      //ntp orphan
      leaf orphan {
        description
          "Threshold Stratum for orphan mode";
        tailf:cli-full-command;
        type uint8 {
          range "1..16";
        }
      }
      //ntp panic
      container panic {
        description
          "Reject time updates > panic threshold (default 1000Sec)";
        leaf update {
          description
            "Reject time updates > panic threshold (default 1000Sec)";
          type empty;
        }
      }
      //ntp passive
      leaf passive {
        description
          "NTP passive mode";
        tailf:cli-full-command;
        type empty;
      }
      //ntp peer
      // peer Configure NTP peer
      container peer {
        description
          "Configure NTP peer";
        uses ntp-peer-server-grouping;
        list vrf {
          description
            "VPN Routing/Forwarding Information";
          tailf:cli-suppress-mode;
          tailf:cli-delete-when-empty;
          tailf:cli-compact-syntax;
          tailf:cli-reset-container;
          tailf:cli-incomplete-command;
          tailf:cli-diff-dependency "/ios:native/vrf/definition";
          tailf:cli-diff-dependency "/ios:native/ip/vrf";
          key "name";
          leaf name {
            type string;
          }
          uses ntp-peer-server-grouping;
        }
      }
      // ntp server
      container server {
        description
          "Configure NTP server";
        uses ntp-peer-server-grouping;
        list vrf {
          description
            "VPN Routing/Forwarding Information";
          tailf:cli-suppress-mode;
          tailf:cli-delete-when-empty;
          tailf:cli-compact-syntax;
          tailf:cli-reset-container;
          tailf:cli-incomplete-command;
          tailf:cli-diff-dependency "/ios:native/vrf/definition";
          tailf:cli-diff-dependency "/ios:native/ip/vrf";
          key "name";
          leaf name {
            type string;
          }
          uses ntp-peer-server-grouping;
        }
      }
      // ntp source
      container source {
        description
          "Configure interface for source address";
        uses interface-grouping;
      }
      // trusted-key Key numbers for trusted time sources
      list trusted-key {
        description
          "Key numbers for trusted time sources";
        tailf:cli-suppress-mode;
        key "number";
        leaf number {
          type uint16;
        }
        leaf end-key {
          tailf:alt-name "-";
          description
            "End Key";
          tailf:cli-allow-join-with-value {
            tailf:cli-display-joined;
          }
          type uint16;
        }
      }
      // ntp update-calender
      leaf update-calendar {
        description
          "Periodically update calendar with NTP time";
        type empty;
      }
    }
    
    /// ========================================================================
    /// no mac-address-table
    /// ========================================================================
    container mac-address-table {
      description
        "Configure the MAC address table";
      container evc-xconnect {
        description
          "All ethernet virtual connections xconnect";
        leaf l2pt-forward-all {
          description
            "Layer 2 Protocol Forward All";
          type empty;
        }
      }
      container limit {
        description
          "Enter parameters for mac limit feature";
        list bdomain {
          description
            "bdomain number for  mac limit feature";
          tailf:cli-suppress-mode;
          tailf:cli-delete-when-empty;
          key "number";
          leaf number {
            type uint16 {
              range "1..4095";
            }
          }
          leaf action {
            description
              "Enter action";
            tailf:cli-full-command;
            type enumeration {
              enum "warning";
              enum "limit";
              enum "shutdown";
            }
          }
          leaf maximum {
            description
              "Enter max allowed entries";
            type uint32 {
              range "0..16000";
            }
          }
        }
      }
      container learning {
        description
          "Enable a MAC table learning feature";
        list vlan {
          description
            "Layer 2 table learning per VLAN";
          tailf:cli-suppress-mode;
          tailf:cli-delete-when-empty;
          key "id";
          leaf id {
            type uint16 {
              range "1..4094";
            }
          }
          leaf module {
            description
              "Layer 2 table learning per VLAN per module";
            type uint8 {
              range "1..9";
            }
          }
        }
      }
    }
    
    /// ========================================================================
    /// privilege
    /// ========================================================================
    container privilege {
      description
        "Command privilege parameters";
      // privilege exec
      container exec {
        description
          "Exec mode";
        // privilege exec level
        list level {
          description
            "Set privilege level of command";
          tailf:cli-suppress-mode;
          tailf:cli-delete-when-empty;
          tailf:cli-compact-syntax;
          tailf:cli-incomplete-command;
          tailf:cli-no-key-completion;
          key "privilege";
          leaf privilege {
            tailf:cli-incomplete-command;
            tailf:cli-incomplete-no;
            tailf:cli-suppress-range;
            type uint8;
          }
          list command-list {
            tailf:cli-suppress-mode;
            tailf:cli-delete-when-empty;
            tailf:cli-drop-node-name;
            tailf:cli-compact-syntax;
            tailf:cli-show-long-obu-diffs;
            tailf:cli-no-key-completion;
            tailf:cli-suppress-key-abbreviation;
            tailf:cli-no-match-completion;
            ordered-by user;
            key "command";
            leaf command {
              tailf:cli-drop-node-name;
              tailf:cli-multi-word-key;
              type string {
                pattern "(show.*)|(write.*)";
              }
            }
          }
        }
      }
    }

    /// ========================================================================
    /// redundancy
    /// ========================================================================
    container redundancy {
      description
        "Enter redundancy mode";
      tailf:cli-add-mode;
      tailf:cli-mode-name "config-red";
      presence true;
      // redundancy maintenance-mode
      leaf maintenance-mode {
        description
          "Enable/Disable maintenance mode ";
        type empty;
      }
      // redundancy main-cpu
      container main-cpu {
        description
          "Enter main-cpu mode";
        tailf:cli-add-mode;
        presence true;
        container auto-sync {
          leaf running-config {
            type empty;
          }
          leaf config-register {
            type empty;
          }
          leaf bootvar {
            type empty;
          }
          leaf standard {
            type empty;
          }
        }
        container standby {
           description 
             "Standby";
           container console {
              description 
                "Console";
              leaf enable {
                 description 
                   "Enable";
                 type empty;
              }
           }
           container initialization {
              description 
                "Initialization";
              container delay {
                 description 
                   "Delay";
                 tailf:cli-sequence-commands;
                 tailf:cli-compact-syntax;
                 leaf second {
                    tailf:cli-drop-node-name;
                    description 
                      "Delay value in seconds";
                    type uint16 {
                       range "30..1800";
                    }
                 }
                 leaf boot-only {
                    description 
                      "Delay effective only on system boot";
                    tailf:cli-optional-in-sequence;
                    type empty;
                 }                 
              }
           }
        }
      }
       // redundancy mode
      leaf mode {
        description
          "redundancy mode for this chassis";
        type enumeration {
          enum "rpr";
          enum "rpr-plus";
          enum "sso";
          enum "none";
        }
      }
      leaf notification-timer {
        description
          "Specify Redundancy notification timer (milliseconds)";
        type uint16 {
            range "8000..30000";
        }
      }
      container policy {
         description 
           "redundancy policy enforcement";
         container config-sync {
            description 
              "config sync parameters";
            container bulk {
               description 
                 "bulk configuration mode";
               container prc {
                  description 
                    "prc policy enforcement";
                  leaf reload {
                     description 
                       "reload standby";
                     tailf:cli-boolean-no;
                     type boolean;
                  }
               }
            }
            container lbl {
               description 
                 "line-by-line configuration mode";
               container prc {
                  description 
                    "prc policy enforcement";
                  leaf reload {
                     description 
                       "reload standby";
                     tailf:cli-boolean-no;
                     type boolean;
                  }
               }
            }
         }
      }
      container timer {
         description 
           "Select a timer to configure";
         leaf rpso {
            description 
              "Delay value in seconds";
            type uint16 {
               range "120..1200";
            }
         }
      }
      container interchassis {
        description
          "Enter interchassis mode";
        list group {
          description
            "Enter the redundancy group number";
          tailf:cli-mode-name "config-r-ic";
          key "group-number";
          leaf group-number {
            type uint64 {
              range "1..4294967295";
            }
          }
          container monitor {
            description
              "define the peer monitoring method";
            tailf:cli-compact-syntax;
            tailf:cli-sequence-commands {
              tailf:cli-reset-siblings;
            }
            leaf peer {
              description
                "the peer method";
              type empty;
            }
            leaf bfd {
              description
                "set peer monitoring method to bfd";
              type empty;
            }
          }
          container member {
            description
              "specify a redundancy group member";
            leaf ip {
              description
                "specify the redundancy group member using an ip address";
              type inet:ipv4-address;
            }
          }
          container backbone {
            description
              "specify a redundancy group member";
            container interface {
              uses interface-grouping;
            }
          }
        }
      }
    }

    /// ========================================================================
    /// scheduler
    /// ========================================================================
    container scheduler {
      description
        "Scheduler parameters";
      container runtime {
        description "Process runtime controls";
        leaf netinput {
          description "Process-switching run time (in milliseconds)";
          type uint16 {
            range "100..40000";
          }
        }
      }
      container allocate {
        tailf:cli-sequence-commands;
        tailf:cli-compact-syntax;
        description
          "Guarantee CPU time for processes";
        leaf interrupt-time {
          tailf:cli-drop-node-name;
          tailf:cli-incomplete-command;
          type uint16 {
            range "400..60000";
          }
        }
        leaf process-time {
          tailf:cli-drop-node-name;
          type uint16 {
            range "100..4000";
          }
        }
      }
    }
    /// =======================================================================
    /// epm
    ///===================================================================
    container epm {
      description "EPM Global Configuration Commands";
      leaf logging {
        description "Enable EPM logging";
        type empty;
        }
    }

    /// ========================================================================
    /// spanning-tree
    /// ========================================================================
    container spanning-tree {
      description
        "Spanning Tree Subsystem";
      leaf backbonefast {
        description
          "Enable BackboneFast Feature";
        type empty;
      }
      container bridge {
        leaf priority {
          type uint8;
        }
        leaf ID {
          type string;
        }
      }
      // spanning-tree etherchannel
      container etherchannel {
        description
          "Spanning tree etherchannel specific configuration";
        container guard {
          description
            "Configure guard features for etherchannel";
          leaf misconfig {
            description
              "Enable guard to protect against etherchannel misconfiguration";
            type empty;
          }
        }
      }
      // spanning-tree extend
      container extend {
        description
          "Spanning Tree 802.1t extensions";
        leaf system-id {
          description
            "Extend system-id into priority portion of the bridge id (PVST & Rapid PVST only)";
          type empty;
        }
      }
      //  logging       Enable Spanning tree logging
      leaf logging {
        description
          "Enable Spanning tree logging";
        tailf:cli-full-command;
        type empty;
      }
      // spanning-tree loopguard
      container loopguard {
        description
          "Spanning tree loopguard options";
        leaf default {
          description
            "Enable loopguard by default on all ports";
          type empty;
        }
      }
      // spanning-tree mst
      container mst {
        description
          "Multiple spanning tree configuration";
        list instance-range {
          tailf:cli-suppress-mode;
          tailf:cli-delete-when-empty;
          tailf:cli-drop-node-name;
          tailf:cli-compact-syntax;
          tailf:cli-range-list-syntax;
          key "id";
          leaf id {
            type union {
              type uint16;
              type string;
            }
          }
          leaf priority {
            description
              "Set the bridge priority for the spanning tree";
            type uint16 {
              range "0..61440";
            }
          }
          leaf root {
            description
              "Configure switch as root";
            type enumeration {
              enum "primary";
              enum "secondary";
            }
          }
        }
        // spanning-tree mst configuration
        container configuration {
          description
            "Enter MST configuration submode";
          tailf:cli-add-mode;
          tailf:cli-mode-name "config-mst";
          tailf:cli-explicit-exit;
          leaf name {
            description
              "Set configuration name";
            type string;
          }
          list instance {
            description
              "Map vlans to an MST instance";
            tailf:cli-suppress-mode;
            tailf:cli-delete-when-empty;
            key "id";
            leaf id {
              type uint16 {
                range "0..4094";
              }
            }
            leaf-list vlan {
              description
                "Range of vlans to add to the instance mapping";
              tailf:cli-range-list-syntax;
              type union {
                type uint16;
                type string;
              }
            }
          }
          //  private-vlan  Set private-vlan synchronization
          container private-vlan {
            description
              "Set private-vlan synchronization";
            leaf synchronize {
              description
                "Synchronize vlans";
              type empty;
            }
          }
          //  revision      Set configuration revision number
          leaf revision {
            description
              "Set configuration revision number";
            type uint16;
          }
        }
        //  forward-time   Set the forward delay for the spanning tree
        leaf forward-time {
          description
            "number of seconds for the forward delay timer";
          type uint8 {
            range "4..30";
          }
        }
        //  hello-time     Set the hello interval for the spanning tree
        leaf hello-time {
          description
            "number of seconds between generation of config BPDUs";
          type uint8 {
            range "1..10";
          }
        }
        //  max-age        Set the max age interval for the spanning tree
        leaf max-age {
          description
            "maximum number of seconds the information in a BPDU is valid";
          type uint8 {
            range "6..40";
          }
        }
        //  max-hops       Set the max hops value for the spanning tree
        leaf max-hops {
          description
            "maximum number of hops a BPDU is valid";
          type uint8 {
            range "1..255";
          }
        }
      }
      // spanning-tree optimize
      container optimize {
        container bpdu {
          leaf transmission {
            tailf:cli-boolean-no;
            tailf:cli-show-no;
            type boolean;
          }
        }
      }
      //  pathcost      Spanning tree pathcost options
      container pathcost {
        description
          "Spanning tree pathcost options";
        container method {
          description
            "Method to calculate default port path cost";
          leaf long {
            description
              "Use 32 bit based values for default port path costs";
            type empty;
          }
          leaf short {
            type empty;
          }
        }
      }
      // spanning-tree portfast
      container portfast {
        description
          "Spanning tree portfast options";
        tailf:cli-compact-syntax;
        tailf:cli-sequence-commands {
          tailf:cli-reset-siblings;
        }
        leaf bdpu {
          tailf:cli-drop-node-name;
          tailf:cli-optional-in-sequence;
          type enumeration {
            enum "bpdufilter";
            enum "bpduguard";
          }
        }
        leaf default {
          description
            "Enable portfast by default on all access ports";
          type empty;
        }
      }
      //  transmit      STP transmit parameters
      container transmit {
        description
          "STP transmit parameters";
        leaf hold-count {
          description
            "Value for txholdcount parameter";
          type uint8 {
            range "1..20";
          }
        }
      }
      //  uplinkfast    Enable UplinkFast Feature
      //  spanning-tree uplinkfast
      container uplinkfast {
        description
          "Enable UplinkFast Feature";
        presence "true";
        leaf max-update-rate {
          description
            "Rate at which station address updates are sent";
          type uint32 {
            range "0..32000";
          }
        }
      }
      // spanning-tree mode
      leaf mode {
        description
          "Spanning tree operating mode";
        tailf:cli-show-with-default;
        tailf:cli-full-command;
        type enumeration {
          enum "mst";
          enum "pvst";
          enum "rapid-pvst";
        }
      }
      //  vlan          VLAN Switch Spanning Tree
      // spanning-tree vlans-max-age
      list vlan {
        description
          "VLAN Switch Spanning Tree";
        tailf:cli-suppress-mode;
        tailf:cli-delete-when-empty;
        key "id";
        leaf id {
          type string;
        }
        leaf max-age {
          description
            "Set the max age interval for the spanning tree";
          type uint8 {
            range "6..40";
          }
        }
        leaf forward-time {
          description
            "Set the forward delay for the spanning tree";
          type uint8 {
            range "4..30";
          }
        }
        leaf hello-time {
          description
            "Set the hello interval for the spanning tree";
          type uint8 {
            range "1..10";
          }
        }
        leaf priority {
          description
            "Set the bridge priority for the spanning tree";
          type uint16 {
            range "0..61440";
          }
        }
        container root {
          description
            "Configure switch as root";
          container primary {
            description
              "Configure this switch as primary root for this spanning tree";
            tailf:cli-compact-syntax;
            tailf:cli-sequence-commands {
              tailf:cli-reset-siblings;
            }
            leaf diameter {
              description
                "Network diameter of this spanning tree";
              type uint8 {
                range "2..7";
              }
            }
            leaf hello-time {
              description
                "Hello interval for this spanning tree";
              type uint8 {
                range "1..10";
              }
            }
          }
          container secondary {
            description
              "Configure switch as secondary root";
            tailf:cli-compact-syntax;
            tailf:cli-sequence-commands {
              tailf:cli-reset-siblings;
            }
            leaf diameter {
              description
                "Network diameter of this spanning tree";
              type uint8 {
                range "2..7";
              }
            }
            leaf hello-time {
              description
                "Hello interval for this spanning tree";
              type uint8 {
                range "1..10";
              }
            }
          }
        }
      }
    }


    /// ========================================================================
    /// subscriber
    /// ========================================================================
    container subscriber {
      description
        "Subscriber configuration";
      leaf templating {
        description
          "Configure subscriber templating";
        type empty;
      }
    }

    /// ========================================================================
    /// track
    /// ========================================================================
    container track {
      description
        "Object tracking configuration commands";
      list tracked-object {
        tailf:cli-drop-node-name;
        tailf:cli-mode-name "config-track";
        key "object-number";
        leaf object-number {
          type uint32 {
            range "1..1000";
          }
        }
        container interface {
          description
            "Select an interface to track";
          tailf:cli-hide-in-submode;
          tailf:cli-flatten-container;
          tailf:cli-compact-syntax;
          tailf:cli-sequence-commands;
          leaf name {
            tailf:cli-drop-node-name;
            type string;
          }
          leaf protocol {
            tailf:cli-drop-node-name;
            type enumeration {
              enum "ip";
              enum "ipv6";
              enum "line-protocol";
            }
          }
          leaf routing {
            description
              "Track interface IPv6 routing capability";
            tailf:cli-optional-in-sequence;
            when "../protocol = 'ip' or ../protocol = 'ipv6'";
            type empty;
          }
        }
        container ip {
          description
            "IP protocol";
          tailf:cli-hide-in-submode;
          tailf:cli-flatten-container;
          container route {
            tailf:cli-compact-syntax;
            tailf:cli-sequence-commands;
            tailf:cli-flatten-container;
            leaf address {
              type inet:ipv4-address;
            }
            leaf mask {
              tailf:cli-drop-node-name;
              type inet:ipv4-address;
            }
            leaf reachability {
              description
                "Route reachability state";
              tailf:cli-optional-in-sequence;
              tailf:cli-full-command;
              type empty;
            }
            leaf metric {
              description
                "Route metric";
              tailf:cli-optional-in-sequence;
              tailf:cli-full-command;
              type enumeration {
                enum "threshold";
              }
            }
          }
          container sla {
            description
              "IP Service Level Agreement";
            tailf:cli-flatten-container;
            tailf:cli-compact-syntax;
            tailf:cli-sequence-commands;
            leaf number {
              description
                "Entry number";
              tailf:cli-drop-node-name;
              type uint32;
            }
            leaf reachability {
              description
                "Reachability";
              tailf:cli-optional-in-sequence;
              tailf:cli-full-command;
              type empty;
            }
            leaf state {
              description
                "Return code state";
              tailf:cli-optional-in-sequence;
              tailf:cli-full-command;
              type empty;
            }
          }
        }
        container ipv6 {
          description
            "IPv6 protocol";
          tailf:cli-hide-in-submode;
          tailf:cli-flatten-container;
          container route {
            description
              "IPv6 route";
            tailf:cli-compact-syntax;
            tailf:cli-sequence-commands;
            tailf:cli-flatten-container;
            leaf address {
              tailf:cli-drop-node-name;
              type inet:ipv6-prefix;
            }
            leaf reachability {
              description
                "Route reachability state";
              tailf:cli-optional-in-sequence;
              tailf:cli-full-command;
              type empty;
            }
            leaf metric {
              description
                "Route metric";
              tailf:cli-full-command;
              type enumeration {
                enum "threshold";
              }
            }
          }
        }
        container list {
          description
            "Group objects in a list";
          tailf:cli-hide-in-submode;
          tailf:cli-flatten-container;
          leaf boolean {
            description
              "List state based on a boolean calculation on objects";
            tailf:cli-full-command;
            type enumeration {
              enum "and";
              enum "or";
            }
          }
          leaf threshold {
            description
              "List state based on a threshold of UP and DOWN objects";
            tailf:cli-full-command;
            type enumeration {
              enum "percentage";
              enum "weight";
            }
          }
        }
        leaf stub-object {
          description
            "Stub tracking object";
          tailf:cli-hide-in-submode;
          tailf:cli-full-command;
          type empty;
        }
        container default {
          description
            "Set a command to its defaults";
          uses default-track-grouping;
        }
        uses track-grouping;
      }
      container resolution {
        description
          "Tracking resolution parameters";
        container ip {
          description
            "IP protocol";
          container route {
            description
              "Route metric resolution";
            leaf bgp {
              description
                "BGP route metric resolution";
              tailf:cli-full-command;
              type uint32 {
                range "256..40000000";
              }
            }
            leaf eigrp {
              description
                "EIGRP route metric resolution";
              tailf:cli-full-command;
              type uint32 {
                range "256..40000000";
              }
            }
            leaf isis {
              description
                "ISIS route metric resolution";
              tailf:cli-full-command;
              type uint32 {
                range "1..1000";
              }
            }
            leaf ospf {
              description
                "OSPF route metric resolution";
              tailf:cli-full-command;
              type uint32 {
                range "1..1562";
              }
            }
            leaf static {
              description
                "Static route metric resolution";
              tailf:cli-full-command;
              type uint32 {
                range "1..100000";
              }
            }
          }
        }
      }
      container timer {
        description
          "Polling interval timers";
        container interface {
          description
            "Interface polling timer";
          uses track-timer-grouping;
        }
        container ip {
          description
            "IP protocol";
          container route {
            description
              "IP route polling timer";
            uses track-timer-grouping;
          }
          container sla {
            description
              "IP SLA polling timer";
            uses track-timer-grouping;
          }
        }
        container ipv6 {
          description
            "IPv6 protocol";
          container route {
            description
              "IPv6 route polling timer";
            uses track-timer-grouping;
          }
        }
        container list {
          description
            "Boolean list polling timer";
          uses track-timer-grouping;
        }
        container stub-object {
          description
            "EEM stub polling timer";
          uses track-timer-grouping;
        }
      }
    }



    /// ========================================================================
    /// dot1x
    /// ========================================================================
    container dot1x {
      description
        "IEEE 802.1X Global Configuration Commands";
      // dot1x credentials    
      list credentials {
        description "Configure 802.1X credentials profiles";
        key "profile-name";
        leaf profile-name {
          description "Specify a profile name";
          type string;
        }
        leaf username {
          description 
            "Set the authentication userid";
          type string;    
        }
        container password {
          description 
            "Set the authentication password";
          tailf:cli-compact-syntax;
          tailf:cli-sequence-commands;
          leaf type {
            tailf:cli-drop-node-name;
            tailf:cli-optional-in-sequence;
            type enumeration {
              enum "0";
              enum "7";
            }
          }
          leaf secret {
            tailf:cli-drop-node-name;
            type string;
          }            
        }
        leaf pki-trustpoint {
          description 
            "Set the default pki trustpoint";
          type string;    
        }
      }    
      // dot1x critical
      container critical {
        description
          "Set 802.1x Critical Authentication parameters";
        leaf eapol {
          description
            "Send EAPOL-Success on successful Critical Authentication";
          type empty;
        }
        container recovery {
          description
            "Set 802.1x Critical Authentication Recovery parameters";
          leaf delay {
            description
              "Set 802.1x Critical Authentication Recovery Delay period";
            type uint16 {
              range "1..10000";
            }
          }
        }
      }      
      container test {
        description "Configure dot1x test related parameters";
        leaf timeout {
          description "Seconds";
          type uint16 {
            range "1..65535";
          }
        }
      }
      // dot1x supplicant
      container supplicant {
        description
          "802.1X supplicant configuration";
        leaf force-multicast {
          description
            "Force 802.1X supplicant to send multicast packets";
          type empty;
        }
      }      
      // dot1x system-auth-control
      leaf system-auth-control {
        description
          "Enable or Disable SysAuthControl";
        type empty;
      }
    }
    
    ///=================================================================
    /// network-policy
    ///====================================================
    container network-policy {
      description "Network Policy";
      leaf profile {
        description "Network Policy Profile";
        type uint32 {
          range "1..4294967295";
        }
      }
    }
    ///=============================================================
    /// Mode-config-fallback-profile
    ///=============================================================

    grouping Mode-config-fallback-profile {
      //tailf:cli-drop-node-name;
      leaf description {
        tailf:cli-multi-value;
        description "Any textual description";
        type string;
      }
      container ip {
        description "Internet Protocol configuration commands";
        list access-group {
          description "Specify access control for packets";
          tailf:cli-suppress-mode;
          key "name";
          leaf name {
            description "IP expanded access list (standard or extended)";
            type union {
              type uint16 {
                range "1300..2699";
              }
              type string;
            }
          }
          leaf in {
            description "inbound packets";
            type empty;
          }
        }   
        leaf admission {
          description "Name of IP admission rule";
          type string;
        }
      }
    }
    ///================================================
    /// fallback
    ///===========================================
    container fallback {
      description "Fallback configuration commands";
      container profile {
        description "Create a Fallback profile";
        list fallback-list{
          tailf:cli-drop-node-name;
          description "Specify a policy name";
          key "name";
          leaf name {
            type string;
          }
          uses Mode-config-fallback-profile;
        }
      }
    }
 
    /// ========================================================================
    /// power
    /// ========================================================================
    container power {
      description
        "Power configure";
      tailf:cli-compact-syntax;
      tailf:cli-sequence-commands;

            //  cycle            power cycle a module (deprecated)
            //  enable           module slot power control
      container inline {
        description "Inline power configuration";
        presence true;
        container consumption {
          description "Inline device power consumption";
          leaf default {
            description "Inline device power consumption";
            type uint16 {
              range "4000..15400";
            }
          }
        }
        container logging {
          description "Inline power logging messages";
          leaf global {
            description "Enable global inline power logging messages";
            type empty;
          }
        }
      }
            
      leaf redundancy-mode {
        description
          "set power supply redundancy mode";
        type enumeration {
          enum "combined";
          enum "redundant";
        }
      }
      leaf max-min {
        tailf:cli-drop-node-name;
        type enumeration {
          enum "max";
        }
      }
      leaf inputs {
        type uint8;
      }
    }

    /// ========================================================================
    /// parameter-map
    /// ========================================================================
    list parameter-map {
      description
        "parameter map";
      tailf:cli-mode-name "config-profile";
      key "name";
      leaf name {
        type string;
      }
      leaf type {
        description
          "parameter map type";
        tailf:cli-prefix-key;
        type enumeration {
          enum "cws-tunnel";
          enum "inspect";
          enum "inspect-global";
          enum "webauth";
          enum "inspect-vrf";
          enum "inspect-zone";
          enum "regex";
          enum "authbypass";
        }
      }
      leaf parameter-map-type {
        tailf:alt-name "type";
        description
          "type - web-auth, consent or both";
        type enumeration {
          enum "webauth";
          enum "authbypass";
        }  
      }
      container timeout {
        description "timeout for the webauth session";
        when "../type = 'webauth'";
        container init-state {
          description "init-state timeout";
          presence true;
          leaf sec {          
            description "WEBAUTH Timeout in Seconds";
            type uint32 {
              range "60..3932100";
            }
          }
        }
        container fin-wait {
          description "fin-wait timeout";
          leaf msec {          
            description "WEBAUTH Timeout in milliseconds";
            type uint32 {
              range "1..2147483647";
            }
          }
        }
      }
      container watch-list{
        description "Watch List of webauth clients";
        when "../type = 'webauth'";
        leaf enabled {
          description "Enable Watchlist";
          type empty;
        }
        leaf dynamic-expiry-timeout {
          description "dynamic_expiry_timeout";
          type uint32 {
            range "0..2147483";
          }
        }
        container add-item {
          description "Add item to Watch-list";          
          leaf ipv4 {
            description "IPv4 Watch List Entry";
            type inet:ipv4-address;
          }
          leaf ipv6 {
            description "IPv6 Watch List Entry";
            type inet:ipv6-address;
          }
        }
      }
      container aggressive-aging {
        description
          "Aggressive Aging parameters";
        when "../type = 'inspect-global'";
        container high {
          description
            "Specify the high watermark for aggressive-aging";
          choice absolute-percent {
            case absolute-case {
              container absolute {
                tailf:cli-drop-node-name;
                tailf:cli-sequence-commands;
                tailf:cli-compact-syntax;
                leaf value {
                  tailf:cli-drop-node-name;
                  type uint64 {
                    range "1..4294967295";
                  }
                }
                leaf low {
                  description
                    "Specify the low watermark for aggressive-aging";
                  type uint64 {
                    range "1..4294967295";
                  }
                }
              }
            }
            case percent-case {
              container percent {
                description
                  "high watermark in percentage of max-incomplete value";
                tailf:cli-sequence-commands;
                tailf:cli-compact-syntax;
                leaf value {
                  tailf:cli-drop-node-name;
                  type uint8 {
                    range "1..100";
                  }
                }
                leaf low_percent {
                  tailf:alt-name "low percent";
                  description
                    "Specify the low watermark for aggressive-aging in percents";
                  type uint8 {
                    range "1..100";
                  }
                }
              }
            }
          }
        }
      }
      leaf alert {
        description
          "Turn on/off alert";
        type enumeration {
          enum "off";
          enum "on";
        }
      }
      leaf application-inspect {
        description
          "Turn on application inspection";
        type enumeration {
          enum "all";
          enum "dns";
          enum "exec";
          enum "ftp";
          enum "gtp";
          enum "h323";
          enum "http";
          enum "imap";
          enum "login";
          enum "msrpc";
          enum "netbios";
          enum "pop3";
          enum "rtsp";
          enum "shell";
          enum "sip";
          enum "skinny";
          enum "smtp";
          enum "sunrpc";
          enum "tftp";
        }
      }
      leaf audit-trail {
        description
          "Turn on/off audit trail";
        when "../type = 'inspect'";
        type enumeration {
          enum "off";
          enum "on";
        }
      }
      leaf dns-timeout {
        description
          "Specify timeout for DNS";
        when "../type = 'inspect'";
        type uint32 {
          range "1..2147483";
        }
      }
      container icmp {
        description
          "Config timeout values for icmp";
        when "../type = 'inspect'";
        leaf idle-time {
          description
            "Specify timeout for icmp";
          type uint32 {
            range "1..2147483";
          }
        }
      }
      container lisp {
        description
          "Turn on LISP options";
        leaf inner-packet-inspection {
          description
            "inner-packet-inspection";
          type empty;
        }
      }
      container log {
        description
          "Configure inspect logging parameters";
        leaf dropped-packets {
          description
            "Log dropped packets";
          type empty;
        }
        container flow-export {
          description
            "Configure inspect external logging parameters";
          container template {
            description
              "Configure record template parameters";
            leaf timeout-rate {
              description
                "Rate to resend the template in seconds";
              type uint32 {
                range "0..65535";
              }
            }
          }
          container v9 {
            description
              "Netflow version 9";
            container udp {
              description
                "Use UDP to export records";
              container destination {
                description
                  "Specify the flow-export destination";
                tailf:cli-sequence-commands;
                tailf:cli-compact-syntax;
                leaf dst-ip {
                  tailf:cli-drop-node-name;
                  type inet:ipv4-address;
                }
                leaf dst-port {
                  tailf:cli-drop-node-name;
                  type uint16;
                }
              }
            }
          }
        }
      }
      leaf max-destination {
        description
          "config maximum destination";
        when "../type = 'inspect-zone'";
        type uint64 {
          range "1..4294967295";
        }
      }
      container max-incomplete {
        description
          "Specify maximum number of incomplete connections before clamping";
        leaf high {
          description
            "Specify high-watermark for clamping";
          type uint32 {
            range "1..2147483647";
          }
        }
        leaf low {
          description
            "Specify low-watermark for clamping";
          type uint32 {
            range "1..2147483647";
          }
        }
      }
      container one-minute {
        description
          "Specify one-minute-sample watermarks for clamping";
        when "../type = 'inspect'";
        leaf high {
          description
            "Specify high-watermark for clamping";
          type uint32 {
            range "1..2147483647";
          }
        }
        leaf low {
          description
            "Specify low-watermark for clamping";
          type uint32 {
            range "1..2147483647";
          }
        }
      }
      container sessions {
        description
          "Maximum number of inspect sessions";
        when "../type = 'inspect'";
        leaf maximum {
          description
            "Maximum sessions";
          type uint32 {
            range "1..2147483647";
          }
        }
      }
      container tcp {
        description
          "Config timeout values for tcp connections";
        leaf finwait-time {
          description
            "Specify timeout for TCP connections after a FIN";
          type uint32 {
            range "1..2147483";
          }
        }
        leaf idle-time {
          description
            "Specify idle timeout for tcp connections";
          type uint32 {
            range "1..2147483";
          }
        }
        container max-incomplete {
          description
            "Specify max half-open connection per host";
          leaf host {
            description
              "Specify max half-open connection per host";
            type uint32 {
              range "1..4294967295";
            }
          }
        }
        leaf synwait-time {
          description
            "Specify timeout for TCP connections after a SYN and no";
          type uint32 {
            range "1..2147483";
          }
        }
      }
      container threat-detection {
        description
          "Configure Threat Detection";
        when "../type = 'inspect-zone'";
        leaf basic-threat {
          description
            "Enable Threat Detection";
          type empty;
        }
        container rate {
          description
            "Configure Threat Detection rate";
          container fw-drop {
            description
              "Configure Threat Detection rate for firewall drop events";
            tailf:cli-sequence-commands;
            tailf:cli-compact-syntax;
            leaf average-time-frame {
              description
                "Configure Threat Detection average time frame";
              type uint32 {
                range "600..3600";
              }
            }
            leaf average-threshold {
              description
                "Configure Threat Detection average threshold";
              type uint64 {
                range "1..4294967295";
              }
            }
            leaf burst-threshold {
              description
                " Configure Threat Detection burst threshold";
              type uint64 {
                range "1..1000000000";
              }
            }
          }
          container inspect-drop {
            description
              "Configure Threat Detection rate for firewall inspection based drop events";
            tailf:cli-sequence-commands;
            tailf:cli-compact-syntax;
            leaf average-time-frame {
              description
                "Configure Threat Detection average time frame";
              type uint32 {
                range "600..3600";
              }
            }
            leaf average-threshold {
              description
                "Configure Threat Detection average threshold";
              type uint64 {
                range "1..4294967295";
              }
            }
            leaf burst-threshold {
              description
                " Configure Threat Detection burst threshold";
              type uint64 {
                range "1..1000000000";
              }
            }
          }
          container syn-attack {
            description
              "Configure Threat Detection rate for syn attack events";
            tailf:cli-sequence-commands;
            tailf:cli-compact-syntax;
            leaf average-time-frame {
              description
                "Configure Threat Detection average time frame";
              type uint32 {
                range "600..3600";
              }
            }
            leaf average-threshold {
              description
                "Configure Threat Detection average threshold";
              type uint64 {
                range "1..4294967295";
              }
            }
            leaf burst-threshold {
              description
                " Configure Threat Detection burst threshold";
              type uint64 {
                range "1..1000000000";
              }
            }
          }
        }
      }
      container udp {
        description
          "Config timeout values for udp flows";
        when "../type = 'inspect'";
        leaf idle-time {
          description
            "Specify idle timeout for udp";
          type uint32 {
            range "1..2147483";
          }
        }
      }
      container vrf {
        description
          "vrf binding with parameter map";
        tailf:cli-sequence-commands;
        tailf:cli-compact-syntax;
        leaf name {
          tailf:cli-drop-node-name;
          type string;
        }
        leaf inspect {
          description
            "vrf binding with parameter map";
          type string;
        }
      }
      leaf zone-mismatch {
        description
          "Config zone-mismatch option";
        type enumeration {
          enum "drop";
        }
      }
    }


    /// ========================================================================
    /// vpdn
    /// ========================================================================
    container vpdn {
      description
        "Virtual Private Dialup Network";
      leaf authen-before-forward {
        description
          "Authenticate a user locally before tunnelling";
        type empty;
      }
      leaf enable {
        description
          "Enable VPDN";
        type empty;
      }
      leaf-list search-order {
        ordered-by user;
        description
          "Configure the order to search different VPDN tunnel types";
        tailf:cli-flat-list-syntax;
        type enumeration {
          enum "dnis";
          enum "domain";
          enum "multihop-hostname";
        }
      }
    }

    /// ========================================================================
    /// ppp
    /// ========================================================================
    container ppp {
      description
        "PPP global configuration";
      container packet {
        description
          "Configure control packet rate throttling";
        tailf:cli-compact-syntax;
        tailf:cli-sequence-commands;
        leaf throttle {
          description
            "Configure control packet rate throttling";
          type uint32 {
            range "1..100000";
          }
        }
        leaf allow_time {
          tailf:cli-drop-node-name;
          type uint32 {
            range "1..3600";
          }
        }
        leaf block_time {
          tailf:cli-drop-node-name;
          type uint32 {
            range "2..3600";
          }
        }
      }
    }

    /// ========================================================================
    /// bba-group
    /// ========================================================================
    container bba-group {
      description
        "Configure BBA Group";
      list pppoe {
        description
          "PPPoE type";
        key "id";
        leaf id {
          type union {
            type string;
            type enumeration {
              enum "global";
            }
          }
        }
        container vendor-tag {
          description
            "PPPoE Vendor Specific Tag";
          container circuit-id {
            description
              "Circuit-Id";
            leaf service {
              description
                "Enable processing";
              type empty;
            }
          }
          container dsl-sync-rate {
            description
              "DSL-Sync-Rate";
            leaf service {
              description
                "Enable processing";
              type empty;
            }
          }
          container remote-id {
            description
              "Remote-Id";
            leaf service {
              description
                "Enable processing";
              type empty;
            }
          }
          leaf strip {
            description
              "Strip all vendor tags";
            type empty;
          }
        }
        leaf virtual-template {
          description
            "BBA virtual template command";
          type uint16 {
            range "1..4095";
          }
        }
      }
    }
    


    /// ========================================================================
    /// mac
    /// ========================================================================
    container mac {
      description
        "Global MAC configuration subcommands";
      container access-list {
        description
          "Named access-list";
        list extended {
          description
            "Extended Access List";
          key "id";
          leaf id {
            type string;
          }
          container deny {
            description
              "Specify packets to reject";
            tailf:cli-compact-syntax;
            tailf:cli-sequence-commands;
            container source {
              tailf:cli-compact-syntax;
              tailf:cli-flatten-container;
              tailf:cli-drop-node-name;
              choice target-choice {
                leaf any {
                  description
                    "any source MAC address";
                  type empty;
                }
                leaf host {
                  description
                    "A single source host";
                  type string;
                }
                leaf mac-address {
                  description
                    "48-bit source MAC address";
                  tailf:cli-drop-node-name;
                  type string;
                }
              }
            }
            container dest {
              tailf:cli-compact-syntax;
              tailf:cli-flatten-container;
              tailf:cli-drop-node-name;
              choice target-choice {
                leaf any {
                  description
                    "any destination MAC address";
                  type empty;
                }
                leaf host {
                  description
                    "A single destination host";
                  type string;
                }
                leaf mac-address {
                  description
                    "48-bit destination MAC address";
                  tailf:cli-drop-node-name;
                  type string;
                }
              }
            }
            leaf ethertype {
              tailf:cli-drop-node-name;
              type string;
            }
          }
          container permit {
            description
              "Specify packets to forward";
            tailf:cli-compact-syntax;
            tailf:cli-sequence-commands;
            container source {
              tailf:cli-compact-syntax;
              tailf:cli-flatten-container;
              tailf:cli-drop-node-name;
              choice target-choice {
                leaf any {
                  description
                    "any source MAC address";
                  type empty;
                }
                leaf host {
                  description
                    "A single source host";
                  type string;
                }
                leaf mac-address {
                  description
                    "48-bit source MAC address";
                  tailf:cli-drop-node-name;
                  type string;
                }
              }
            }
            container dest {
              tailf:cli-compact-syntax;
              tailf:cli-flatten-container;
              tailf:cli-drop-node-name;
              choice target-choice {
                leaf any {
                  description
                    "any destination MAC address";
                  type empty;
                }
                leaf host {
                  description
                    "A single destination host";
                  type string;
                }
                leaf mac-address {
                  description
                    "48-bit destination MAC address";
                  tailf:cli-drop-node-name;
                  type string;
                }
              }
            }
            leaf ethertype {
              tailf:cli-drop-node-name;
              type string;
            }
          }
        }
      }
      //   address-table    Configure the MAC address table
      container address-table {
        description
          "Configure the MAC address table";
        tailf:cli-sequence-commands;
        tailf:cli-compact-syntax;
        leaf aging-time {
          description
            "Set MAC address table entry maximum age";
          type uint32 {
            range "0 | 10..1000000";
          }
        }
        leaf routed-mac {
          description
            "Set RM Aging interval";
          tailf:cli-optional-in-sequence;
          tailf:cli-full-command;
          type empty;
        }
        leaf vlan {
          description
            "VLAN Keyword";
          tailf:cli-optional-in-sequence;
          tailf:cli-full-command;
          type uint16 {
            range "1..4094";
          }
        }
        leaf control-packet-learn {
          description
            "Enable/Disable learning from Control Packets";
          tailf:cli-optional-in-sequence;
          tailf:cli-full-command;
          type empty;
        }
        container learning {
          description
            "Enable MAC table learning feature";
          tailf:cli-optional-in-sequence;
          tailf:cli-full-command;
          leaf vlan {
            description
              "<1-4094>;;VLAN id to enable MAC Address learning";
            type uint16 {
              range "1..4094";
            }
          }
        }
        container notification {
          description
            "Enable/Disable MAC Notification on the switch";
          tailf:cli-optional-in-sequence;
          tailf:cli-sequence-commands;
          tailf:cli-compact-syntax;
          container change {
            description
              "Enable/Disable MAC Notification feature on the switch";
            tailf:cli-optional-in-sequence;
            tailf:cli-sequence-commands;
            tailf:cli-compact-syntax;
            presence "true";
            leaf history-size {
              description
                "Number of entries in history table (0-500)";
              tailf:cli-optional-in-sequence;
              tailf:cli-full-command;
              type uint16 {
                range "0..500";
              }
            }
            leaf interval {
              description
                "Notification interval in seconds (0-2147483647)";
              tailf:cli-optional-in-sequence;
              tailf:cli-full-command;
              type uint32 {
                range "0..2147483647";
              }
            }
          }
          leaf mac-move {
            description
              "Enable Mac Move Notification";
            tailf:cli-optional-in-sequence;
            tailf:cli-full-command;
            type empty;
          }
          container threshold {
            description
              "Configure L2 Table monitoring";
            tailf:cli-optional-in-sequence;
            tailf:cli-sequence-commands;
            tailf:cli-compact-syntax;
            presence "true";
            leaf interval {
              description
                "<120-1000000> Interval time in seconds";
              type uint32 {
                range "120..1000000";
              }
            }
            container limit {
              description
                "Limit percentage";
              tailf:cli-optional-in-sequence;
              tailf:cli-sequence-commands;
              tailf:cli-compact-syntax;
              leaf percentage {
                description
                  "Percentage (0-100)";
                tailf:cli-drop-node-name;
                type uint8 {
                  range "0..100";
                }
              }
              leaf interval {
                description
                  "<120-1000000> Interval time in seconds";
                tailf:cli-optional-in-sequence;
                tailf:cli-full-command;
                type uint32 {
                  range "120..1000000";
                }
              }
            }
          }
        }
        container static {
          description
            "Static MAC entry";
          tailf:cli-sequence-commands;
          tailf:cli-compact-syntax;
          leaf mac-address {
            description
              "xxxx.xxxx.xxxx 48 bit mac address";
            tailf:cli-drop-node-name;
            tailf:cli-incomplete-command;
            type cisco-mac-address-type;
          }
          leaf vlan {
            description
              "<1-4094> VLAN id of mac address table (1-4094)";
            tailf:cli-incomplete-command;
            type uint16 {
              range "1..4094";
            }
          }
          leaf drop {
            description
              "drop frames";
            tailf:cli-optional-in-sequence;
            tailf:cli-full-command;
            type empty;
          }
          leaf interface {
            description
              "Output interface exact long name";
            tailf:cli-optional-in-sequence;
            tailf:cli-full-command;
            type string;
          }
        }
      }
      //   packet-classify  packet classification by mac ACL
    }
    /// ========================================================================
    /// tacacs
    /// ========================================================================
    container tacacs {
      description
        "TACACS server configuration command";
      tailf:cli-diff-dependency "/ios:native/aaa";
      list server {
        description
          "Server configuration";
        tailf:cli-mode-name "config-server-tacacs";
        key "name";
        leaf name {
          type string;
        }
        container address {
          description
            "Specify ip address for tacacs server";
          leaf ipv4 {
            description
              "Configure ipv4 address for tacacs server";
            type union {
              type string;
              type inet:ipv4-address;
            }
          }
        }
        container key {
          description
            "per-server encryption key (overrides default)";
          tailf:cli-compact-syntax;
          tailf:cli-sequence-commands;
          leaf encryption {
            tailf:cli-drop-node-name;
            tailf:cli-incomplete-command;
            tailf:cli-optional-in-sequence;
            type enumeration {
              enum "0";
              enum "7";
            }
          }
          leaf key {
            tailf:cli-drop-node-name;
            tailf:cli-full-command;
            tailf:cli-multi-value;
            type string;
          }
        }
      }
    }

    /// ========================================================================
    /// tacacs-server
    /// ========================================================================
    container tacacs-server {
      description
        "Modify TACACS query parameters";
      // tacacs-server host *
      list host {
        description
          "Specify a TACACS server";
        tailf:cli-suppress-mode;
        tailf:cli-delete-when-empty;
        tailf:cli-compact-syntax;
        tailf:cli-reset-container;
        key "name";
        leaf name {
          type host-type;
        }
        // tacacs-server host * port
        leaf port {
          description
            "TCP port for TACACS+ server (default is 49)";
          type uint16 {
            range "1..65535";
          }
        }
        // tacacs-server host * key
        leaf key {
          description
            "Set TACACS+ encryption key.";
          type union {
            type enumeration {
              enum "0";
              enum "7";
            }
            type string;
          }
        }
        leaf encryption-key {
          when "../key = '0' or ../key = '7'";
          tailf:cli-drop-node-name;
          tailf:cli-full-command;
          tailf:cli-multi-value;
          type string;
        }
        // tacacs-server host * timeout
        leaf timeout {
          description
            "Time to wait for this TACACS server to reply (overrides default)";
          type uint16 {
            range "1..1000";
          }
        }
      }
      // tacacs-server timeout
      leaf timeout {
        description
          "Time to wait for a TACACS server to reply";
        type uint16 {
          range "1..1000";
        }
      }
      // tacacs-server directed-request
      container directed-request {
        description
          "Allow user to specify tacacs server to use with `@server'";
        tailf:cli-compact-syntax;
        tailf:cli-sequence-commands;
        presence "true";
        leaf restricted {
          description
            "restrict queries to directed request servers only";
          tailf:cli-optional-in-sequence;
          type empty;
        }
        leaf no-truncate {
          description
            "Do not truncate the @hostname from username.";
          type empty;
        }
      }
      // tacacs-server key
      container key {
        description
          "Set TACACS+ encryption key.";
        tailf:cli-compact-syntax;
        tailf:cli-sequence-commands;
        leaf encryption {
          tailf:cli-drop-node-name;
          tailf:cli-incomplete-command;
          tailf:cli-optional-in-sequence;
          type enumeration {
            enum "0";
            enum "7";
          }
        }
        leaf key {
          tailf:cli-drop-node-name;
          tailf:cli-full-command;
          tailf:cli-multi-value;
          type string;
        }
      }
    }

    /// ========================================================================
    /// upgrade
    /// ========================================================================
    container upgrade {
      description
        "Global upgrade configuration subcommands";
      container fpd {
        description
          "Configure field programmable devices upgrade options";
        leaf auto {
          description
            "Auto upgrade all FPD images";
          type empty;
        }
        leaf path {
          description
            "Set path to locate the FPD image package file for auto upgrade";
          type string;
        }
      }
    }
    
    /// ========================================================================
    /// vtp
    /// ========================================================================
    grouping device-modes {
      leaf mst {
        description "Set the mode for MST VTP instance";
        type empty;
      }
      leaf unknown {
        description "Set the mode for unknown VTP instances";
        type empty;
      }
      leaf vlan {
        description "Set the mode for VLAN VTP instance";
        type empty;
      }
    }
    container vtp {
      description
        "Configure global VTP state";
      // vtp file
      leaf file {
        description
          "Configure IFS filesystem file where VTP configuration is stored.";
        type string;
      }
      // vtp interface
      container interface {
        description
          "Configure Interface as the preferred source for the VTP IP updater address";
        tailf:cli-sequence-commands;
        tailf:cli-compact-syntax;
        leaf interface-name {
          tailf:cli-drop-node-name;
          description
            "The name of the interface providing the VTP updater ID for this device";
          type string;
        }
        leaf only {
          description
            "Use only this interface's IP address as the VTP IP updater address";
          tailf:cli-optional-in-sequence;
          type empty;
        }
      }
      //vtp password
      container password {
        description
          "Set the password for the VTP administrative domain";
        tailf:cli-sequence-commands;
        tailf:cli-compact-syntax;
        leaf password {
          tailf:cli-drop-node-name;
          description
            "The ascii password for the VTP administrative domain";
          type string;
        }
        leaf hidden {
          tailf:cli-break-sequence-commands;
          tailf:cli-full-command;
          description
            "Set the VTP password hidden option";
          type empty;
        }
        leaf secret {
          description
            "Specify the vtp password in encrypted form";
          tailf:cli-full-command;
          type empty;
        }
      }
      // vtp pruning
      leaf pruning {
        description
          "Set the adminstrative domain to permit pruning";
        type empty;
      }
      // vtp version
      leaf version {
        description
          "Set the adminstrative domain to VTP version";
        type uint8 {
          range "1..3";
        }
      }
      // vtp domain
      leaf domain {
        description
          "Set the name of the VTP administrative domain.";
        type string;
      }
      //vtp mode
      container mode {
        description "Configure VTP device mode";
        container client {
          description "Set the device to client mode";
          presence true;
          uses device-modes;
        }
        container off {
          description "Set the device to off mode";
          presence true;
          uses device-modes;
        }
        container server {
          description "Set the device to server mode";
          presence true;
          uses device-modes;
        }
        container transparent {
          description "Set the device to transparent mode";
          presence true;
          uses device-modes;
        }
      }
    }

    /// ========================================================================
    /// ap
    /// ========================================================================
    container ap {
      description
        "Configures Cisco APs";
      list group {
        description
          "Manage AP Groups VLAN feature";
        tailf:cli-mode-name "config-apgroup";
        key "name";
        leaf name {
          type string;
        }
        container config {
          tailf:cli-drop-node-name;
          container airtime-fairness {
            description 
              "airtime-fairness for this AP group";
            container dot11 {
               description 
                 "Configures airtime-fairness parameters for the AP group";
               container _24GHz {
                   tailf:alt-name "24GHz";
                   description 
                     "Configures 2.4 GHz airtime-fairness policy";
                   leaf mode {
                       description 
                         "Configure airtime-fairness in enforce mode";
                       type enumeration {
                         enum "enforce-policy";
                         enum "monitor";
                       }
                   }
                   leaf optimization {
                       description 
                         "Enable airtime-fairness optimization";
                       type empty;
                   }
               }
               container _5GHz {
                   tailf:alt-name "5GHz";
                   description 
                     "Configures 5 GHz airtime-fairness policy";
                   leaf mode {
                       description 
                         "Configure airtime-fairness in enforce mode";
                       type enumeration {
                         enum "enforce-policy";
                         enum "monitor";
                       }  
                   }
                   leaf optimization {
                       description 
                         "Enable airtime-fairness optimization";
                       type empty;
                   }
              }
            }
          }
          leaf description {
              description 
                "Enter description";
              type string;
          }
          container hyperlocation {
              description 
                "Configures Hyperlocation feature on all supported APs";
               presence true;
               container threshold {
                   description 
                     "Sets Hyperlocation thresholds";
                   leaf detection {
                       description 
                         "RSSI threshold to filter out packets with low RSSI(in dBm)";                       
                       type int8 {
                           range "-100..-50";
                       }                       
                   }
                   leaf reset {
                       description 
                         "Enter a value smaller than trigger threshold";
                       type uint8 {
                           range "0..99";
                       }
                   }
                   leaf trigger {
                       description 
                         "Enter number of scan cycles";
                       type uint8 {
                           range "1..100";
                       }
                   }
               }
          }
          container ntp {
              description 
                "Sets the NTP server IP address";
              leaf ip {
                  description 
                    "NTP server IPv4 address";  
                  type inet:ipv4-address;                  
              }
          }
          list port {
              description 
                "Configure LAN port parameters of an AP group";
              tailf:cli-mode-name "config-port-apgroup";
              key "id";
              leaf id {
                  description 
                    "Enter port ID for LAN";
                  type uint8 {
                      range "1..3";
                  }
              }           
              uses ap-port-grouping;              
          }
          leaf remote-lan {
              description 
                "Enter Remote-LAN name";
              type string;
          }
          list wlan {
              description 
                "Add WLAN to ap group";
              tailf:cli-mode-name "config-wlan-apgroup";
              key "name";
              leaf name {
                  description 
                    "Enter WLAN name";
                  type string;
              }              
              uses ap-wlan-grouping;
         }
        }
      }
      //// ap dot11
      container dot11 {
	description
	 "Configures 802.11 parameters";
        container _24ghz {
	  tailf:alt-name "24ghz";
          description
	   "Configures 802.11b parameters.";
	  container rate {
	    description
	     "Configure 802.11b operational rates";
		        container RATE_11M {
                            description
			     "802.11 12M Rate"; 
			    leaf supported {
			     description
			      "set a rate to supported";
				type empty;
			    }
                        }
                        container RATE_12M {
                            description
			     "802.11 12M Rate";
			    leaf supported {
			     description
			      "set a rate to supported";
			       type empty;
			    }
                        }
                        container RATE_18M {
                            description
			     "802.11 18M Rate";
                	    leaf supported {
			     description
			      "set a rate to supported";
			     type empty;
			    }
                        }
			container RATE_1M {
                            description
			     "802.11 12M Rate";
			    leaf supported {
			      description
			       "set a rate to supported";
			      type empty;
			    }
                        }
                        container RATE_24M {
                            description
			     "802.11 24M Rate";
			    leaf supported {
			     description
			      "set a rate to supported";
			      type empty;
			    }
                        }
		        container RATE_2M {
                            description
			     "802.11 24M Rate";
			    leaf supported {
			     description
			      "set a rate to supported";
			     type empty;
			    }
                        }
                        container RATE_36M {
                            description
			     "802.11 36M Rate";
			    leaf supported {
			     description
			      "set a rate to supported";
			     type empty;
			    }
                        }
                        container RATE_48M {
                            description
			     "802.11 48M Rate";
			    leaf supported {
			      description
			       "set a rate to supported";
			      type empty;
			    }
                        }
                        container RATE_54M {
                            description
			     "802.11 54M Rate";
			    leaf supported {
			     description
			      "set a rate to supported";
			     type empty;
			    }
                        }
			container RATE_5_5M {
                            description
			     "802.11 5.5M Rate";
 			    leaf supported {
			     description
			      "set a rate to supported";
			     type empty;
			    }
                        }
                        container RATE_6M {
                            description
			     "802.11 6M Rate";
			    leaf supported {
			     description
			      "set a rate to supported";
			     type empty;
			    }
                        }
                        container RATE_9M {
                            description
			     "802.11 9M Rate";
			    leaf supported {
			      description
			       "set a rate to supported";
			      type empty;
			    }
                        }
            }// rate
	} //c 24ghz
	container _49ghz {
	  tailf:alt-name "49ghz";
          description
	   "Configures 802.11a parameters.";
	  container rrm {
	   description
	    "Radio Resource Management";
	    container profile {
	      description
		"802.11a performance profile";
		leaf foreign {
		 description
		  "802.11a foreign interference threshold (0-100)";
		     type uint8 {
                       range "0..100";
		     }
		} // foreign
	    } // profile
	  }   // c rrm
	}     // c 49ghz
	container _5ghz {
	   tailf:alt-name "5ghz";
           description
	    "Configures 802.11a parameters.";
	   container rate {
	    description
	     "Configure 802.11b operational rates";
		        container RATE_11M {
                            description
			     "802.11 12M Rate";
			    leaf supported {
			     description
			      "set a rate to supported";
				type empty;
			    }
                        }
                        container RATE_12M {
                            description
			     "802.11 12M Rate";
			    leaf supported {
			     description
			      "set a rate to supported";
			       type empty;
			    }
                        }
                        container RATE_18M {
                            description
			     "802.11 18M Rate";
			    leaf supported {
			      description
			       "set a rate to supported";
			      type empty;
			    }
                        }
			container RATE_1M {
                            description
			     "802.11 12M Rate";
			    leaf supported {
			      description
			       "set a rate to supported";
			      type empty;
			    }
                        }
                        container RATE_24M {
                            description
			     "802.11 24M Rate";
			    leaf supported {
			     description
			      "set a rate to supported";
			     type empty;
			    }
                        }
		        container RATE_2M {
                            description
			     "802.11 24M Rate";
 			    leaf supported {
			       description
			        "set a rate to supported";
			       type empty;
			    }
                        }
                        container RATE_36M {
                            description
			     "802.11 36M Rate";
 			    leaf supported {
			      description
			       "set a rate to supported";
			      type empty;
			    }
                        }
                        container RATE_48M {
                            description
			     "802.11 48M Rate";
			    leaf supported {
			      description
			       "set a rate to supported";
			      type empty;
			    }
                        }
                        container RATE_54M {
                            description
			     "802.11 54M Rate";
			    leaf supported {
			     description
			      "set a rate to supported";
			     type empty;
			    }
                        }
			container RATE_5_5M {
                            description
			     "802.11 5.5M Rate";
			    leaf supported {
			      description
			       "set a rate to supported";
			      type empty;
			    }
                        }
                        container RATE_6M {
                            description
			     "802.11 6M Rate";
			    leaf supported {
			      description
			       "set a rate to supported";
			      type empty;
			    }
                        }
                        container RATE_9M {
                            description
			     "802.11 9M Rate";
 			    leaf supported {
			      description
			       "set a rate to supported";
			      type empty;
			    }
                        }
            } // rate
        } // c 5ghz
	container airtime-fairness {
	  description
	    "Configures airtime-fairness policy";
	  list policy-name {
	    description
	      "Configure airtime-fairness policy";
	    tailf:cli-suppress-mode;
            tailf:cli-sequence-commands;
            tailf:cli-compact-syntax;
            key "policy-name";
	    leaf policy-name {
	      description
		"Enter the airtime-fairness policy name"; 
	      tailf:cli-full-command;
	      type string;
	    }
	    leaf policy-id {
	      tailf:cli-drop-node-name;
	      type uint16 {
                range "0..511";
	      }   
	    } 
	  } // list policy-name
	}   // airtime-fairness
      } // ap dot11
    } 

    /// ========================================================================
    /// wsma
    /// ========================================================================
    container wsma {
      description
        "Configure Web Services Management Agents";
      container agent {
        description
          "Configure WSMA agents";
        container exec {
          description
            "Start WSMA exec agent";
          tailf:cli-add-mode;
          tailf:cli-mode-name "wsma-exec-agent";
          leaf-list profile {
            tailf:cli-list-syntax;
            type string;
          }
        }
        container config {
          description
            "Start WSMA config agent";
          tailf:cli-add-mode;
          tailf:cli-mode-name "wsma-config-agent";
          leaf-list profile {
            tailf:cli-list-syntax;
            type string;
          }
        }
        container filesys {
          description
            "Start WSMA file system agent";
          tailf:cli-add-mode;
          tailf:cli-mode-name "wsma-filesys-agent";
          leaf-list profile {
            tailf:cli-list-syntax;
            type string;
          }
        }
        container notify {
          description
            "Start WSMA notify agent";
          tailf:cli-add-mode;
          tailf:cli-mode-name "wsma-notify-agent";
          leaf-list profile {
            tailf:cli-list-syntax;
            type string;
          }
        }
      }
      container profile {
        description
          "Configure WSMA profile";
        list listener {
          description
            "Configure a listener profile";
          tailf:cli-mode-name "config-wsma-listen";
          key "name";
          leaf name {
            type string;
          }
          leaf transport {
            description
              "The transport to use";
            type enumeration {
              enum "http";
              enum "https";
              enum "ssh";
              enum "tls";
            }
          }
        }
      }
    }

    /// ========================================================================
    /// rep
    /// ========================================================================
    container rep {
      description
        "Resilient Ethernet Protocol characteristics";
      container admin {
        description
          "administrative configuration";
        list vlan {
          description
            "VLAN";
          key "name";
          leaf name {
            type uint16 {
              range "2..4094";
            }
          }
        }
      }
    }
 

    /// ========================================================================
    /// xconnect
    /// ========================================================================
    container xconnect {
      container logging {
        // xconnect pseudowire
        container pseudowire {
          leaf status {
            tailf:cli-full-command;
            type empty;
          }
        }
        // xconnect redundancy2
        leaf redundancy {
          tailf:cli-full-command;
          type empty;
        }
      }
    }

    /// ========================================================================
    /// fabric
    /// ========================================================================
    container fabric {
      description
        "Catalyst 6000 crossbar fabric configuration commands";
            //  buffer-reserve  Reserve FIFO buffer
            //  clear-block     Enable clear-block congestion control for
            //                  fabric channels
            //  error-recovery  Fabric error-recovery
            //  required        Fabric required for system to operate

            // fabric switching-mode
      container switching-mode {
        description
          "Switching mode settings";
        container allow {
          description
            "Allow settings";
          choice allow-choice {
            leaf bus-mode {
              description
                "Allow switching in bus mode for modules";
              type empty;
            }
            container truncated {
              description
                "Truncated switching mode";
              presence "true";
              leaf threshold {
                description
                  "Number of SFM-capable modules for truncated switching mode. Switch applies the threshold only when the mode is disallowed. Switch ignores the threshold when the truncated mode is allowed";
                type uint8 {
                  range "1..9";
                }
              }
            }
          }
        }
        container force {
          description
            "Force modules to different switching modes";
          leaf bus-mode {
            description
              "Switching mode of service modules will be forced to bus-mode by powercycling it.";
            type empty;
          }
        }
      }
      //  timer           set poll time (in Seconds) for drop counter
      //                  timestamp and peak utilization
    }


    /// ========================================================================
    /// port-channel
    /// ========================================================================
    container port-channel {
      description
        "EtherChannel configuration";
            //  hash-distribution  Hash Distribution method
      // port-channel auto
      leaf auto {
        description 
          "LACP auto for the system";
        type empty;
      }
            // port-channel load-balance
      container load-balance {
        description
          "Load Balancing method";
        leaf load-balance {
          tailf:cli-drop-node-name;
          type enumeration {
            enum "dst-ip";
            enum "dst-mac";
            enum "dst-mixed-ip-port";
            enum "dst-port";
            enum "mpls";
            enum "src-dst-ip";
            enum "src-dst-mac";
            enum "src-dst-mixed-ip-port";
            enum "src-dst-port";
            enum "src-ip";
            enum "src-mac";
            enum "src-mixed-ip-port";
            enum "src-port";
          }
        }
        //extended
       container extended {
         description 
           "Extended Load Balance Methods";
         presence true;
         leaf-list extended {
           tailf:cli-flat-list-syntax;
           tailf:cli-drop-node-name;       
           type enumeration {
             enum "dst-ip";
             enum "dst-mac";
             enum "dst-port";
             enum "ipv6-label";
             enum "l3-proto";
             enum "src-ip";
             enum "src-mac";
             enum "src-port";
           }
         }
       }
     }
     
//  per-module         per-module configuration
    }

    /// ========================================================================
    /// key
    /// ========================================================================
    container key {
      description
        "Key management";
      list chain {
        description
          "Key-chain management";
        tailf:cli-mode-name "config-keychain";
        key "name";
        leaf name {
          type string;
        }
        leaf macsec {
          tailf:cli-hide-in-submode;
          type empty;
        }
        list key {
          description
            "Configure a key";
          tailf:cli-mode-name "config-keychain-key";
          key "id";
          leaf id {
            type string;
          }
          leaf cryptographic-algorithm {
            description 
              "Set cryptographic authentication algorithm";
            type enumeration {
              enum "aes-128-cmac";
              enum "aes-256-cmac";
              enum "hmac-sha-1";
              enum "hmac-sha-256";
              enum "hmac-sha-384";
              enum "hmac-sha-512";
              enum "md5";
            }  
          }
          container key-string {
            description
              "Set key string";
            tailf:cli-compact-syntax;
            leaf encryption {
              tailf:cli-drop-node-name;
              type enumeration {
                enum "0";
                enum "6";
                enum "7";
              }
            }
            leaf key {
              tailf:cli-drop-node-name;
              type string {
                length "0..80";
              }
            }
          }
        }
      }
    }
    
    /// ========================================================================
    /// l2
    /// ========================================================================
    container l2 {
      description
        "Layer 2 configuration";
      leaf router-id {
        description
          "Configure a layer 2 identifier";
        type inet:ipv4-address;
      }
      // l2 vfi *
      list vfi {
        description
          "Configure a virtual forwarding instance";
        tailf:cli-mode-name "config-vfi";
        tailf:cli-compact-syntax;
        key "name";
        leaf name {
          type string;
        }
        leaf mode {
          tailf:cli-drop-node-name;
          tailf:cli-hide-in-submode;
          type enumeration {
            enum "autodiscovery";
            enum "manual";
            enum "point-to-point";
          }
        }
        leaf evc {
          when "../mode = 'autodiscovery' or ../mode = 'manual'";
          tailf:cli-drop-node-name;
          tailf:cli-hide-in-submode;
          type string;
        }
        container vpn {
          description
            "VPN configuration";
          when "../mode = 'autodiscovery' or ../mode = 'manual'";
          leaf id {
            description
              "VPN id";
            type uint64 {
              range "1..4294967295";
            }
          }
        }
        leaf bridge-domain {
          description
            "bridge-domain";
          type uint16 {
            range "1..16384";
          }
        }
        list neighbor {
          description
            "VFI neighbor configuration";
          tailf:cli-suppress-mode;
          tailf:cli-sequence-commands;
          tailf:cli-compact-syntax;
          key "router-id";
          leaf router-id {
            type inet:ipv4-address;
          }
          leaf vc-id {
            tailf:cli-drop-node-name;
            tailf:cli-optional-in-sequence;
            type uint64 {
              range "1..4294967295";
            }
          }
          leaf encapsulation {
            description
              "Connection encapsulation type";
            tailf:cli-break-sequence-commands;
            tailf:cli-full-command;
            type enumeration {
              enum "l2tpv3";
              enum "mpls";
            }
          }
          leaf pw-class {
            description
              "Pseudowire-class configuration";
            type string;
          }
        }
      }
    }
    
    /// ========================================================================
    /// l2protocol-tunnel
    /// ========================================================================
    container l2protocol-tunnel {
      description
        "Tunnel Layer2 protocols";
      leaf cos {
        description
          "Class of Service";
        type uint8 {
          range "0..7";
        }
      }
      container global {
        description
          "Global settings";
        leaf drop-threshold {
          description
            "L2PT packets drop threshold";
          type uint16 {
            range "100..20000";
          }
        }
      }
    }
    
    /// ========================================================================
    /// system
    /// ========================================================================
    container system {
      description
        "Set the system configuration";
      container debug {
        description
          "Debug Shell";
        container shell {
          description
            "Debug Shell";
          container switch {
            description
              "Set config on switches in stack";
            leaf switch-number {
              description
                "Switch number";
              tailf:cli-drop-node-name;
              type uint8 {
                range "1..9";
              }
            }
            leaf all {
              description
                "Set config for all switches in stack";
              type empty;
            }
          }
        }
      }
      container disable {
        description
          "Disable password recovery";
        container password {
          description
            "Disable password recovery";
          container recovery {
            description
              "Disable password recovery";
            container switch {
              description
                "Set config on switches in stack";
              leaf number {
                description
                  "Switch number";
                tailf:cli-drop-node-name;
                type uint8 {
                  range "1..9";
                }
              }
              leaf all {
                description
                  "Set config for all switches in stack";
                type empty;
              }
            }
          }
        }
      }
      container environment {
        description
          "Set the system environment settings";
        container fan-fail-action {
          description
            "Set the FRU/PS fan fail action. ";
          leaf shut {
            description
              "Shutdown the system when multiple fan fails";
            type empty;
          }
        }
        container temperature {
          description
            "Set the system temperature settings";
          container threshold {
            description
              "Set the system temperature thresholds";
            container yellow {
              description
                "Set the yellow thresholds. ";
              tailf:cli-sequence-commands;
              tailf:cli-compact-syntax;
              leaf delta-value {
                tailf:cli-drop-node-name;
                description
                  "Delta value from Red threshold in Degree Celcius";
                type uint8 {
                  range "5..25";
                }
              }
              leaf detail {
                description
                  "print yellow temperature threshold";
                tailf:cli-optional-in-sequence;
                type empty;
              }
            }
          }
        }
      }
      container fnf {
        description
          "Flexible Netflow";
        container bytes-count {
          description
            "Bytes Count";
          leaf layer2 {
            description
              "Show L2 bytes in byte count collect field";
            type empty;
          }
        }
      }
      container ignore {
        description
          "Ignore Startup Config";
        container startupconfig {
          description
            "Ignore Startup Config";
          container switch {
            description
              "Set config on switches in stack";
            leaf number {
              description
                "Switch number";
              tailf:cli-drop-node-name;
              type uint8 {
                range "1..9";
              }
            }
            leaf all {
              description
                "Set config for all switches in stack";
              type empty;
            }
          }
        }
      }
      container mode-button {
        description
          "Enable Mode button for reset";
        leaf reset {
          description
            "Enable reset";
          type empty;
        }
      }
      container mtu {
        description
          "Set the system Maximum Transmission Unit (MTU)";
        leaf size {
          tailf:cli-drop-node-name;
          type uint16 {
            range "1500..9198";
          }
        }
        leaf jumbo {
          description
            "Set Jumbo MTU value for GigabitEthernet or TenGigabitEthernet interfaces";
          type uint16 {
            range "1500..9000";
          }
        }
        leaf routing {
          description
            "Set the Routing MTU for the system";
          type uint16 {
            range "1500";
          }
        }
      }
    }
    
    /// ========================================================================
    /// errdisable
    /// ========================================================================
    container errdisable {
      description
        "Error disable";
      // errdisable detect
      container detect {
        description
          "Error disable detection";
        container cause {
          description
            "Enable error disable detection for application";
          leaf all {
            description
              "Enable error detection on all cases";
            tailf:cli-full-command;
            type empty;
          }
          leaf arp-inspection {
            description
              "Enable error detection for arp inspection";
            tailf:cli-full-command;
            type empty;
          }
          leaf bpduguard {
            description
              "Enable error detection on bpdu-guard";
            tailf:cli-full-command;
            type empty;
          }
          leaf dhcp-rate-limit {
            description
              "Enable error detection on dhcp-rate-limit";
            tailf:cli-full-command;
            type empty;
          }
          leaf dtp-flap {
            description
              "Enable error detection on dtp-flapping";
            tailf:cli-full-command;
            type empty;
          }
          leaf gbic-invalid {
            description
              "Enable error detection on gbic-invalid";
            tailf:cli-full-command;
            type empty;
          }
          leaf inline-power {
            description
              "Enable error detection for inline-power";
            tailf:cli-full-command;
            type empty;
          }
          leaf l2ptguard {
            description
              "Enable timer to recover from l2protocol-tunnel error disable state";
            tailf:cli-full-command;
            type empty;
          }
          leaf link-flap {
            description
              "Enable error detection on linkstate-flapping";
            tailf:cli-full-command;
            type empty;
          }
          leaf loopback {
            description
              "Enable error detection on loopback";
            tailf:cli-full-command;
            type empty;
          }
          leaf mlacp-minlink {
            tailf:cli-full-command;
            type empty;
          }
          leaf pagp-flap {
            description
              "Enable error detection on pagp-flapping";
            tailf:cli-full-command;
            type empty;
          }
          leaf pppoe-ia-rate-limit {
            description
              "Enable error detection on PPPoE IA rate-limit";
            tailf:cli-full-command;
            type empty;
          }
          container security-violation {
            description "Enable error detection on 802.1x-guard";
            container shutdown {
              description "Specify error disable shutdown mode for 802.1x-guard";
              leaf vlan {
                description "Shutdown vlan on 802.1x-guard violation";
                type empty;
              }
            }
          }
          leaf sfp-config-mismatch {
            description
              "Enable error detection on SFP config mismatch";
            tailf:cli-full-command;
            type empty;
          }
          leaf small-frame {
            description
              "Enable error detection on small_frame";
            tailf:cli-full-command;
            type empty;
          }
        }
      }
      // errdisable flap-setting
      container flap-setting {
        description
          "Error disable flap detection setting";
        container cause {
          description
            "Set error disable flap parameters for application";
          container dtp-flap {
            description
              "Set the variables related to detection of dtp flaps";
            tailf:cli-compact-syntax;
            tailf:cli-sequence-commands;
            leaf max-flaps {
              description
                "maximum flaps allowed before setting to errdisable";
              type uint8 {
                range "1..100";
              }
            }
            leaf time {
              description
                "time period the flaps are counted";
              type uint8 {
                range "1..120";
              }
            }
          }
          container link-flap {
            description
              "Set the variables related to detection of link flaps";
            tailf:cli-compact-syntax;
            tailf:cli-sequence-commands;
            leaf max-flaps {
              description
                "maximum flaps allowed before setting to errdisable";
              type uint8 {
                range "1..100";
              }
            }
            leaf time {
              description
                "time period the flaps are counted";
              type uint8 {
                range "1..120";
              }
            }
          }
          container pagp-flap {
            description
              "Set the variables related to detection of pagp flaps";
            tailf:cli-compact-syntax;
            tailf:cli-sequence-commands;
            leaf max-flaps {
              description
                "maximum flaps allowed before setting to errdisable";
              type uint8 {
                range "1..100";
              }
            }
            leaf time {
              description
                "time period the flaps are counted";
              type uint8 {
                range "1..120";
              }
            }
          }
        }
      }
      // errdisable recovery
      container recovery {
        description
          "Error disable recovery";
        // errdisable recovery cause
        container cause {
          description
            "Enable error disable recovery for application";
          leaf all {
            description
              "Enable timer to recover from all error causes";
            type empty;
          }
          leaf arp-inspection {
            description
              "Enable timer to recover from arp inspection error disable state";
            type empty;
          }
          leaf bpduguard {
            description
              "Enable timer to recover from BPDU Guard error";
            type empty;
          }
          leaf channel-misconfig {
            description
              "(STP)  Enable timer to recover from channel misconfig error";
            type empty;
          }
          leaf dhcp-rate-limit {
            description
              "Enable timer to recover from dhcp-rate-limit error";
            type empty;
          }
          leaf dtp-flap {
            description
              "Enable timer to recover from dtp-flap error";
            type empty;
          }
          leaf gbic-invalid {
            description
              "Enable timer to recover from invalid GBIC error";
            type empty;
          }
          leaf inline-power {
            description
              "Enable timer to recover from inline-power error";
            type empty;
          }
          leaf l2ptguard {
            description
              "Enable timer to recover from l2protocol-tunnel error disable state";
            type empty;
          }
          leaf link-flap {
            description
              "Enable timer to recover from link-flap error";
            type empty;
          }
          leaf link-monitor-failure {
            type empty;
          }
          leaf loopback {
            description
              "Enable timer to recover from loopback error";
            type empty;
          }
          leaf mac-limit {
            description
              "Enable timer to recover from mac limit disable state";
            type empty;
          }
          leaf mlacp-minlink {
            tailf:cli-full-command;
            type empty;
          }
          container oam-remote-failure {
            tailf:cli-display-separated;
            presence "true";
            leaf critical-event {
              tailf:cli-full-command;
              type empty;
            }
            leaf dying-gasp {
              tailf:cli-full-command;
              type empty;
            }
            leaf link-fault {
              tailf:cli-full-command;
              type empty;
            }
          }
          leaf pagp-flap {
            description
              "Enable timer to recover from pagp-flap error";
            type empty;
          }
          leaf port-mode-failure {
            description
              "Enable timer to recover from port mode change failure";
            type empty;
          }
          leaf pppoe-ia-rate-limit {
            description
              "Enable timer to recover from PPPoE IA rate-limit error";
            type empty;
          }
          leaf psp {
            type empty;
          }
          leaf psecure-violation {
            description
              "Enable timer to recover from psecure violation error";
            type empty;
          }
          leaf security-violation {
            description
              "Enable timer to recover from 802.1x violation error";
            type empty;
          }
          leaf sfp-config-mismatch {
            description
              "Enable timer to recover from SFP config mismatch error";
            type empty;
          }
          leaf small-frame {
            description
              "Enable timer to recover from small frame error";
            type empty;
          }
          leaf storm-control {
            description
              "Enable timer to recover from storm-control error";
            type empty;
          }
          leaf udld {
            description
              "Enable timer to recover from udld error";
            type empty;
          }
          leaf unicast-flood {
            type empty;
          }
          leaf vmps {
            description
              "Enable timer to recover from vmps shutdown error";
            type empty;
          }
        }
        leaf interval {
          description
            "Error disable recovery timer value";
          type uint32 {
            range "30..86400";
          }
        }
      }
    }
    ///==================================================================
    /// identity 
    ///==================================================================
    container identity {
      description "Identity Configuration Commands";
      container profile {
        description "Create an Identity profile";
        leaf dot1x {  
          description "Service type for 802.1x";
          type empty;
        }
        leaf default {
          description "Service type default";
          type empty;
        }
      }
    }
    /// =======================================================================
    /// monitor
    /// =======================================================================
    container monitor {
      description
        "Monitoring different system events";
      container event-trace {
        description
          "Tracing of system events";
              //  all-traces       Configure merged event traces
              //  datainteg        Data integrity events
              //  ipv6             IPv6
              //  sequence-number  Display event trace entries with sequence number
              //  stacktrace       Display stack trace stored with event trace entries
              //  timestamps       Format of event trace timestamps
      }
      // monitor session *
      list session {
        description
          "Configure a SPAN session";
        tailf:cli-suppress-mode;
        tailf:cli-delete-when-empty;
        tailf:cli-compact-syntax;
        tailf:cli-incomplete-command;
        key "id";
        leaf id {
          type uint8 {
            range "1..66";
          }
        }
        // monitor session * destination
        container destination {
          description
            "SPAN destination interface or VLAN";
	  tailf:cli-compact-syntax;
          list interface {
            description
              "SPAN destination interface";
	    tailf:cli-suppress-mode;
	    tailf:cli-sequence-commands;
	    tailf:cli-compact-syntax;
	    key "name";
	    leaf name {
	      description
		"Enter interface name , for eg. GigabitEthernet1/0/1 or Gi1/0/1";
              type string;
            }
            leaf encapsulation {
              description
                "Set encapsulation for destination interface";
              type enumeration {
                enum "dot1q";
                enum "isl";
                enum "replicate";
              }
            }
            leaf ingress {
              description
                "Enable ingress traffic forwarding";
              type empty;
            }
            leaf ingress-encap {
              tailf:cli-drop-node-name;
              when "../ingress" {
                tailf:dependency "../ingress";
              }
              type enumeration {
                enum "dot1q";
                enum "isl";
                enum "untagged";
              }
            }
            leaf vlan {
              description
                "Set default VLAN for untagged ingress traffic";
              when "../ingress" {
                tailf:dependency "../ingress";
              }
              type uint16 {
                range "1..4094";
              }
            }
	  }
          //  remote     SPAN destination Remote
          container remote {
            description "SPAN destination Remote";
            leaf vlan {
              description "Remote SPAN destination RSPAN VLAN";
              type uint16 {
                range "1006..4094";
              }
            }
          }
        }
        //  filter       SPAN filter VLAN
        // monitor session * filter       SPAN filter VLAN
        container filter {
          description
            "SPAN filter VLAN";
          container packet-type {
            tailf:cli-sequence-commands;
            tailf:cli-compact-syntax;
            leaf status {
              tailf:cli-drop-node-name;
              type enumeration {
                enum "good";
                enum "bad";
              }
            }
            leaf direction {
              tailf:cli-drop-node-name;
              type enumeration {
                enum "rx";
                enum "tx";
              }
            }
          }
          container ip {
            description "Specify IP Access control rules";
            container access-group {
              description "Specify access control group";
              leaf acl-name {
                description "Access-list name";
                tailf:cli-drop-node-name;
                type string;
              }
            }
          }
        }
        // monitor session * source
        container source {
          description
            "SPAN source interface, VLAN ";
          list interface {
	    tailf:cli-suppress-mode;
	    tailf:cli-sequence-commands;
	    tailf:cli-compact-syntax;
            description
              "SPAN source interface";
	    key "name";
	    leaf name {
	      description "Enter interface name , for eg. GigabitEthernet1/0/1 or Gi1/0/1";
	      type string;
	    }
            leaf direction {
              tailf:cli-drop-node-name;
              type enumeration {
                enum "both";
                enum "rx";
                enum "tx";             
              }
            }	    
          }
          container vlan {
            description
              "SPAN source VLAN";
            tailf:cli-compact-syntax;
            tailf:cli-flatten-container;
            tailf:cli-sequence-commands;
            leaf vlan {
              tailf:cli-drop-node-name;
              type uint16 {
                range "1..4094";
              }
            }
            // ,     Specify another range of VLANs
            // -     Specify a range of VLANs
            leaf direction {
              tailf:cli-drop-node-name;
              type enumeration {
                enum "both";
                enum "rx";
                enum "tx";
              }
            }
          }
          //  remote     SPAN source Remote
	  container remote {
	   description
	    "SPAN source Remote";
	     leaf vlan {
	      description
	       "Remote SPAN source RSPAN VLAN <1-1001>|<1006-4094>";
	       type uint16 {
		range "1..1001 | 1006..4094";	
	       }
	     }
          } // remote
        }
      }
    }
    
    /// ========================================================================
    /// tftp-server
    /// ========================================================================
    list tftp-server {
      description
        "Provide TFTP service for netload requests";
      tailf:cli-suppress-mode;
      tailf:cli-delete-when-empty;
      tailf:cli-compact-syntax;
      key "name";
      leaf name {
        type string;
      }
    }
    
    /// ========================================================================
    /// radius-server
    /// ========================================================================
    container radius-server {
      description
        "Modify RADIUS query parameters";
      tailf:cli-diff-dependency "/ios:native/aaa";
      // radius-server attribute           Customize selected radius attributes
      list attribute {
        description
          "Customize selected radius attributes";
        tailf:cli-suppress-mode;
        key "number";
        leaf number {
          type uint32;
        }
        leaf send-attribute {
          tailf:cli-drop-node-name;
          type enumeration {
            enum "on-for-login-auth";
            enum "include-in-access-req";
          }
        }
        container access-request {
          description
            "Access-Request packet";
          when "../number = '25'";
          leaf include {
            description
              "Include attribute";
            type empty;
          }
        }
      }
            //  authorization       Authorization processing information
            //  backoff             Retry backoff pattern(Default is retransmits with
            //                      constant delay)
            //  cache               AAA auth cache default server group
            //  challenge-noecho    Data echoing to screen is disabled during
            //                      Access-Challenge
            //  configure-nas       Attempt to upload static routes and IP pools
            //                      at startup
            //  dead-criteria       Set the criteria used to decide when a radius
      // snmp-server dead-criteria       Set the criteria used to decide when a radius
      container dead-criteria {
        description
          "Set the criteria used to decide when a radius server ismarked dead";
        tailf:cli-compact-syntax;
        leaf time {
          description
            "The time during which no properly formed response must be recievedfrom the RADIUS server";
          type uint8 {
            range "1..120";
          }
        }
        leaf tries {
          description
            "The number of times the router must fail to recieve a response fromthe radius server to mark it as dead";
          tailf:cli-full-command;
          type uint8 {
            range "1..100";
          }
        }
      }
      //                      server is marked dead
      //  deadtime            Time to stop using a server that doesn't respond
      // radius-server deadtime *
      leaf deadtime {
        description
          "Time to stop using a server that doesn't respond";
        tailf:cli-full-command;
        type uint32 {
          range "1..1440";
        }
      }
      //  directed-request    Allow user to specify radius server to use
      //                      with `@server'
      //  domain-stripping    Strip the domain from the username
      // radius-server host *
      list host {
        description
          "Specify a RADIUS server";
        tailf:cli-suppress-mode;
        tailf:cli-delete-when-empty;
        tailf:cli-compact-syntax;
        key "id";
        leaf id {
          type union {
            type string;
            type inet:ipv4-address;
          }
        }
        // radius-server host * auth-port
        leaf auth-port {
          description
            "UDP port for RADIUS authentication server (default is 1645)";
          type uint16 {
            range "0..65535";
          }
        }
        // radius-server host * acct-port
        leaf acct-port {
          description
            "UDP port for RADIUS accounting server (default is 1646)";
          type uint16 {
            range "0..65535";
          }
        }
        //  alias         1-8 aliases for this server (max. 8)
        //  backoff       Retry backoff pattern (Default is retransmits with
        //                constant delay)
        //  non-standard  Parse attributes that violate the RADIUS standard
        // radius-server host * retransmit
        //  retransmit    Specify the number of retries to active server
        //                (overrides default)
        leaf retransmit {
          description
            "Specify the number of retries to active server";
          type uint8 {
            range "1..100";
          }
        }
        //  test          Configure server automated testing.
        // radius-server host * test
        container test {
          description
            "Configure server automated testing";
          list username {
            description
              "A name (from local database) that should be used to send requests.";
            tailf:cli-suppress-mode;
            key "name";
            leaf name {
              type string;
            }
            container key {
              description
                "per-server encryption key (overrides default)";
              tailf:cli-compact-syntax;
              leaf encryption {
                tailf:cli-drop-node-name;
                type enumeration {
                  enum "0";
                  enum "7";
                }
              }
              leaf clear-key {
                tailf:cli-drop-node-name;
                tailf:cli-full-command;
                type string;
              }
            }
          }
        }
        // radius-server host * timeout
        leaf timeout {
          description
            "Time to wait for a RADIUS server to reply (overrides default)";
          type uint16 {
            range "1..1000";
          }
        }
        // radius-server host * key
        leaf key {
          description
            "per-server encryption key (overrides default)";
          type union {
            type enumeration {
              enum "0";
              enum "7";
            }
            type string;
          }
        }
        leaf clear-key {
          when "../key = '0' or ../key = '7'";
          tailf:cli-drop-node-name;
          tailf:cli-full-command;
          type string;
        }
        //  non-standard  Parse attributes that violate the RADIUS standard
      }
      //  key                 encryption key shared with the radius servers
      container key {
        description
          "encryption key shared with the radius servers";
        tailf:cli-compact-syntax;
        leaf encryption {
          tailf:cli-drop-node-name;
          type enumeration {
            enum "0";
            enum "7";
          }
        }
        leaf clear-key {
          tailf:cli-drop-node-name;
          tailf:cli-full-command;
          type string;
        }
      }
      //  load-balance        Radius load-balancing options.
      //  optional-passwords  The first RADIUS request can be made without
      //                      requesting a password
      //  retransmit          Specify the number of retries to active server
      leaf retransmit {
        description
          "Specify the number of retries to active server";
        tailf:cli-full-command;
        type uint8 {
          range "1..100";
        }
      }
      //  retry               Specify how the next packet is sent after timeout.
      //  source-ports
      container source-ports {
        description
          "source ports used for sending out RADIUS requests";
        leaf extended {
          description
            "Use 200 source-ports between 21645-21844";
          type empty;
        }
      }
      //  timeout             Time to wait for a RADIUS server to reply
      leaf timeout {
        description
          "Time to wait for a RADIUS server to reply";
        tailf:cli-full-command;
        type uint16 {
          range "1..1000";
        }
      }
      //  transaction         Specify per-transaction parameters
      //  unique-ident        Higher order bits of Acct-Session-Id
      // radius-server vsa *                Vendor specific attribute configuration
      container vsa {
        description
          "Vendor specific attribute configuration";
        container disallow {
          description
            "Forbid certain VSA behaviour";
          leaf unknown {
            description
              "Forbid unknown VSAs";
            type empty;
          }
        }
        container send {
          description
            "Send vendor-specific attributes in requests";
          presence "true";
          container accounting {
            description
              "Send in accounting requests";
            presence "true";
            leaf threegpp2 {
              tailf:alt-name "3gpp2";
              description
                "Send 3GPP2 VSAs in accounting requests";
              type empty;
            }
          }
          container authentication {
            description
              "Send in access requests";
            presence "true";
            leaf threegpp2 {
              tailf:alt-name "3gpp2";
              description
                "Send 3GPP2 VSAs in accounting requests";
              type empty;
            }
          }
          container cisco-nas-port {
            description
              "Send cisco-nas-port VSA(2)";
            presence "true";
            leaf threegpp2 {
              tailf:alt-name "3gpp2";
              description
                "Send 3GPP2 VSAs in accounting requests";
              type empty;
            }
          }
        }
      }
    }

    /// ========================================================================
    /// radius
    /// ========================================================================
    container radius {
      description
        "RADIUS server configuration command";
      tailf:cli-diff-dependency "/ios:native/aaa";
      list filter {
        description
          "Packet filter configuration";
        key "id";
        leaf id {
          type string;
        }
        leaf match {
          tailf:cli-drop-node-name;
          tailf:cli-prefix-key;
          type enumeration {
            enum "match-all";
            enum "match-any";
          }
        }
      }
      list server {
        description
          "Server configuration";
        tailf:cli-mode-name "config-radius-server";
        key "id";
        leaf id {
          type string;
        }
        container address {
          description
            "Specify the radius server address";
          container ipv4 {
            description
              "IPv4 Address";
            tailf:cli-compact-syntax;
            tailf:cli-sequence-commands {
              tailf:cli-reset-siblings;
            }
            leaf host {
              tailf:cli-drop-node-name;
              type string;
            }
            leaf auth-port {
              description
                "UDP port for RADIUS authentication server (default is 1645)";
              tailf:cli-optional-in-sequence;
              type uint16 {
                range "0..65535";
              }
            }
            leaf acct-port {
              description
                "UDP port for RADIUS accounting server (default is 1646)";
              type uint16 {
                range "0..65535";
              }
            }
          }
        }
        container backoff {
          description
            "Retry backoff pattern(Default is retransmits with constant delay)";
          container exponential {
            description
              "Exponential retransmit backoff";
            tailf:cli-compact-syntax;
            tailf:cli-sequence-commands {
              tailf:cli-reset-siblings;
            }
            presence "true";
            leaf max-delay {
              tailf:cli-optional-in-sequence;
              description
                "Max delay between retransmits(default is 3 min)";
              type uint8 {
                range "1..120";
              }
            }
            leaf backoff-retry {
              description
                "Exponential backoff retry number(default is 8)";
              type uint8 {
                range "1..50";
              }
            }
          }
        }
        container key {
          description
            "Per-server encryption key";
          tailf:cli-compact-syntax;
          tailf:cli-sequence-commands {
            tailf:cli-reset-siblings;
          }
          leaf encryption {
            tailf:cli-drop-node-name;
            tailf:cli-incomplete-command;
            tailf:cli-optional-in-sequence;
            type enumeration {
              enum "0";
              enum "5";
            }
          }
          leaf key {
            tailf:cli-drop-node-name;
            tailf:cli-multi-value;
            type string;
          }
        }
        container pac {
          description
            "Protected Access Credential key";
          container key {
            description
              "Per-server encryption key";
            tailf:cli-compact-syntax;
            tailf:cli-sequence-commands {
              tailf:cli-reset-siblings;
            }
            leaf encryption {
              tailf:cli-drop-node-name;
              tailf:cli-incomplete-command;
              tailf:cli-optional-in-sequence;
              type enumeration {
                enum "0";
                enum "6";
                enum "7";
              }
            }
            leaf key {
              tailf:cli-drop-node-name;
              tailf:cli-multi-value;
              type string;
            }
          }
        }
      }
    }


    /// ========================================================================
    /// zone
    /// ========================================================================
    container zone {
      description
        "FW with zoning";
      list security {
        description
          "Security zone";
        tailf:cli-mode-name "config-sec-zone";
        tailf:cli-full-command;
        key "id";
        leaf id {
          type string;
        }
        leaf description {
          description
            "Zone description";
          tailf:cli-multi-value;
          type string;
        }
        leaf protection {
          description
            "config sync cookie protection against sync flood";
          type string;
        }
      }
    }

    /// ========================================================================
    /// zone-pair
    /// ========================================================================
    container zone-pair {
      description
        "Zone pair command";
      list security {
        description
          "Zone-pair name";
        tailf:cli-sequence-commands {
          tailf:cli-reset-siblings;
        }
        tailf:cli-mode-name "config-sec-zone-pair";
        key "id";
        leaf id {
          type string;
        }
        leaf source {
          description
            "Source zone";
          tailf:cli-hide-in-submode;
          tailf:non-strict-leafref {
            path "/ios:native/zone/security/id";
          }
          type string;
        }
        leaf destination {
          description
            "Destination zone";
          tailf:cli-hide-in-submode;
          tailf:non-strict-leafref {
            path "/ios:native/zone/security/id";
          }
          type string;
        }
        leaf description {
          description
            "Zone description";
          tailf:cli-break-sequence-commands;
          tailf:cli-multi-value;
          type string {
            length "1..200";
          }
        }
        container service-policy {
          description
            "Configure CBAC Service Policy";
          container type {
            description
              "Service Policy type";
            leaf inspect {
              description
                "Configure CBAC Service Policy type inspect";
              type string;
              tailf:non-strict-leafref {
                path "/ios:native/policy-map/name";
              }
            }
          }
        }
      }
    }



    /// ========================================================================
    /// aaa
    /// ========================================================================
    container aaa {
      description
        "Authentication, Authorization and Accounting.";
      tailf:cli-incomplete-command;
      leaf new-model {
        description
          "Enable NEW access control commands and functions.(Disables OLD commands.)";
        type empty;
      }
      container group {
        description
          "AAA group definitions";
        tailf:cli-diff-dependency "/ios:native/aaa/new-model";
        container server {
          description
            "AAA Server group definitions";
          list tacacsplus {
            tailf:alt-name "tacacs+";
            description
              "Tacacs+ server-group definition";
            tailf:cli-mode-name "config-sg-tacacs+";
            tailf:cli-full-command;
            key "name";
            leaf name {
              type string;
            }
            container server {
              description
                "Specify a TACACS server";
              leaf name {
                description
                  "Name of tacacs server";
                type string;
              }
            }
            list server-private {
              description
                "Define a private TACACS server (per group)";
              tailf:cli-suppress-mode;
              tailf:cli-delete-when-empty;
              tailf:cli-compact-syntax;
              tailf:cli-sequence-commands;
              tailf:cli-reset-container;
              key "name";
              leaf name {
                type host-type;
              }
              leaf timeout {
                description
                  "Time to wait for this TACACS server to reply (overrides default)";
                tailf:cli-optional-in-sequence;
                type uint16 {
                  range "1..1000";
                }
              }
              container key {
                description
                  "per-server encryption key (overrides default)";
                tailf:cli-compact-syntax;
                tailf:cli-flatten-container;
                tailf:cli-sequence-commands;
                leaf encryption {
                  tailf:cli-drop-node-name;
                  tailf:cli-incomplete-command;
                  tailf:cli-optional-in-sequence;
                  type enumeration {
                    enum "0";
                    enum "7";
                  }
                }
                leaf key {
                  tailf:cli-drop-node-name;
                  tailf:cli-full-command;
                  tailf:cli-multi-value;
                  type string;
                }
              }
              //nat  To send client's post NAT address to tacacs+ server
              //port TCP port for TACACS+ server (default is 49)
              //single-connection Multiplex all packets over a single..
              //..tcp connection to server (for CiscoSecure)
            }
            container ip {
              description
                "Internet Protocol config commands";
              container tacacs {
                description
                  "TACACS configuration commands";
                container source-interface {
                  description
                    "Specify interface for source address in TACACS packets";
                  tailf:cli-diff-dependency "/ios:native/interface";
                  uses interface-grouping;
                }
              }
              container vrf {
                description
                  "Set VPN Routing Forwarding to use with the servers";
                leaf forwarding {
                  description
                    "Configure forwarding table";
                  type string;
                }
              }
            }
          }
          // aaa group server tacacs+
          list tacacs {
            tailf:alt-name "tacacs+";
            description "Tacacs+ server-group definition";
            tailf:cli-mode-name "config-sg-radius";
            key "name";
            leaf name {
              type string;
            }
          }
          // aaa group server radius *
          list radius {
            description
              "Radius server-group definition";
            tailf:cli-mode-name "config-sg-radius";
            key "name";
            leaf name {
              type string;
            }
            container server {
              description
                "Specify a RADIUS server";
              list name {
                description
                  "Name of radius server";
                tailf:cli-suppress-mode;
                key "name";
                leaf name {
                  type string;
                  tailf:non-strict-leafref {
                    path "/ios:native/aaa/group/server/radius/name";
                  }
                }
              }
              list direct {
                tailf:cli-drop-node-name;
                tailf:cli-compact-syntax;
                tailf:cli-suppress-mode;
                key "name";
                leaf name {
                  type inet:host;
                  tailf:cli-disallow-value "name";
                }
                leaf auth-port {
                  description
                    "UDP port for RADIUS authentication server (default is 1645)";
                  type uint16 {
                    range "0..65535";
                  }
                }
                leaf acct-port {
                  description
                    "UDP port for RADIUS accounting server (default is 1646)";
                  type uint16 {
                    range "0..65535";
                  }
                }
              }
            }
            container ip {
              description
                "Internet Protocol config commands";
              container radius {
                description
                  "RADIUS configuration commands";
                leaf source-interface {
                  type string;
                }
              }
              container vrf {
                description
                  "Set VPN Routing Forwarding to use with the servers";
                leaf forwarding {
                  description
                    "Configure forwarding table";
                  tailf:cli-diff-dependency "/ios:native/ip/vrf";
                  tailf:cli-diff-dependency "/ios:native/vrf/definition";
                  type string;
                }
              }
            }
            container load-balance {
              description
                "Server group load-balancing options.";
              container method {
                description
                  "Method by which the next host will be picked.";
                container least-outstanding {
                  description
                    "Pick the server with the least transactions outstanding.";
                  leaf batch-size {
                    description
                      "Size of the transaction batch that should be load-balanced.";
                    type uint32 {
                      range "1..2147483647";
                    }
                  }
                  leaf ignore-preferred-server {
                    description
                      "Should the preferred-server be ignored.";
                    tailf:cli-full-command;
                    type empty;
                  }
                }
              }
            }
            //  server-private Define a private RADIUS server (per group)
            //  subscriber Configures MAC Filtering RADIUS Compatibility mode
            //  throttle Throttle requests to radius server
          }
        }
      }
      // aaa authentication
      container authentication {
        description
          "Authentication configurations parameters.";
        tailf:cli-diff-dependency "/ios:native/aaa/new-model";
         //  arap             Set authentication lists for arap.
        //aaa authentication attempts
        container attempts {
          description
            "Set the maximum number of authentication attempts";
          leaf login {
            description
              "Set the max. number of attempts for login service";
            type uint8 {
              range "1..25";
            }
          }
        }
        //  banner           Message to use when starting login/authentication.

        // aaa authentication dot1x
        container dot1x {
          description
            "Set authentication lists for IEEE 802.1x.";
          list dot1x-list {
            tailf:cli-suppress-mode;
            tailf:cli-delete-when-empty;
            tailf:cli-compact-syntax;
            tailf:cli-drop-node-name;
            key "name";
            leaf name {
              type string;
            }
            uses aaa-authentication-dot1x-grouping;
          }
          container default {
            description
              "The default authentication list.";
            uses aaa-authentication-dot1x-grouping;
          }
        }
        // aaa authentication enable
        container enable {
          description
            "Set authentication list for enable.";
          container default {
            description
              "The default authentication list.";
            tailf:cli-compact-syntax;
            leaf group {
              description
                "Use Server-group";
              type union {
                type string;
                type enumeration {
                  enum "radius";
                  enum "tacacs+";
                }
              }
            }
            leaf enable {
              description
                "Use enable password for authentication.";
              type empty;
            }
            leaf line {
              description
                "Use line password for authentication.";
              type empty;
            }
            leaf none {
              description
                "No authentication.";
              tailf:cli-full-command;
              type empty;
            }
          }
        }
        // aaa authentication eou
        container eou {
            description "Set authentication lists for EAPoUDP";
            container default {
                description "The default authentication list";
                container group {
                    description "Use Server-group";
                    leaf radius {
                        description "Use list of all Radius hosts.";
                        type empty;
                    }
                }
            }
        }
        //  eou              Set authentication lists for EAPoUDP
        //  fail-message     Message to use for failed login/authentication.

        // aaa authentication login *
        list login {
          description
            "Set authentication lists for logins.";
          tailf:cli-suppress-mode;
          tailf:cli-delete-when-empty;
          tailf:cli-compact-syntax;
          key "name";
          leaf name {
            type union {
              type enumeration {
                enum "default";
              }
              type string {
                length "1..31";
              }
            }
          }
          container a1 {
            tailf:cli-drop-node-name;
            tailf:cli-flatten-container;
            tailf:cli-compact-syntax;
            choice auth-login-choice {
              leaf none {
                description
                  "NO authentication.";
                type empty;
              }
              leaf krb5 {
                description
                  "Use Kerberos 5 authentication.";
                type empty;
              }
              leaf krb5-telnet {
                description
                 "Allow logins only if already authenticated via Kerbero";
                type empty;
              }
              leaf line {
                description
                  "Use line password for authentication.";
                type empty;
              } 
              leaf enable {
                description
                  "Use enable password for authentication.";
                type empty;
              }        
              leaf local {
                description
                  "Use local username authentication.";
                type empty;
              }
              leaf local-case {
                description
                  "Use case-sensitive local username authentication.";
                type empty;
              }
              leaf group {
                description
                  "Use Server-group";
                type union {
                  type string;
                  type enumeration {
                    enum "ldap";
                    enum "radius";
                    enum "tacacs+";
                  }
                }
              }
              leaf cache {
                description
                  "Use Cached-group";
                type union {
                  type string;
                  type enumeration {
                    enum "ldap";
                    enum "radius";
                    enum "tacacs+";
                  }
                }
              }
            }
          }
          container a2 {
            when "not(../a1/none)" {
              tailf:dependency "../a1/none";
            }
            tailf:cli-drop-node-name;
            tailf:cli-flatten-container;
            tailf:cli-compact-syntax;
            choice auth-login-choice {
              leaf group {
                description
                  "Use Server-group";
                type union {
                  type string;
                  type enumeration {
                    enum "ldap";
                    enum "radius";
                    enum "tacacs+";
                  }
                }
              }
              leaf cache {
                description
                  "Use Cached-group";
                type union {
                  type string;
                  type enumeration {
                    enum "ldap";
                    enum "radius";
                    enum "tacacs+";
                  }
                }
              }
              leaf none {
                description
                  "NO authentication.";
                type empty;
              }
              leaf krb5 {
                when "not(../../a1/krb5) and not(../../a1/krb5-telnet)" {
                  tailf:dependency "../../a1/krb5";
                  tailf:dependency "../../a1/krb5-telnet";
                }
                type empty;
              }
              leaf krb5-telnet {
                when "not(../../a1/krb5) and not(../../a1/krb5-telnet)" {
                  tailf:dependency "../../a1/krb5";
                  tailf:dependency "../../a1/krb5-telnet";
                }
              type empty;
              }
              leaf line {
                description
                  "Use line password for authentication.";
                type empty;
              } 
              leaf enable {
                description
                  "Use enable password for authentication.";
                type empty;
              }        
              leaf local {
                when "not(../../a1/local) and not(../../a1/local-case)" {
                  tailf:dependency "../../a1/local";
                  tailf:dependency "../../a1/local-case";
                }
                type empty;
              }
              leaf local-case {
                when "not(../../a1/local) and not(../../a1/local-case)" {
                  tailf:dependency "../../a1/local";
                  tailf:dependency "../../a1/local-case";
                }
                type empty;
              }
            }
          }
          container a3 {
            when "not(../a2/none) and not (../a1/none)" {
              tailf:dependency "../a1/none";
              tailf:dependency "../a2/none";
            }
            tailf:cli-drop-node-name;
            tailf:cli-flatten-container;
            tailf:cli-compact-syntax;
            choice auth-login-choice {
              leaf group {
                description
                  "Use Server-group";
                type union {
                  type string;
                  type enumeration {
                    enum "ldap";
                    enum "radius";
                    enum "tacacs+";
                  }
                }
              }
              leaf cache {
                description
                  "Use Cached-group";
                type union {
                  type string;
                  type enumeration {
                    enum "ldap";
                    enum "radius";
                    enum "tacacs+";
                  }
                }
              }
              leaf none {
                description
                  "NO authentication.";
                type empty;
              }
              leaf krb5 {
                when "not(../../a1/krb5) and not(../../a1/krb5-telnet) and not(../../a2/krb5) and not(../../a2/krb5-telnet)" {
                  tailf:dependency "../../a1/krb5";
                  tailf:dependency "../../a1/krb5-telnet";
                  tailf:dependency "../../a2/krb5";
                  tailf:dependency "../../a2/krb5-telnet";
                }
                type empty;
              }
              leaf krb5-telnet {
                when "not(../../a1/krb5) and not(../../a1/krb5-telnet) and not(../../a2/krb5) and not(../../a2/krb5-telnet)" {
                  tailf:dependency "../../a1/krb5";
                  tailf:dependency "../../a1/krb5-telnet";
                  tailf:dependency "../../a2/krb5";
                  tailf:dependency "../../a2/krb5-telnet";
                }
                type empty;
              }
              leaf line {
                description
                  "Use line password for authentication.";
                type empty;
              } 
              leaf enable {
                description
                  "Use enable password for authentication.";
                type empty;
              }  
              leaf local {
                when "not(../../a1/local) and not(../../a1/local-case) and not(../../a2/local) and not(../../a2/local-case)" {
                  tailf:dependency "../../a1/local";
                  tailf:dependency "../../a1/local-case";
                  tailf:dependency "../../a2/local";
                  tailf:dependency "../../a2/local-case";
                }
                type empty;
              }
              leaf local-case {
                when "not(../../a1/local) and not(../../a1/local-case) and not(../../a2/local) and not(../../a2/local-case)" {
                  tailf:dependency "../../a1/local";
                  tailf:dependency "../../a1/local-case";
                  tailf:dependency "../../a2/local";
                  tailf:dependency "../../a2/local-case";
                }
                type empty;
              }
            }
          }
          container a4 {
            when "not(../a2/none) and not(../a1/none) and not(../a3/none)" {
              tailf:dependency "../a1/none";
              tailf:dependency "../a2/none";
              tailf:dependency "../a3/none";
            }
            tailf:cli-drop-node-name;
            tailf:cli-flatten-container;
            tailf:cli-compact-syntax;
            choice auth-login-choice {
              leaf group {
                description
                  "Use Server-group";
                type union {
                  type string;
                  type enumeration {
                    enum "ldap";
                    enum "radius";
                    enum "tacacs+";
                  }
                }
              }
              leaf cache {
                description
                  "Use Cached-group";
                type union {
                  type string;
                  type enumeration {
                    enum "ldap";
                    enum "radius";
                    enum "tacacs+";
                  }
                }
              }
              leaf none {
                description
                  "NO authentication.";
                type empty;
              }
              leaf krb5 {
                when "not(../../a1/krb5) and not(../../a1/krb5-telnet) and not(../../a2/krb5) and not(../../a2/krb5-telnet) and not(../../a3/krb5) and not(../../a3/krb5-telnet)" {
                  tailf:dependency "../../a1/krb5";
                  tailf:dependency "../../a1/krb5-telnet";
                  tailf:dependency "../../a2/krb5";
                  tailf:dependency "../../a2/krb5-telnet";
                  tailf:dependency "../../a3/krb5";
                  tailf:dependency "../../a3/krb5-telnet";
                }
                type empty;
              }
              leaf krb5-telnet {
                when "not(../../a1/krb5) and not(../../a1/krb5-telnet) and not(../../a2/krb5) and not(../../a2/krb5-telnet) and not(../../a3/krb5) and not(../../a3/krb5-telnet)" {
                  tailf:dependency "../../a1/krb5";
                  tailf:dependency "../../a1/krb5-telnet";
                  tailf:dependency "../../a2/krb5";
                  tailf:dependency "../../a2/krb5-telnet";
                  tailf:dependency "../../a3/krb5";
                  tailf:dependency "../../a3/krb5-telnet";
                }
                type empty;
              }
              leaf line {
                description
                  "Use line password for authentication.";
                type empty;
              } 
              leaf enable {
                description
                  "Use enable password for authentication.";
                type empty;
              }  

              leaf local {
                when "not(../../a1/local) and not(../../a1/local-case) and not(../../a2/local) and not(../../a2/local-case) and not(../../a3/local) and not(../../a3/local-case)" {
                  tailf:dependency "../../a1/local";
                  tailf:dependency "../../a1/local-case";
                  tailf:dependency "../../a2/local";
                  tailf:dependency "../../a2/local-case";
                  tailf:dependency "../../a3/local";
                  tailf:dependency "../../a3/local-case";
                }
                type empty;
              }
              leaf local-case {
                when "not(../../a1/local) and not(../../a1/local-case) and not(../../a2/local) and not(../../a2/local-case) and not(../../a3/local) and not(../../a3/local-case)" {
                  tailf:dependency "../../a1/local";
                  tailf:dependency "../../a1/local-case";
                  tailf:dependency "../../a2/local";
                  tailf:dependency "../../a2/local-case";
                  tailf:dependency "../../a3/local";
                  tailf:dependency "../../a3/local-case";
                }
                type empty;
              }
            }
          }
        }
        // aaa authentication ppp *
        list ppp {
          description
            "Set authentication lists for ppp.";
          tailf:cli-suppress-mode;
          tailf:cli-delete-when-empty;
          tailf:cli-compact-syntax;
          tailf:cli-sequence-commands {
            tailf:cli-reset-all-siblings;
          }
          key "id";
          leaf id {
            type string {
              length "1..31";
            }
          }
          container a1 {
            tailf:cli-drop-node-name;
            tailf:cli-flatten-container;
            tailf:cli-compact-syntax;
            choice auth-choice {
              leaf if-needed {
                description
                  "Only authenticate if needed.";
                tailf:cli-optional-in-sequence;
                type empty;
              }
              leaf none {
                description
                  "NO authentication.";
                type empty;
              }
              leaf krb5 {
                description
                  "Use Kerberos 5 authentication.";
                type empty;
              }
              leaf local {
                description
                  "Use local username authentication.";
                type empty;
              }
              leaf local-case {
                description
                  "Use case-sensitive local username authentication.";
                type empty;
              }
              leaf group {
                description
                  "Use Server-group";
                type union {
                  type string;
                  type enumeration {
                    enum "radius";
                    enum "tacacs+";
                  }
                }
              }
              leaf cache {
                description
                  "Use Cached-group";
                type union {
                  type string;
                  type enumeration {
                    enum "radius";
                    enum "tacacs+";
                  }
                }
              }
            }
          }
          container a2 {
            when "not(../a1/none)" {
              tailf:dependency "../a1/none";
            }
            tailf:cli-drop-node-name;
            tailf:cli-flatten-container;
            tailf:cli-compact-syntax;
            choice auth-choice {
              leaf group {
                description
                  "Use Server-group";
                type union {
                  type string;
                  type enumeration {
                    enum "radius";
                    enum "tacacs+";
                  }
                }
              }
              leaf cache {
                description
                  "Use Cached-group";
                type union {
                  type string;
                  type enumeration {
                    enum "radius";
                    enum "tacacs+";
                  }
                }
              }
              leaf none {
                description
                  "NO authentication.";
                type empty;
              }
              leaf krb5 {
                when "not(../../a1/krb5)" {
                  tailf:dependency "../../a1/krb5";
                }
                type empty;
              }
              leaf local {
                when "not(../../a1/local) and not(../../a1/local-case)" {
                  tailf:dependency "../../a1/local";
                  tailf:dependency "../../a1/local-case";
                }
                type empty;
              }
              leaf local-case {
                when "not(../../a1/local) and not(../../a1/local-case)" {
                  tailf:dependency "../../a1/local";
                  tailf:dependency "../../a1/local-case";
                }
                type empty;
              }
            }
          }
          container a3 {
            when "not(../a2/none) and not (../a1/none)" {
              tailf:dependency "../a1/none";
              tailf:dependency "../a2/none";
            }
            tailf:cli-drop-node-name;
            tailf:cli-flatten-container;
            tailf:cli-compact-syntax;
            choice auth-choice {
              leaf group {
                description
                  "Use Server-group";
                type union {
                  type string;
                  type enumeration {
                    enum "radius";
                    enum "tacacs+";
                  }
                }
              }
              leaf cache {
                description
                  "Use Cached-group";
                type union {
                  type string;
                  type enumeration {
                    enum "radius";
                    enum "tacacs+";
                  }
                }
              }
              leaf none {
                description
                  "NO authentication.";
                type empty;
              }
              leaf krb5 {
                when "not(../../a1/krb5) and not(../../a2/krb5)" {
                  tailf:dependency "../../a1/krb5";
                  tailf:dependency "../../a2/krb5";
                }
                type empty;
              }
              leaf local {
                when "not(../../a1/local) and not(../../a1/local-case) and not(../../a2/local) and not(../../a2/local-case)" {
                  tailf:dependency "../../a1/local";
                  tailf:dependency "../../a1/local-case";
                  tailf:dependency "../../a2/local";
                  tailf:dependency "../../a2/local-case";
                }
                type empty;
              }
              leaf local-case {
                when "not(../../a1/local) and not(../../a1/local-case) and not(../../a2/local) and not(../../a2/local-case)" {
                  tailf:dependency "../../a1/local";
                  tailf:dependency "../../a1/local-case";
                  tailf:dependency "../../a2/local";
                  tailf:dependency "../../a2/local-case";
                }
                type empty;
              }
            }
          }
          container a4 {
            when "not(../a2/none) and not(../a1/none) and not(../a3/none)" {
              tailf:dependency "../a1/none";
              tailf:dependency "../a2/none";
              tailf:dependency "../a3/none";
            }
            tailf:cli-drop-node-name;
            tailf:cli-flatten-container;
            tailf:cli-compact-syntax;
            choice auth-choice {
              leaf group {
                description
                  "Use Server-group";
                type union {
                  type string;
                  type enumeration {
                    enum "radius";
                    enum "tacacs+";
                  }
                }
              }
              leaf cache {
                description
                  "Use Cached-group";
                type union {
                  type string;
                  type enumeration {
                    enum "radius";
                    enum "tacacs+";
                  }
                }
              }
              leaf none {
                description
                  "NO authentication.";
                type empty;
              }
              leaf krb5 {
                when "not(../../a1/krb5) and not(../../a2/krb5) and not(../../a3/krb5)" {
                  tailf:dependency "../../a1/krb5";
                  tailf:dependency "../../a2/krb5";
                  tailf:dependency "../../a3/krb5";
                }
                type empty;
              }
              leaf local {
                when "not(../../a1/local) and not(../../a1/local-case) and not(../../a2/local) and not(../../a2/local-case) and not(../../a3/local) and not(../../a3/local-case)" {
                  tailf:dependency "../../a1/local";
                  tailf:dependency "../../a1/local-case";
                  tailf:dependency "../../a2/local";
                  tailf:dependency "../../a2/local-case";
                  tailf:dependency "../../a3/local";
                  tailf:dependency "../../a3/local-case";
                }
                type empty;
              }
              leaf local-case {
                when "not(../../a1/local) and not(../../a1/local-case) and not(../../a2/local) and not(../../a2/local-case) and not(../../a3/local) and not(../../a3/local-case)" {
                  tailf:dependency "../../a1/local";
                  tailf:dependency "../../a1/local-case";
                  tailf:dependency "../../a2/local";
                  tailf:dependency "../../a2/local-case";
                  tailf:dependency "../../a3/local";
                  tailf:dependency "../../a3/local-case";
                }
                type empty;
              }
            }
          }
        }
      }
      // aaa authorization
      container authorization {
        description
          "Authorization configurations parameters.";
        tailf:cli-incomplete-command;
        tailf:cli-diff-dependency "/ios:native/aaa/new-model";
        container auth-type {
            description "For Authentication Proxy Services";
            container default {
                description "The default authorization list.";
                leaf group {
                    description "Use server-group.";
                    type enumeration {
                        enum "radius";
                    }
                }
            }
        }
        list commands {
          description
            "For exec (shell) commands.";
          tailf:cli-suppress-mode;
          tailf:cli-delete-when-empty;
          tailf:cli-compact-syntax;
          tailf:cli-incomplete-command;
          key "level list-name";
          leaf level {
            description
              "Enable level";
            type uint8 {
              range "0..15";
            }
          }
          leaf list-name {
            tailf:cli-incomplete-command;
            tailf:cli-disallow-value "group";
            type union {
              type enumeration {
                enum "default";
              }
              type string;
            }
          }
          leaf group {
            description
              "Use server-group.";
            tailf:cli-disallow-value "if-authenticated|local|none";
            type union {
              type enumeration {
                enum "tacacs+";
              }
              type string;
            }
          }
          leaf if-authenticated {
            description
              "Succeed if user has authenticated.";
            type empty;
          }
          leaf local {
            description
              "Use local database.";
            type empty;
          }
          leaf none {
            description
              "No authorization (always succeeds).";
            type empty;
          }
        }
        leaf console {
          type empty;
        }
        leaf config-commands {
          description
            "For configuration mode commands.";
          type empty;
        }
        //  configuration For downloading configurations from AAA server
        //  console For enabling console authorization
        //  credential-download  For downloading EAP credential
        //                       from Local/RADIUS/LDAP

        // aaa authorization exec *
        list exec {
          description
            "For starting an exec (shell).";
          tailf:cli-suppress-mode;
          tailf:cli-delete-when-empty;
          tailf:cli-compact-syntax;
          key "name";
          leaf name {
            type string;
          }
	  container a1 {
	    tailf:cli-drop-node-name;
	    tailf:cli-flatten-container;
	    tailf:cli-compact-syntax;
	    choice auth-exec-choice {
	      leaf if-authenticated {
		description
		  "Succeed if user has authenticated.";
		type empty;
	      }
	      leaf none {
		description
		  "No authorization (always succeeds)";
		type empty;
	      }
	      leaf krb5-instance {
		description
		  "Use Kerberos instance privilege maps";
		type empty;
	      }
	      leaf local {
		description
		  "Use local database";
		type empty;
	      }
	      leaf group {
		description
		  "Use Server-group";
		type union {
		  type string;
		  type enumeration {
			enum "ldap";
			enum "radius";
			enum "tacacs+";
		  }
		}
	     }
	     leaf cache {
		description
		  "Use Cached-group";
		type union {
		  type string;
		  type enumeration {
			enum "ldap";
			enum "radius";
			enum "tacacs+";
	  	  }
		}
	      }
	    }
	  }
	  container a2 {
	    when "not(../a1/none) and not(../a1/if-authenticated)" {
	      tailf:dependency "../a1/none";
	      tailf:dependency "../a1/if-authenticated";
	    }
	    tailf:cli-drop-node-name;
	    tailf:cli-flatten-container;
	    tailf:cli-compact-syntax;
	    choice auth-exec-choice {
	      leaf group {
		description
		  "Use Server-group";
		type union {
		  type string;
		  type enumeration {
			enum "ldap";
			enum "radius";
			enum "tacacs+";
		  }
		}
	      }
	      leaf cache {
		description
		  "Use Cached-group";
		type union {
		  type string;
		  type enumeration {
			enum "ldap";
			enum "radius";
			enum "tacacs+";
		  }
		}
	      }
              leaf if-authenticated {
		description
		  "Succeed if user has authenticated.";
		type empty;
	      }
	      leaf none {
		description
		  "No authorization (always succeeds).";
		type empty;
	      }
	      leaf krb5-instance {
		when "not (../../a1/krb5-instance)" {
		  tailf:dependency "../../a1/krb5-instance";
		}  
		type empty;
	      }
	      leaf local {
		when "not(../../a1/local)" {
		  tailf:dependency "../../a1/local";
		}
		type empty;
	      }
	    }
	  }
	  container a3 {
	    when "not(../a2/none) and not (../a1/none) and not(../a2/if-authenticated) and not(../a1/if-authenticated)" {
	      tailf:dependency "../a1/none";
	      tailf:dependency "../a2/none";
	      tailf:dependency "../a1/if-authenticated";
	      tailf:dependency "../a2/if-authenticated";
	    }
	    tailf:cli-drop-node-name;
	    tailf:cli-flatten-container;
	    tailf:cli-compact-syntax;
	    choice auth-exec-choice {
	      leaf group {
		description
		  "Use Server-group";
		type union {
		  type string;
		  type enumeration {
			enum "ldap";
			enum "radius";
			enum "tacacs+";
		  }
		}
	      }
	      leaf cache {
		description
		  "Use Cached-group";
		type union {
		  type string;
		  type enumeration {
			enum "ldap";
			enum "radius";
			enum "tacacs+";
		  }
		}
	      }
	      leaf none {
		description
		  "No authorization (always succeeds).";
		type empty;
	      }
	      leaf if-authenticated {
		description
		  "Succeed if user has authenticated.";
		type empty;
	      }
	      leaf krb5-instance {
		when "not (../../a1/krb5-instance) and not (../../a2/krb5-instance)" {
		  tailf:dependency "../../a1/krb5-instance";
		  tailf:dependency "../../a2/krb5-instance";
		}  
		type empty;
	      }
	      leaf local {
		when "not(../../a1/local) and not(../../a2/local)" {
		  tailf:dependency "../../a1/local";
		  tailf:dependency "../../a2/local";
		}
		type empty;
	      }
	    }
	  }
	  container a4 {
	    when "not(../a2/none) and not(../a1/none) and not(../a3/none) and not(../a2/if-authenticated) and not(../a1/if-authenticated) and not(../a3/if-authenticated)" {
	      tailf:dependency "../a1/none";
	      tailf:dependency "../a2/none";
	      tailf:dependency "../a3/none";
	      tailf:dependency "../a1/if-authenticated";
	      tailf:dependency "../a2/if-authenticated";
	      tailf:dependency "../a3/if-authenticated";
	    }
	    tailf:cli-drop-node-name;
	    tailf:cli-flatten-container;
	    tailf:cli-compact-syntax;
	    choice auth-exec-choice {
	      leaf group {
		description
		  "Use Server-group";
		type union {
		  type string;
		  type enumeration {
			enum "ldap";
			enum "radius";
			enum "tacacs+";
		  }
		}
	      }
	      leaf cache {
		description
		  "Use Cached-group";
		type union {
		  type string;
		  type enumeration {
			enum "ldap";
			enum "radius";
			enum "tacacs+";
		  }
		}
	      }
	      leaf none {
		description
		  "No authorization (always succeeds).";
		type empty;
	      }
	      leaf if-authenticated {
		description
		  "Succeed if user has authenticated.";
		type empty;
	      }
	      leaf krb5-instance {
		when "not (../../a1/krb5-instance) and not (../../a2/krb5-instance) and not (../../a3/krb5-instance)" {
		  tailf:dependency "../../a1/krb5-instance";
		  tailf:dependency "../../a2/krb5-instance";
		  tailf:dependency "../../a3/krb5-instance";
		}  
		type empty;
	      }
	      leaf local {
		when "not(../../a1/local) and not(../../a2/local) and not(../../a3/local)" {
		  tailf:dependency "../../a1/local";
		  tailf:dependency "../../a2/local";
		  tailf:dependency "../../a3/local";
		}
		type empty;
	      }
	    }
	  }
	}
        // aaa authorization eventmanager *
        list eventmanager {
          description
            "For starting an exec (shell).";
          tailf:cli-suppress-mode;
          tailf:cli-delete-when-empty;
          tailf:cli-compact-syntax;
          key "name";
          leaf name {
            type string;
          }
          leaf group {
            description
              "Use server-group.";
            type union {
              type string;
              type enumeration {
                enum "ldap";
                enum "radius";
                enum "tacacs";
              }
            }
          }
          leaf local {
            description
              "Use local database.";
            type empty;
          }
          leaf none {
            description
              "No authorization (always succeeds).";
            type empty;
          }
        }
        // aaa authorization network *
        list network {
          description
            "For network services. (PPP, SLIP, ARAP)";
          tailf:cli-suppress-mode;
          key "id";
          leaf id {
            type union {
              type enumeration {
                enum "default";
              }
              type string {
                length "1..31";
              }
            }
          }
          container a1 {
            tailf:cli-drop-node-name;
            tailf:cli-flatten-container;
            tailf:cli-compact-syntax;
            choice auth-choice {
              leaf if-authenticated {
                description
                  "Succeed if user has authenticated.";
                type empty;
              }
              leaf none {
                description
                  "NO authentication.";
                type empty;
              }
              leaf local {
                description
                  "Use local username authentication.";
                type empty;
              }
              leaf group {
                description
                  "Use Server-group";
                type union {
                  type string;
                  type enumeration {
                    enum "radius";
                    enum "tacacs+";
                  }
                }
              }
              leaf cache {
                description
                  "Use Cached-group";
                type union {
                  type string;
                  type enumeration {
                    enum "radius";
                    enum "tacacs+";
                  }
                }
              }
            }
          }
          container a2 {
            when "not(../a1/none) and not(../a1/if-authenticated)" {
              tailf:dependency "../a1/none";
              tailf:dependency "../a1/if-authenticated";
            }
            tailf:cli-drop-node-name;
            tailf:cli-flatten-container;
            tailf:cli-compact-syntax;
            choice auth-choice {
              leaf group {
                description
                  "Use Server-group";
                type union {
                  type string;
                  type enumeration {
                    enum "radius";
                    enum "tacacs+";
                  }
                }
              }
              leaf cache {
                description
                  "Use Cached-group";
                type union {
                  type string;
                  type enumeration {
                    enum "radius";
                    enum "tacacs+";
                  }
                }
              }
              leaf if-authenticated {
                description
                  "Succeed if user has authenticated.";
                type empty;
              }
              leaf none {
                description
                  "NO authentication.";
                type empty;
              }
              leaf local {
                when "not(../../a1/local)" {
                  tailf:dependency "../../a1/local";
                }
                type empty;
              }
            }
          }
          container a3 {
            when "not(../a2/none) and not (../a1/none) and not(../a2/if-authenticated) and not(../a1/if-authenticated)" {
              tailf:dependency "../a1/none";
              tailf:dependency "../a2/none";
              tailf:dependency "../a1/if-authenticated";
              tailf:dependency "../a2/if-authenticated";
            }
            tailf:cli-drop-node-name;
            tailf:cli-flatten-container;
            tailf:cli-compact-syntax;
            choice auth-choice {
              leaf group {
                description
                  "Use Server-group";
                type union {
                  type string;
                  type enumeration {
                    enum "radius";
                    enum "tacacs+";
                  }
                }
              }
              leaf cache {
                description
                  "Use Cached-group";
                type union {
                  type string;
                  type enumeration {
                    enum "radius";
                    enum "tacacs+";
                  }
                }
              }
              leaf none {
                description
                  "NO authentication.";
                type empty;
              }
              leaf if-authenticated {
                description
                  "Succeed if user has authenticated.";
                type empty;
              }
              leaf local {
                when "not(../../a1/local) and not(../../a2/local)" {
                  tailf:dependency "../../a1/local";
                  tailf:dependency "../../a2/local";
                }
                type empty;
              }
            }
          }
          container a4 {
            when "not(../a2/none) and not(../a1/none) and not(../a3/none) and not(../a2/if-authenticated) and not(../a1/if-authenticated) and not(../a3/if-authenticated)" {
              tailf:dependency "../a1/none";
              tailf:dependency "../a2/none";
              tailf:dependency "../a3/none";
              tailf:dependency "../a1/if-authenticated";
              tailf:dependency "../a2/if-authenticated";
              tailf:dependency "../a3/if-authenticated";
            }
            tailf:cli-drop-node-name;
            tailf:cli-flatten-container;
            tailf:cli-compact-syntax;
            choice auth-choice {
              leaf group {
                description
                  "Use Server-group";
                type union {
                  type string;
                  type enumeration {
                    enum "radius";
                    enum "tacacs+";
                  }
                }
              }
              leaf cache {
                description
                  "Use Cached-group";
                type union {
                  type string;
                  type enumeration {
                    enum "radius";
                    enum "tacacs+";
                  }
                }
              }
              leaf none {
                description
                  "NO authentication.";
                type empty;
              }
              leaf if-authenticated {
                description
                  "Succeed if user has authenticated.";
                type empty;
              }
              leaf local {
                when "not(../../a1/local) and not(../../a2/local) and not(../../a3/local)" {
                  tailf:dependency "../../a1/local";
                  tailf:dependency "../../a2/local";
                  tailf:dependency "../../a3/local";
                }
                type empty;
              }
            }
          }
        }
        // aaa authorization auth-proxy
        container auth-proxy {
            description "For Authentication Proxy Services";
            container default {
                description "The default authorization list.";
                container group {
                    description "Use server-group.";
                    leaf radius {
                        description "Use list of all Radius hosts.";
                        type empty;
                    }
                    leaf group-name {
                      tailf:cli-drop-node-name;
                      type string;
                    }
                }
            }
        }
      }
      // aaa accounting
      container accounting {
        description
          "Accounting configurations parameters.";
        tailf:cli-incomplete-command;
        tailf:cli-diff-dependency "/ios:native/aaa/new-model";
        list commands {
          description
            "For exec (shell) commands.";
          tailf:cli-compact-syntax;
          tailf:cli-incomplete-command;
          tailf:cli-sequence-commands;
          tailf:cli-suppress-mode;
          tailf:cli-delete-when-empty;
          key "level list-name";
          leaf level {
            description
              "Enable level";
            type uint8 {
              range "0..15";
            }
          }
          leaf list-name {
            type union {
              type enumeration {
                enum "default";
              }
              type string {
                length "1..31";
              }
            }
          }
          leaf action-type {
            tailf:cli-drop-node-name;
            tailf:cli-incomplete-command;
            type enumeration {
              enum "none";
              enum "start-stop";
              enum "stop-only";
            }
          }
          leaf broadcast {
            description
              "Use Broadcast for Accounting";
            tailf:cli-optional-in-sequence;
            tailf:cli-incomplete-command;
            type empty;
          }
          leaf group {
            description
              "Use Server-group";
            tailf:cli-full-command;
            type union {
              type string;
              type enumeration {
                enum "tacacs+";
              }
            }
          }
        }
        container delay-start {
          description "Delay PPP Network start record until peer IP address is known.";
          leaf extended-delay {
            description "";
            type uint8 {
              range "1..2";
            }
          }
          leaf all {
            description 
              "Delay start records for all vrf and non-vrf users.";
            type empty;
          }
        }
        list dot1x {
          description
            "For dot1x sessions.";
          tailf:cli-suppress-mode;
          tailf:cli-sequence-commands;
          tailf:cli-compact-syntax;
          key "name";
          leaf name {
            type string;
          }
          container start-stop {
            description
              "Record start and stop without waiting";
            tailf:cli-compact-syntax;
            tailf:cli-sequence-commands;
            tailf:cli-reset-container;
            leaf broadcast {
              description
                "Use Broadcast for Accounting";
              tailf:cli-optional-in-sequence;
              type empty;
            }
            leaf group {
              description
                "Use Server-group";
              type union {
                type string;
                type enumeration {
                  enum "radius";
                  enum "tacacs+";
                }
              }
            }
          }
        }
        list exec {
          description
            "For starting an exec (shell).";
          tailf:cli-incomplete-command;
          tailf:cli-suppress-mode;
          key "name";
          leaf name {
            type string;
          }
          uses aaa-accounting-grouping;
        }
        container exec-submode {
          tailf:cli-drop-node-name;
          list exec {
            description
              "For starting an exec (shell).";
            tailf:cli-mode-name "cfg-acct-mlist";
            key "name";
            leaf name {
              type string;
            }
            container action-type {
              description
                "Type of action to be performed on accounting records";
              uses aaa-accounting-grouping;
            }
          }
        }
        list network {
          description
            "For network services. (PPP, SLIP, ARAP)";
          tailf:cli-suppress-mode;
          tailf:cli-compact-syntax;
          tailf:cli-sequence-commands {
            tailf:cli-reset-siblings;
          }
          key "id";
          leaf id {
            type union {
              type enumeration {
                enum "default";
              }
              type string {
                length "1..31";
              }
            }
          }
          container start-stop {
            description
              "Record start and stop without waiting";
            tailf:cli-compact-syntax;
            tailf:cli-sequence-commands;
            tailf:cli-reset-container;
            
            leaf group {
              description
                "Use Server-group";
              type union {
                type string;
                type enumeration {
                  enum "radius";
                  
                }
              }
            }
          }
          choice network-choice {
            case a {
              leaf none {
                description
                  "No accounting.";
                type empty;
              }
            }
            case b {
              leaf mode {
                tailf:cli-drop-node-name;
                type enumeration {
                  enum "start-stop";
                  enum "stop-only";
                }
              }
              leaf broadcast {
                description
                  "Use Broadcast for Accounting";
                tailf:cli-optional-in-sequence;
                type empty;
              }
              container a1 {
                tailf:cli-compact-syntax;
                tailf:cli-drop-node-name;
                tailf:cli-flatten-container;
                leaf group {
                  description
                    "Use server-group.";
                  type union {
                    type string;
                    type enumeration {
                      enum "ldap";
                      enum "radius";
                      enum "tacacs";
                    }
                  }
                }
              }
              container a2 {
                tailf:cli-compact-syntax;
                tailf:cli-drop-node-name;
                tailf:cli-flatten-container;
                leaf group {
                  description
                    "Use server-group.";
                  type union {
                    type string;
                    type enumeration {
                      enum "ldap";
                      enum "radius";
                      enum "tacacs";
                    }
                  }
                }
              }
              container a3 {
                tailf:cli-compact-syntax;
                tailf:cli-drop-node-name;
                tailf:cli-flatten-container;
                leaf group {
                  description
                    "Use server-group.";
                  type union {
                    type string;
                    type enumeration {
                      enum "ldap";
                      enum "radius";
                      enum "tacacs";
                    }
                  }
                }
              }
              container a4 {
                tailf:cli-compact-syntax;
                tailf:cli-drop-node-name;
                tailf:cli-flatten-container;
                leaf group {
                  description
                    "Use server-group.";
                  type union {
                    type string;
                    type enumeration {
                      enum "ldap";
                      enum "radius";
                      enum "tacacs";
                    }
                  }
                }
              }
            }
          }
        }
        container send {
          description
            "Send records to accounting server";
          container counters {
            description
              "Enable specific counters in the Stop record";
            leaf ipv6 {
              description
                "Send IPv6 counters in the Stop Record";
              type empty;
            }
          }
          container stop-record {
            description
              "Generate STOP records for a specified event";
            leaf always {
              description
                "Generate STOP records always, even if the START record is not sent";
              tailf:cli-full-command;
              type empty;
            }
            container authentication {
              description
                "Generate STOP records for authentication failures";
              container failure {
                description
                  "Generate STOP records for authentication failures";
                presence "true";
                leaf vrf {
                  description
                    "VPN Routing/Forwarding parameters";
                  type string;
                }
              }
              container success {
                description
                  "Generate STOP records for authenticated users";
                container remote-server {
                  description
                    "Successfully authenticated, through access-accept, by a remote AAA server";
                  presence "true";
                  leaf vrf {
                    description
                      "VPN Routing/Forwarding parameters";
                    type string;
                  }
                }
              }
            }
          }
        }
        container system {
          description
            "For system events.";
          choice default-guarantee-first {
            case default-case {
              container default {
                description
                  "The default accounting list.";
                tailf:cli-compact-syntax;
                presence "true";
                leaf none {
                  description
                    "No accounting.";
                  tailf:cli-full-command;
                  type empty;
                }
                container start-stop {
                  description
                    "Record start and stop without waiting";
                  tailf:cli-compact-syntax;
                  tailf:cli-sequence-commands;
                  tailf:cli-reset-container;
                  leaf broadcast {
                    description
                      "Use Broadcast for Accounting";
                    tailf:cli-optional-in-sequence;
                    type empty;
                  }
                  leaf group {
                    description
                      "Use Server-group";
                    type union {
                      type string;
                      type enumeration {
                        enum "radius";
                        enum "tacacs+";
                      }
                    }
                  }
                }
                leaf vrf {
                  description
                    "VPN Routing/Forwarding parameters";
                  type string;
                }
              }
            }
            case guarantee-first-case {
              leaf guarantee-first {
                description
                  "Guarantee system accounting as first record.";
                tailf:cli-boolean-no;
                tailf:cli-trim-default;
                type boolean;
              }
            }
          }
        }
         container update {
            description "Enable accounting update records";
            leaf periodic {
                description "Periodic intervals to send accounting update records(in minutes)";
                type uint32 {
                    range "1..71582";
                }
            }
        }
        container auth-proxy {
          description 
            "For Authentication Proxy Services";
          container default {
            description 
              "The default authorization list.";
            container start-stop {
              description 
                "Record start and stop without waiting";
              leaf group {
                description 
                  "Use server-group.";
                type string;
              }
            }
          }
        }
      }
      //aaa server
      container server {
        description
          "Local AAA server";
        tailf:cli-incomplete-command;
        tailf:cli-diff-dependency "/ios:native/aaa/new-model";
        container radius {
          description
            "Profile for local radius server";
          container dynamic-author {
            description
              "Local server profile for RFC 3576 support";
            tailf:cli-add-mode;
	    presence true;
            tailf:cli-mode-name "config-locsvr-da-radius";
            list client {
              description
                "Specify a RADIUS client";
              tailf:cli-suppress-mode;
              key ip;
              leaf ip {
                type union {
                  type inet:ipv4-address;
                  type inet:ipv6-address;
                  type string;
                }
              }
              list vrf {
                description
                  "Virtual Routing/Forwarding parameters";
                tailf:cli-suppress-mode;
                key name;
                leaf name {
                  type string;
                }
              }
              container server-key {
                description
                  "Specify a RADIUS client server-key";
                tailf:cli-flatten-container;
                tailf:cli-compact-syntax;
                leaf key {
                  tailf:cli-drop-node-name;
                  type enumeration {
                    enum "0";
                    enum "6";
                    enum "7";
                  }
                }
                leaf string {
                  tailf:cli-drop-node-name;
                  type string;
                }
              }
            }
            container server-key {
              description
                "Specify a RADIUS client server-key";
              tailf:cli-compact-syntax;
              leaf key {
                tailf:cli-drop-node-name;
                type enumeration {
                  enum "0";
                  enum "6";
                  enum "7";
                }
              }
              leaf string {
                tailf:cli-drop-node-name;
                type string;
              }
            }
            container domain {
              description
                "Username domain options";
              leaf delimiter {
                description
                  "Domain delimiter, Choose from {@, /, $, %, \, #, -}";
                type string;
              }
              container stripping {
                description
                  "Match incoming username left oriented of the @ domain delimiter";
                presence true;
                leaf right-to-left {
                  description
                    "Terminate the string at the first delimiter going from right to left";
                  type empty;
                }
              }
            }
            leaf auth-type {
              description
                "Specify the server authorization type";
              type enumeration {
                enum all;
                enum any;
                enum session-key;
              }
            }
          }
        }
      }
      // aaa session-id
      leaf session-id {
        description
          "AAA Session ID";
        tailf:cli-diff-dependency "/ios:native/aaa/new-model";
        type enumeration {
          enum "common";
          enum "unique";
        }
      }
    }
    
 
     /// ========================================================================
     /// ethernet
    /// ========================================================================
    container ethernet {
      description
        "Ethernet configuration";
      // ethernet evc
      list evc {
        description
          "define an Ethernet virtual connection (EVC)";
        tailf:cli-compact-syntax;
        tailf:cli-full-command;
        key "name";
        leaf name {
          type string {
            length "1..100";
          }
        }
      }
      // ethernet lmi
      container lmi {
        description
          "Local Management Interface";
        leaf ce {
          description
            "Ethernet LMI Customer Edge";
          tailf:cli-full-command;
          type empty;
        }
        leaf global {
          description
            "Ethernet LMI is enabled on all supported Interfaces";
          tailf:cli-full-command;
          type empty;
        }
      }
      // ethernet cfm
      container cfm {
        description
          "Connectivity Fault Management";
        container ais {
          description
            "AIS Maintenance Condition";
          container link-status {
            description
              "8023ah SMEP or link state up/down";
            container global {
              description
                "8023ah SMEP or link state state up/down AIS global configuration";
              tailf:cli-add-mode;
              tailf:cli-mode-name "config-ais-link-cfm";
              presence "true";
              container cfm-Mode__config-ais-link-cfm {
                tailf:cli-drop-node-name;
                leaf disable {
                  description
                    "Disable AIS transmission";
                  type empty;
                }
                leaf level {
                  description
                    "Maintenance Level";
                  type uint8 {
                    range "0..7";
                  }
                }
                container period {
                  description
                    "AIS Transmission period";
                  leaf tp-1 {
                    tailf:alt-name "1";
                    type empty;
                  }
                  leaf tp-60 {
                    tailf:alt-name "60";
                    description
                      "Seconds";
                    type empty;
                  }
                }
              }
            }
          }
        }
        container alarm {
          description
            "CFM Alarm";
          leaf delay {
            description
              "msec (default 2500 msec)";
            type uint16 {
              range "2500..10000";
            }
          }
          container notification {
            description
              "CFM alarm notification";
            leaf all {
              description
                "Report all defects: DefRDI, DefMACStatus, DefRemote, DefError, DefXcon";
              type empty;
            }
            leaf error-xcon {
              description
                "Report only: DefError and DefXcon";
              type empty;
            }
            leaf mac-remote-error-xcon {
              description
                "Report only: DefMACStatus, DefRemote, DefError and DefXcon (default)";
              type empty;
            }
            leaf none {
              description
                "No defects to be reported";
              type empty;
            }
            leaf remote-error-xcon {
              description
                "Report only: DefRemote, DefError and DefXcon";
              type empty;
            }
            leaf xcon {
              description
                "Report only: DefXcon";
              type empty;
            }
          }
          leaf packet {
            description
              "max DefError and DefXcon packets";
            type uint16 {
              range "1..65535";
            }
          }
          leaf reset {
            description
              "msec (default 10000 msec)";
            type uint16 {
              range "2500..10000";
            }
          }
        }
        leaf ieee {
          description
            "CFM IEEE enable";
          tailf:cli-full-command;
          type empty;
        }
        leaf global {
          description
            "CFM global enable";
          tailf:cli-full-command;
          type empty;
        }
        list domain {
          description
            "Configure a domain";
          tailf:cli-mode-name "config-ecfm";
          tailf:cli-compact-syntax;
          tailf:cli-incomplete-command;
          key "name";
          leaf name {
            type string;
          }
          leaf level {
            description
              "Maintenance Level";
            tailf:cli-hide-in-submode;
            type uint8;
          }
          list service {
            description
              "Maintenance Association within Domain";
            tailf:cli-mode-name "config-ecfm-srv";
            tailf:cli-compact-syntax;
            tailf:cli-sequence-commands;
            key "name";
            leaf name {
              type string;
            }
            leaf evc {
              description
                "Specify EVC";
              tailf:cli-hide-in-submode;
              type string;
              tailf:non-strict-leafref {
                path "/ios:native/ethernet/evc/name";
              }
            }
            leaf vlan {
              description
                "VLAN id";
              tailf:cli-break-sequence-commands;
              type uint16 {
                range "1..4094";
              }
            }
            container continuity-check {
              description
                "Enable Continuity Check for Maintenance Association";
              presence "true";
            }
          }
        }
        container logging {
          description
            "Enable CFM syslog messages";
          presence "true";
          leaf ais {
            description
              "AIS logging";
            type empty;
          }
          container alarm {
            description
              "Alarm logging";
            leaf cisco {
              description
                "Cisco MIB syslogs";
              type empty;
            }
            leaf ieee {
              description
                "IEEE MIB syslogs";
              type empty;
            }
          }
        }
        container mep {
          description
            "Maintenance End Point";
          container crosscheck {
            description
              "Cross Check remote MEPs";
            leaf start-delay {
              description
                "seconds (30 seconds default)";
              type uint16 {
                range "1..65535";
              }
            }
          }
        }
        container mip {
          description
            "CFM MIP commands";
          container auto-create {
            description
              "CFM MIP auto creation";
            container level {
              description
                "Maintenance Level";
              list mef-num {
                tailf:cli-drop-node-name;
                tailf:cli-suppress-mode;
                key "mef-num";
                leaf mef-num {
                  description
                    "maintenance level number";
                  type uint8 {
                    range "0..7";
                  }
                }
                leaf evc {
                  description
                    "EVC name";
                  type string;
                }
                leaf vlan {
                  description
                    "VLAN id";
                  type uint16 {
                    range "1..4094";
                  }
                }
              }
            }
          }
          leaf filter {
            description
              "CFM MIP filter";
            type empty;
          }
        }
        container traceroute {
          description
            "CFM Traceroute";
          container cache {
            description
              "CFM Traceroute Cache";
            presence "true";
            leaf hold-time {
              description
                "minutes (default 100)";
              type uint16 {
                range "1..65535";
              }
            }
            leaf size {
              description
                "Number of cached lines (default 100)";
              type uint16 {
                range "1..4095";
              }
            }
          }
        }
      }
      //ethernet ring g8032
      container ring {
        description
          "Ring";
        container g8032 {
          description
            "Specify the g.8032 ethernet ring";
          list rings {
            tailf:cli-drop-node-name;
            tailf:cli-mode-name "config-erp-ring";
            key "name";
            leaf name {
              description
                "Name of the ethernet ring";
              type string;
            }
            container ring-Mode-config-erp-ring {
              tailf:cli-drop-node-name;
              container exclusion-list {
                description
                  "Specifiy exclusion list not protected by ERP";
                leaf vlan-ids {
                  description
                    "List of VLAN IDs in the form a-b,c,d,e-f,g";
                  type string;
                }
              }
              list instance {
                description
                  "Configure the g.8032 ethernet ring instance";
                tailf:cli-mode-name "config-erp-inst";
                key "number";
                leaf number {
                  description
                    "Instance number";
                  type uint8 {
                    range "1..2";
                  }
                }
                container aps-channel {
                  description
                    "Configure g.8032 instance aps-channel";
                  tailf:cli-add-mode;
                  tailf:cli-mode-name "config-erp-inst-aps";
                  presence "true";
                  container aps-Mode-config-erp-inst-aps {
                    tailf:cli-drop-node-name;
                    leaf level {
                      description
                        "Specify the APS message level";
                      type uint8 {
                        range "0..7";
                      }
                    }
                    container port0 {
                      description
                        "Configure g.8032 aps-channel info associated to port0";
                      container service {
                        description
                          "Specify an Ethernet Service Instance";
                        leaf instance {
                          description
                            "Specify an Ethernet Service Instance";
                          type uint16 {
                            range "1..8184";
                          }
                        }
                      }
                    }
                    container port1 {
                      description
                        "Configure g.8032 aps-channel info associated to port1";
                      choice service-instance {
                        case none-case {
                          leaf none {
                            description
                              "Specify port1 APS channel as none";
                            type empty;
                          }
                        }
                        case service-instance-case {
                          container service {
                            description
                              "Specify an Ethernet Service Instance";
                            leaf instance {
                              description
                                "Specify an Ethernet Service Instance";
                              type uint16 {
                                range "1..8184";
                              }
                            }
                          }
                        }
                      }
                    }
                  }
                }
                leaf description {
                  description
                    "Description for the instance";
                  tailf:cli-multi-value;
                  type string;
                }
                container inclusion-list {
                  description
                    "Specify inclusion list protected by ERP";
                  leaf vlan-ids {
                    description
                      "Associates a set of VLAN IDs with the current instance";
                    type string;
                  }
                }
                leaf profile {
                  description
                    "Ethernet ring profile name";
                  type string;
                }
                container rpl {
                  description
                    "Specify RPL owner, neighbor or next-neighbor";
                  choice port {
                    case port0 {
                      leaf port0 {
                        description
                          "Assign port0 as RPL owner, neighbor or next-neighbor";
                        type enumeration {
                          enum "neighbor";
                          enum "next-neighbor";
                          enum "owner";
                        }
                      }
                    }
                    case port1 {
                      leaf port1 {
                        description
                          "Assign port1 as RPL owner, neighbor or next-neighbor";
                        type enumeration {
                          enum "neighbor";
                          enum "next-neighbor";
                          enum "owner";
                        }
                      }
                    }
                  }
                }
              }
              leaf open-ring {
                description
                  "Specify the g.8032 ring as open ring";
                type empty;
              }
              container port0 {
                description
                  "Port0 of the local node connected to G.8032 ring";
                container interface {
                  description
                    "Assign port interface";
                  tailf:cli-compact-syntax;
                  tailf:cli-flatten-container;
                  uses interface-grouping;
                }
              }
              container port1 {
                description
                  "Port1 of the local node connected to G.8032 ring";
                container interface {
                  description
                    "Assign port interface";
                  tailf:cli-compact-syntax;
                  tailf:cli-flatten-container;
                  uses interface-grouping;
                }
                leaf none {
                  description
                    "Assign port1 as none to enable g.8032 open-ring";
                  type empty;
                }
              }
            }
          }
          list profile {
            description
              "g.8032 ring profile configuration";
            tailf:cli-mode-name "config-erp-profile";
            key "pr-name";
            leaf pr-name {
              description
                "ERP profile name string";
              type string;
            }
            container pr-Mode__config-erp-profile {
              tailf:cli-drop-node-name;
              leaf non-revertive {
                description
                  "Non-revertive ring instance";
                type empty;
              }
              container timer {
                description
                  "g.8032 timer";
                leaf guard {
                  description
                    "milliseconds";
                  type uint16 {
                    range "10..2000";
                  }
                }
                leaf hold-off {
                  description
                    "seconds";
                  type uint8 {
                    range "0..10";
                  }
                }
                leaf wtr {
                  description
                    "minutes";
                  type uint8 {
                    range "1..12";
                  }
                }
              }
            }
          }
        }
      }
    }
    


    /// ========================================================================
    /// alarm-contact
    /// ========================================================================
    list alarm-contact {
      tailf:cli-suppress-mode;
      tailf:cli-delete-when-empty;
      key "name";
      leaf name {
        type uint8 {
          range "1..4";
        }
      }
      leaf description {
        tailf:cli-multi-value;
        type string {
          length "1..80";
        }
      }
      leaf severity {
        type enumeration {
          enum "critical";
          enum "major";
          enum "minor";
        }
      }
      leaf trigger {
        type enumeration {
          enum "open";
          enum "closed";
        }
      }
    }

    /// ========================================================================
    /// access-list
    /// ========================================================================
    container access-list {
      tailf:cli-incomplete-command;
      tailf:cli-compact-syntax;
      description
        "Add an access list entry";
      list access-list-standard-range {
        tailf:cli-drop-node-name;
        tailf:cli-suppress-mode;
        tailf:cli-delete-when-empty;
        tailf:cli-compact-syntax;
        tailf:cli-incomplete-command;
        key "listnumber";
        leaf listnumber {
          tailf:cli-drop-node-name;
          tailf:cli-incomplete-command;
          tailf:cli-incomplete-no;
          tailf:cli-suppress-range;
          type uint16 {
            range "1..99";
          }
        }
        list std-access-list-rule {
          tailf:cli-suppress-mode;
          tailf:cli-delete-when-empty;
          tailf:cli-drop-node-name;
          tailf:cli-compact-syntax;
          tailf:cli-show-long-obu-diffs;
          ordered-by user;
          key "rule";
          leaf rule {
            tailf:cli-drop-node-name;
            tailf:cli-multi-word-key;
            type string;
          }
        }
      }
      // acess-list *
      list access-list-extended-range {
        tailf:cli-drop-node-name;
        tailf:cli-suppress-mode;
        tailf:cli-delete-when-empty;
        tailf:cli-compact-syntax;
        tailf:cli-incomplete-command;
        key "listnumber";
        leaf listnumber {
          tailf:cli-drop-node-name;
          tailf:cli-incomplete-command;
          tailf:cli-incomplete-no;
          tailf:cli-suppress-range;
          type uint16 {
            range "100..199";
          }
        }
        list ext-access-list-rule {
          tailf:cli-suppress-mode;
          tailf:cli-delete-when-empty;
          tailf:cli-drop-node-name;
          tailf:cli-compact-syntax;
          tailf:cli-show-long-obu-diffs;
          ordered-by user;
          key "rule";
          leaf rule {
            tailf:cli-drop-node-name;
            tailf:cli-multi-word-key;
            type string;
          }
        }
      }
      container hardware {
        container capture {
          leaf mode {
            type enumeration {
              enum "vlan";
            }
          }
        }
      }
    }

    /// ========================================================================
    ///  Bridge-domain
    /// ========================================================================
    grouping config-bdomain-mode-grouping {
      container ip {
        description
          "IP related commands";
        container igmp {
          description
            "IP igmp commands";
          container snooping {
            description
              "IP igmp snooping commands";
            presence "true";
            container check {
              description
                "enforce TTL or Rtr-Alert Option checking";
              leaf rtr-alert-option {
                description
                  "Only accept IGMP packets with router-alert option";
                type empty;
              }
              leaf ttl {
                description
                  "Only accept IGMP packets with TTL=1";
                type empty;
              }
            }
            container explicit-tracking {
              description
                "IGMP explicit host tracking configuration";
              leaf limit {
                description
                  "Explicit Host Tracking DB limit";
                type empty;
              }
            }
            leaf immediate-leave {
              description
                "Enable IGMPv2 immediate leave processing";
              type empty;
            }
            leaf last-member-query-count {
              description
                "Last member query count";
              type uint8 {
                range "1..7";
              }
            }
            leaf last-member-query-interval {
              description
                "Last member query interval";
              type uint16 {
                range "100..32767";
              }
            }
            container mrouter {
              description
                "Configure an L2 port as a multicast router port";
              leaf interface {
                description
                  "next-hop interface to mrouter";
                type empty;
              }
            }
            container querier {
              description
                "Enable IGMP querier for this Bdomain";
              presence "true";
              leaf address {
                description
                  "IGMP querier source IP address";
                type empty;
              }
              leaf max-response-time {
                description
                  "IGMP querier maximum response time (sec)";
                type empty;
              }
              leaf query-interval {
                description
                  "IGMP querier query interval (sec)";
                type empty;
              }
              leaf tcn {
                description
                  "IGMP querier TCN related parameters";
                type empty;
              }
              leaf timer {
                description
                  "IGMP other querier timer";
                type empty;
              }
              leaf version {
                description
                  "IGMP version";
                type empty;
              }
            }
            leaf report-suppression {
              description
                "Enable IGMP report suppression";
              type empty;
            }
            leaf robustness-variable {
              type uint8 {
                range "1..3";
              }
            }
            leaf static {
              description
                "Configure an L2 port as a member of a group";
              type inet:ipv4-address;
            }
          }
        }
      }
      container mac {
        description
          "MAC Address related commands";
        leaf aging-time {
          description
            "Set age time of mac addresses per bridge domain";
          type uint16 {
            range "30..3600";
          }
        }
        leaf learning {
          description
            "Disable mac learning on bridge domain";
          type empty;
        }
        container limit {
          description
            "Limit the MAC Addresses learnt";
          container action {
            description
              "action when exceeding the limit";
            container flooding {
              description
                "Mac flooding";
              leaf disable {
                description
                  "disable";
                type empty;
              }
            }
          }
          container maximum {
            description
              "Maximum";
            leaf addresses {
              description
                "Addresses";
              type uint32 {
                range "1..65536";
              }
            }
          }
        }
      }
      container member {
        description
          "bridge-domain member";
        list mem-ipv4 {
          tailf:cli-drop-node-name;
          tailf:cli-suppress-mode;
          key "mem-ipv4";
          leaf mem-ipv4 {
            description
              "IP address of the peer";
            type inet:ipv4-address;
          }
          list mem-vcid {
            tailf:cli-drop-node-name;
            tailf:cli-suppress-mode;
            key "mem-vcid";
            leaf mem-vcid {
              description
                "<1..4294967295>;;Enter VC ID value";
              type uint32 {
                range "1..4294967295";
              }
            }
            container encapsulation {
              description
                "Data encapsulation method";
              presence "true";
              leaf mpls {
                description
                  "Use MPLS encapsulation";
                type empty;
              }
            }
            container template {
              description
                "Template to use for encapsulation and protocol configuration";
              presence "true";
              leaf template {
                description
                  "<WORD>;;template name (Max size 32)";
                tailf:cli-drop-node-name;
                type string;
              }
            }
          }
          container encapsulation {
            description
              "Data encapsulation method";
            leaf mpls {
              description
                "Use MPLS encapsulation";
              type empty;
            }
          }
          leaf template {
            description
              "Template to use for encapsulation and protocol configuration";
            type string;
          }
        }
        list ACR {
          tailf:cli-suppress-mode;
          key "acr-int";
          leaf acr-int {
            description
              "<WORD>;;Virtual ACR interface";
            type string;
          }
          container service-instance {
            description
              "ethernt serivce instance";
            list id {
              tailf:cli-drop-node-name;
              tailf:cli-suppress-mode;
              key "id";
              leaf id {
                description
                  "<1..8000>;;Service Instance Identifier";
                type uint16 {
                  range "1..8000";
                }
              }
              leaf split-horizon {
                description
                  "Configure this port as a member of a split horizon group";
                type empty;
              }
            }
          }
        }
        leaf Analysis-Module {
          description
            "Cisco network analysis service module";
          type uint8;
        }
        leaf Fcpa {
          description
            "Fiber Channel";
          type uint8;
        }
        leaf SBC {
          description
            "Session Border Controller";
          type uint32 {
            range "0..2147483647";
          }
        }
        leaf SONET_ACR {
          description
            "Virtual SONET-ACR controller";
          type uint8;
        }

        leaf _controller {
          tailf:cli-drop-node-name;
          type string;
        }

        leaf Service-Engine {
          description
            "Cisco service engine module";
          type uint8;
        }
        leaf Tunnel-tp {
          description
            "MPLS Transport Profile interface";
          type uint16 {
            range "0..65535";
          }
        }
        leaf VPN {
          description
            "VPN interface";
          type uint32 {
            range "0..2147483647";
          }
        }
        leaf Virtual-TokenRing {
          description
            "Virtual TokenRing";
          type uint32 {
            range "0..2147483647";
          }
        }
        leaf ucse {
          description
            "Cisco ucse server";
          type uint8;
        }
        leaf vasileft {
          description
            "VasiLeft interface";
          type uint16 {
            range "1..2000";
          }
        }
        leaf vasiright {
          description
            "VasiRight interface";
          type uint16 {
            range "1..2000";
          }
        }
        leaf vfi {
          description
            "Enter VFI name";
          type string;
        }
        leaf vni {
          type uint32 {
            range "4096..16777215";
          }
        }
        list member-interface {
          tailf:cli-drop-node-name;
          tailf:cli-suppress-mode;
          tailf:cli-sequence-commands;
          tailf:cli-compact-syntax;
          key "interface";
          leaf interface {
            type string;
          }
          leaf interface-id {
            tailf:cli-drop-node-name;
            tailf:cli-optional-in-sequence;
            type union {
              type string;
              type uint32;
            }
          }
          leaf service-instance {
            description
              "ethernt serivce instance";
            type uint32 {
              range "1..8000";
            }
          }
          container split-horizon {
            description
              "Configure this port as a member of a split horizon group";
            tailf:cli-flatten-container;
            tailf:cli-break-sequence-commands;
            leaf group {
              description
                "Split-horizon group";
              type uint8;
            }
          }
        }
      }
      leaf shutdown {
        description
          "Take the bridge domain admin down";
        type empty;
      }
    }
    container bridge-domain {
      description
        "Bridge-domain global configuration commands";
      list brd-id {
        tailf:cli-drop-node-name;
        tailf:cli-mode-name "config-bdomain";
        key "bridge-domain-id";
        leaf bridge-domain-id {
          description
            "<1..8192>;;bridge-domain ID";
          type uint16 {
            range "1..8192";
          }
        }
        uses config-bdomain-mode-grouping;
      }
      container c-mac {
        description
          "Configure c-mac global commands";
        leaf aging-time {
          description
            "Configure aging time for c-mac bridge domains";
          type uint16 {
            range "30..3600";
          }
        }
      }
      container otv {
        description
          "Configure overlay bridge domains";
        container default {
          description
            "Change default setting of overlay bridge domains";
          leaf age-time {
            description
              "Configure default mac aging time of overlay bridge domains";
            type uint16 {
              range "30..3600";
            }
          }
        }
      }
      container parameterized {
        description
          "bridge-domain is derived from parameters";
        container vlan {
          description
            "bridge-domain from service instance vlan";
          tailf:cli-add-mode;
          tailf:cli-mode-name "config-bdomain";
          presence "true";
          uses config-bdomain-mode-grouping;
        }
      }
    }

    /// ========================================================================
    /// crypto
    /// ========================================================================
    container crypto {
      description
        "Encryption module";
      // crypto call
      container call {
        description
          "Configure Crypto Call Admission Control";
        container admission {
          description
            "Configure Crypto Call Admission Control";
          container limit {
            description
              "Configure Crypto Call Admission Control limits";
            container all {
              description
                "onfigure Crypto Call Admission Control total in-negotiation SA limit";
              leaf in-negotiation-sa {
                description
                  "Maximum number of in-negotiation SAs allowed";
                type uint32 {
                  range "10..99999";
                }
              }
            }
            container ike {
              description
                "Configure Crypto Call Admission Control active IKE SA limit";
              leaf in-negotiation-sa {
                description
                  "Maximum number of in-negotiation IKE SAs allowed";
                type uint32 {
                  range "10..99999";
                }
              }
              leaf sa {
                description
                  "Maximum active IKE SAs allowed";
                type uint32 {
                  range "0..99999";
                }
              }
            }
            container ipsec {
              description
                "Configure Crypto Call Admission Control active IPSec SA limit";
              leaf sa {
                description
                  "Maximum active IPSec SAs allowed";
                type uint32 {
                  range "0..99999";
                }
              }
            }
          }
        }
      }
      // crypto dynamic-map
      list dynamic-map {
        description
          "Specify a dynamic crypto map template";
        tailf:cli-mode-name "config-crypto-map";
        key "name sequence";
        leaf name {
          type string;
        }
        leaf sequence {
          type uint16;
        }
        container default {
          description
            "Set a command to its defaults";
          uses crypto-dynamic-map-default-grouping;
        }
        uses crypto-dynamic-map-grouping;
      }
      // crypto engine
      container engine {
        description
          "Enter a crypto engine configurable menu";
        leaf software {
          description
            "Software crypto engine";
          type enumeration {
            enum "ipsec";
            enum "isakmp";
          }
        }
      }
      // crypto gdoi
      container gdoi {
        description
          "Configure GKM (Group Key Management, GDOI or G-IKEv2) Policy";
        list group {
          description
            "Configure a GKM (Group Key Management, GDOI or G-IKEv2) Group";
          tailf:cli-mode-name "config-gkm-group";
          key "name";
          leaf name {
            type string;
            tailf:cli-disallow-value "ipv6";
          }
          leaf ipv6 {
            description
              "IPv6 GKM (Group Key Management) Group";
            tailf:cli-prefix-key;
            type empty;
          }
          uses crypto-gdio-grouping;
          container default {
            description
              "Set a command to its defaults";
            uses crypto-gdio-default-grouping;
          }
        }
      }
      // crypto gkm
      container gkm {
        description
          "Configure GKM (Group Key Management, GDOI or G-IKEv2) Policy";
        list group {
          description
            "Configure a GKM (Group Key Management, GDOI or G-IKEv2) Group";
          tailf:cli-mode-name "config-gkm-group";
          key "name";
          leaf name {
            type string;
            tailf:cli-disallow-value "ipv6";
          }
          leaf ipv6 {
            description
              "IPv6 GKM (Group Key Management) Group";
            tailf:cli-prefix-key;
            type empty;
          }
          uses crypto-gdio-grouping;
          container default {
            description
              "Set a command to its defaults";
            uses crypto-gdio-default-grouping;
          }
        }
      }
      // crypto identity
      list identity {
        description
          "Enter a crypto identity list";
        tailf:cli-mode-name "config-crypto-identity";
        key "name";
        leaf name {
          type string;
        }
        container default {
          description
            "Set a command to its defaults";
          uses crypto-identity-default-grouping;
        }
        uses crypto-identity-grouping;
      }
      // crypto ikev2
      container ikev2 {
        description
          "Configure IKEv2 Options";
        uses crypto-ikev2-grouping;
      }
      // crypto ipsec
      container ipsec {
        description
          "Configure IPSEC policy";
        uses crypto-ipsec-grouping;
      }
      // crypto isakmp
      container isakmp {
        description
          "Configure ISAKMP policy";
        uses crypto-isakmp-grouping;
      }
      // crypto key
      container key {
        description
          "Long term key operations";
        uses crypto-key-grouping;
      }
      // crypto keyring
      list keyring {
        description
          "Key ring commands";
        tailf:cli-mode-name "config-keyring";
        key "name";
        leaf name {
          type string;
        }
        leaf vrf {
          description
            "Mention a vrf it belongs to";
          tailf:cli-hide-in-submode;
          type string;
        }
        container default {
          description
            "Set a command to its defaults";
          uses crypto-keyring-grouping;
        }
        uses crypto-keyring-grouping;
      }
      // crypto logging
      container logging {
        description
          "logging messages";
        container ezvpn {
          description
            "ezvpn logging enable/disable";
          presence "true";
          leaf group {
            description
              "ezvpn group";
            type string;
          }
        }
        leaf ikev2 {
          description
            "logging IKEv2 sessions";
          type empty;
        }
        leaf session {
          description
            "logging up/down session";
          type empty;
        }
      }
      // crypto map
      container map-ipv6 {
        tailf:cli-drop-node-name;
        list map {
          description
            "Enter a crypto map";
          tailf:cli-mode-name "config-crypto-map";
          tailf:cli-sequence-commands;
          tailf:cli-compact-syntax;
          key "name";
          leaf name {
            type string;
          }
          leaf ipv6 {
            description
              "IPv6 crypto map";
            tailf:cli-optional-in-sequence;
            tailf:cli-prefix-key;
            type empty;
          }
          leaf sequence-number {
            tailf:cli-drop-node-name;
            tailf:cli-hide-in-submode;
            type uint16;
          }
          leaf keying {
            tailf:cli-drop-node-name;
            tailf:cli-hide-in-submode;
            tailf:cli-optional-in-sequence;
            type enumeration {
              enum "ipsec-isakmp";
              enum "ipsec-manual";
              enum "gdoi";
            }
          }
          choice dynamic-profile {
            case dynamic-case {
              leaf dynamic {
                description
                  "Enable dynamic crypto map support";
                tailf:cli-hide-in-submode;
                tailf:cli-break-sequence-commands;
                tailf:cli-full-command;
                when "../keying = 'ipsec-isakmp'";
                type string;
              }
            }
            case profile-case {
              leaf profile {
                description
                  "Enable crypto map as a crypto-profile";
                tailf:cli-hide-in-submode;
                tailf:cli-full-command;
                when "../keying = 'ipsec-isakmp'";
                type string;
              }
            }
          }
          container default {
            description
              "Set a command to its defaults";
            tailf:cli-break-sequence-commands;
            uses crypto-map-default-grouping;
          }
          uses crypto-map-grouping;
        }
      }
      container map-ipv6-gdoi {
        tailf:cli-drop-node-name;
        list map {
          description
            "Enter a crypto map";
          tailf:cli-mode-name "config-crypto-map-fail-close";
          key "name";
          leaf name {
            type string;
          }
          leaf ipv6 {
            description
              "IPv6 crypto map";
            tailf:cli-prefix-key;
            type empty;
          }
          leaf gdoi {
            description
              "Configure crypto map gdoi features";
            tailf:cli-hide-in-submode;
            type enumeration {
              enum "fail-close";
            }
          }
          container default {
            description
              "Set a command to its defaults";
            uses crypto-map-gdoi-default-mapping;
          }
          uses crypto-map-gdoi-mapping;
        }
      }
      container map-client {
        tailf:cli-drop-node-name;
        list map {
          description
            "Enter a crypto map";
          tailf:cli-suppress-mode;
          key "name";
          leaf name {
            type string;
          }
          leaf ipv6 {
            description
              "IPv6 crypto map";
            tailf:cli-prefix-key;
            type empty;
          }
          container client {
            description
              "Specify client configuration settings";
            tailf:cli-display-separated;
            container accounting {
              description
                "Accounting parameters.";
              leaf list {
                description
                  "AAA accounting list to use";
                tailf:cli-full-command;
                type string;
              }
            }
            container authentication {
              description
                "Use Extended Authentication";
              leaf list {
                description
                  "AAA authentication list to use";
                tailf:cli-full-command;
                type string;
              }
            }
            container configuration {
              description
                "Specify client configuration settings";
              container address {
                description
                  "Specify client network address configuration";
                leaf initiate {
                  description
                    "Push the network address to the client";
                  tailf:cli-full-command;
                  type empty;
                }
                leaf respond {
                  description
                    "Respond to network address requests from the client";
                  tailf:cli-full-command;
                  type empty;
                }
              }
            }
          }
          container isakmp {
            description
              "Specify isakmp configuration settings";
            tailf:cli-sequence-commands;
            tailf:cli-compact-syntax;
            tailf:cli-display-separated;
            leaf authorization {
              description
                "Authorization parameters.";
              type empty;
            }
            leaf list {
              description
                "AAA Authorization list to use";
              tailf:cli-full-command;
              type string;
            }
          }
          leaf isakmp-profile {
            description
              "Specify isakmp profile to use";
            tailf:cli-full-command;
            type string;
          }
          leaf local-address {
            description
              "Interface to use for local address for this crypto map";
            tailf:cli-full-command;
            type string;
          }
          container redundancy {
            description
              "High availability options for this map";
            tailf:cli-display-separated;
            container replay-interval {
              description
                "HA replay counter interval";
              tailf:cli-sequence-commands;
              tailf:cli-compact-syntax;
              leaf inbound {
                description
                  "HA inbound replay counter interval";
                type uint32 {
                  range "0..1000";
                }
              }
              leaf outbound {
                description
                  "HA outbound replay counter interval";
                type uint32 {
                  range "1000..10000";
                }
              }
            }
          }
        }
      }
      // crypto mib
      container mib {
        description
          "Configure Crypto-related MIB Parameters";
        container ipsec {
          description
            "onfigure MIB Parameters";
          container flowmib {
            description
              "Configure IPSec Flow-MIB Parameters";
            container history {
              description
                "Configure IPSEC Flow MIB History Parameters";
              container failure {
                description
                  "Configure IPSEC Flow MIB Failure History Parameters";
                leaf size {
                  description
                    "Configure IPSEC Flow MIB Tunnel Failure History Window Size";
                  type uint8;
                }
              }
              container tunnel {
                description
                  "Configure IPSEC Flow MIB Tunnel History Parameters";
                leaf size {
                  description
                    "Configure IPSEC Flow MIB Tunnel Failure History Window Size";
                  type uint8;
                }
              }
            }
          }
        }
      }
      // crypto pki
      container pki {
        description
          "Public Key components";
        leaf authenticate {
          description
            "Get the CA certificate";
          type string;
        }
        container certificate {
          description
            "Actions on certificates";

/* Hex-data is not supported
          container certificate {
            tailf:cli-drop-node-name;
            tailf:cli-exit-command "quit";
            list hex-data {
              tailf:cli-drop-node-name;
              tailf:cli-suppress-mode;
              ordered-by "user";
              key hex;
              leaf hex {
                tailf:cli-multi-value;
                type string {
                }
              }
            }
          }
Hex-data is not supported */

          // crypto pki certificate chain *
          list chain {
            description
              "Identify certificates";
            tailf:cli-mode-name "config-cert-chain";
            key "name";
            leaf name {
              type string;
            }
            // crypto pki certificate chain * / certificate *
            list certificate {
              description
                "Certificate issued by the CA";
              tailf:cli-mode-name "config-pki-hexmode";
              tailf:cli-exit-command "quit";
              tailf:cli-delete-when-empty;
              key "serial";
              leaf serial {
                type string;
              }
              leaf certtype {
                tailf:cli-drop-node-name;
                tailf:cli-prefix-key;
                type enumeration {
                  enum "ca";
                  enum "ra-encrypt";
                  enum "ra-general";
                  enum "ra-sign";
                  enum "rollover";
                  enum "self-signed";
                }
              }

/* Hex-data is not supported
              list hex-data {
                tailf:cli-drop-node-name;
                tailf:cli-suppress-mode;
                ordered-by "user";
                key hex;
                leaf hex {
                  tailf:cli-multi-value;
                  type string {
                  }
                }
              }
Hex-data is not supported */

            }
          }
          list map {
            description
              "Define certificate attributes map";
            tailf:cli-mode-name "ca-certificate-map";
            key "tag";
            leaf tag {
              type string;
            }
            leaf sequence {
              tailf:cli-drop-node-name;
              tailf:cli-hide-in-submode;
              type uint16;
            }
            uses crypto-pki-certificate-map-grouping;
          }
          leaf pool {
            description
              "Identify CA certificates in pool";
            type empty;
          }
          leaf query {
            description
              "Get certificates from the CA after reboot";
            type empty;
          }
          container storage {
            description
              "specify where to store certificates";
            leaf path {
              tailf:cli-drop-node-name;
              tailf:cli-full-command;
              type union {
                type enumeration {
                  enum "bootflash:";
                  enum "flash:";
                  enum "nvram:";
                }
                type string;
              }
            }
            leaf on {
              description
                "Create keypairs on device";
              type empty;
            }
            leaf with-keypair {
              description
                "Store certificates with keypair";
              type empty;
            }
          }
          leaf validate {
            description
              "Validate a certificate chain";
            type string;
          }
        }
        // crypto pki crl
        container crl {
          description
            "Actions on certificate revocation lists";
          container cache {
            description
              "Cache which holds recently parsed CRLs";
            leaf size {
              description
                "Size of the recently parsed CRL cache";
              type uint32 {
                range "0..131072";
              }
            }
          }
          container download {
            description
              "auto-download CRL";
            container schedule {
              description
                "Schedule time to auto-download CRL";
              leaf prepublish {
                description
                  "Requests CRL at prepublish time";
                type uint16;
              }
              container retries {
                description
                  "Retry request for failed CDP locations";
                leaf number {
                  tailf:cli-drop-node-name;
                  type uint8 {
                    range "1..15";
                  }
                }
                leaf interval {
                  description
                    "retry time interval for each attempt";
                  type uint16 {
                    range "15..600";
                  }
                }
              }
              container time {
                description
                  "Request auto-download CRL at this time";
                tailf:cli-sequence-commands;
                tailf:cli-compact-syntax;
                leaf date {
                  tailf:cli-drop-node-name;
                  type enumeration {
                    enum "Friday";
                    enum "Monday";
                    enum "Saturday";
                    enum "Sunday";
                    enum "Thursday";
                    enum "Tuesday";
                    enum "Wednesday";
                  }
                }
                leaf clock {
                  tailf:cli-drop-node-name;
                  type string;
                }
              }
            }
            leaf trustpoint {
              description
                "Trustpoint to auto-download CRL";
              type string;
            }
            container url {
              description
                "URL to auto-download CRL";
              tailf:cli-sequence-commands;
              tailf:cli-compact-syntax;
              leaf name {
                tailf:cli-drop-node-name;
                type string;
              }
              leaf source-interface {
                description
                  "Interface used as source address";
                tailf:cli-break-sequence-commands;
                type string;
              }
              leaf vrf {
                description
                  "VRF to use for CRL download";
                type string;
              }
            }
          }
          leaf request {
            description
              "Requests a current CRL";
            type string;
          }
        }
        leaf enroll {
          description
            "Request a certificate from a CA";
          type string;
        }
        list export {
          description
            "Export certificate or PKCS12 file";
          tailf:cli-suppress-mode;
          key "name";
          leaf name {
            type string;
          }
          container pem {
            description
              "Export to PEM files";
            tailf:cli-hide-in-submode;
            tailf:cli-flatten-container;
            container terminal {
              description
                "Export via the terminal (cut-and-paste)";
              tailf:cli-flatten-container;
              presence "true";
              container pem-3des {
                description
                  "Encrypt the private key with 3DES";
                tailf:cli-flatten-container;
                tailf:alt-name "3des";
                leaf password {
                  description
                    "Passphrase";
                  tailf:cli-multi-value;
                  type string;
                }
              }
              container des {
                description
                  "Encrypt the private key with DES";
                tailf:cli-flatten-container;
                leaf password {
                  description
                    "Passphrase";
                  tailf:cli-multi-value;
                  type string;
                }
              }
              leaf rollover {
                description
                  "Export the rollover CA certificate";
                type empty;
              }
            }
            container url {
              description
                "Export via the file systems";
              tailf:cli-flatten-container;
              tailf:cli-sequence-commands;
              tailf:cli-compact-syntax;
              uses crypto-key-url-file-ex-grouping;
              leaf encrypt {
                tailf:cli-drop-node-name;
                tailf:cli-optional-in-sequence;
                type enumeration {
                  enum "3des";
                  enum "des";
                }
              }
              leaf password {
                description
                  "Passphrase";
                tailf:cli-multi-value;
                when "../encrypt";
                type string;
              }
            }
          }
          container pkcs12 {
            description
              "Export to PKCS12 file";
            tailf:cli-hide-in-submode;
            tailf:cli-flatten-container;
            tailf:cli-sequence-commands;
            tailf:cli-compact-syntax;
            uses crypto-key-url-file-ex-grouping;
            leaf password {
              description
                "Passphrase";
              tailf:cli-multi-value;
              type string;
            }
          }
        }
        //crypto pki import
        list import {
          description
            "Import certificate or PKCS12 file";
          tailf:cli-suppress-mode;
          key "name";
          leaf name {
            type string;
          }
          leaf certificate {
            description
              "Import a certificate from a TFTP server or the terminal";
            type empty;
          }
          container pem {
            description
              "Import from PEM files";
            tailf:cli-hide-in-submode;
            tailf:cli-flatten-container;
            tailf:cli-compact-syntax;
            leaf check {
              description
                "Validate certificate on input";
              type empty;
            }
            leaf exportable {
              description
                "Allow the key as to be exported";
              type empty;
            }
            container terminal {
              description
                "Import via the terminal (cut-and-paste)";
              tailf:cli-flatten-container;
              leaf password {
                description
                  "Passphrase";
                tailf:cli-multi-value;
                type string;
              }
            }
            container url {
              description
                "Export via the file systems";
              tailf:cli-flatten-container;
              tailf:cli-sequence-commands;
              tailf:cli-compact-syntax;
              uses crypto-key-url-file-ex-grouping;
              leaf password {
                description
                  "Passphrase";
                tailf:cli-multi-value;
                type string;
              }
            }
            leaf usage-keys {
              description
                "Usage key pairs";
              type empty;
            }
          }
          container pkcs12 {
            description
              "Import from PKCS12 file";
            tailf:cli-hide-in-submode;
            tailf:cli-flatten-container;
            tailf:cli-sequence-commands;
            tailf:cli-compact-syntax;
            uses crypto-key-url-file-ex-grouping;
            leaf password {
              description
                "Passphrase";
              tailf:cli-multi-value;
              type string;
            }
          }
        }
        // crypto pki profile enrollment
        container profile {
          description
            "Define a certificate profile";
          list enrollment {
            description
              "Define an enrollment profile";
            tailf:cli-mode-name "ca-profile-enroll";
            key "tag";
            leaf tag {
              type string;
            }
            uses crypto-pki-profile-enrollment-grouping;
            container default {
              description
                "Set a command to its defaults";
              uses crypto-pki-profile-enrollment-grouping;
            }
          }
        }
        //crypto pki server
        container server {
          description
            "Enable IOS Certificate server";
          tailf:cli-sequence-commands;
          tailf:cli-compact-syntax;
          leaf name {
            tailf:cli-drop-node-name;
            type string;
          }
          leaf rollover {
            description
              "Rollover the server's key and certificate";
            tailf:cli-optional-in-sequence;
            type empty;
          }
          leaf cancel {
            description
              "Cancel a pending rollover";
            tailf:cli-optional-in-sequence;
            type empty;
          }
        }
        // crypto pki trustpoint *
        list trustpoint {
          description
            "Define a CA trustpoint";
          tailf:cli-mode-name "ca-trustpoint";
          key "id";
          leaf id {
            type string;
          }
          //  authorization     Authorization parameters.
          //  auto-enroll       Automatically enroll this router identity
          //  certificate       certificate options
          //  chain-validation  Validation parameters
          //  crl               CRL options
          container enrollment {
            description
              "Enrollment parameters";
            leaf http-proxy {
              description
                "HTTP proxy server for enrollment";
              type string;
            }
            container mode {
              description
                "Mode supported by the Certificate Authority";
              leaf ra {
                description
                  "Registration Authority mode";
                type empty;
              }
            }
            leaf pkcs12 {
              type empty;
            }
            leaf profile {
              description
                "Specify an profile for enrollment";
              type string;
            }
            container retry {
              description
                "Polling parameters";
              leaf count {
                description
                  "How many times to poll CA for our certificate";
                type uint8 {
                  range "1..100";
                }
              }
              leaf period {
                description
                  "How long to wait between requests to CA for our certificate";
                type uint8 {
                  range "1..60";
                }
              }
            }
            leaf selfsigned {
              description
                "Generate a Self Signed Certificate";
              type empty;
            }
            container terminal {
              description
                "Enroll via the terminal (cut-and-paste)";
              presence "true";
              leaf pem {
                description
                  "Include PEM encapsulation boundaries";
                type empty;
              }
            }
            leaf url {
              description
                "CA server enrollment URL";
              type string;
            }
          }
          leaf serial-number {
            description 
              "include serial number";
            type empty;        
          }
          //  exit              Exit from certificate authority trustpoint
          //                    entry mode
          //  fingerprint       CA Certificate Fingerprint
          //  fqdn              include fully-qualified domain name
          //  hash              Hash algorithm
          //  ip-address        include ip address
          //  ip-extension      RFC3779 IP extension for device certificate
          //                    request
          //  match             Match a certificate map
          //  no                Negate a command or set its defaults
          //  ocsp              OCSP parameters
          //  on                create keypair on device.
          //  password          revocation password
          //  primary           Specify trustpoint as primary
          //  query             Query parameters
          //  regenerate        Regenerate keys on re-enrollment
          leaf revocation-check {
            description
              "Revocation checking options";
            type enumeration {
              enum "crl";
              enum "none";
              enum "ocsp";
            }
          }
          //  root              Protocol to get CA certificate
          leaf rsakeypair {
            description
              "Specify rsakeypair for this identity";
            type string;
          }
          leaf auto-enroll {
            description 
              "Automatically enroll this router identity";
            type empty;
          }
          //  serial-number     include serial number
          //  show              Show this router trustpoint
          //  source            Specify source
          //  storage           key and certificate storage location to use
          //                    with this trustpoint.
          leaf subject-name {
            description
              "Subject Name";
            type string;
          }
          //  usage             Certificate Usage
          //  vrf               vrf to use for enrollment and obtaining CRLs
        }
        // crypto pki token *
        container token {
          description
            "Configure cryptographic token";
          list token-name {
            tailf:cli-suppress-mode;
            tailf:cli-delete-when-empty;
            tailf:cli-drop-node-name;
            tailf:cli-compact-syntax;
            key "name";
            leaf name {
              type string;
            }
            uses crypto-pki-token-grouping;
          }
        }
        // crypto pki trustpool 
        container trustpool {
          description
            "Define CA trustpool";
          container import {
            description
              "Import a trustpool bundle";
            presence "true";
            leaf clean {
              description
                "Remove all downloaded trustpool certificates prior to import";
              type empty;
            }
            leaf terminal {
              description
                "Import bundle via the terminal (cut-and-paste) in PEM format";
              type empty;
            }
            container url {
              description
                "Import via the file systems";
              uses crypto-key-url-file-im-grouping;
            }
          }
        }
        // crypto pki default
        container default {
          description
            "set default values for tokens";
          uses crypto-pki-token-grouping;
        }
      }
      // crypto ssl
      container ssl {
        description
          "Configure Crypto SSL Options";
        container authorization {
          description
            "ssl authorization";
          leaf policy {
            description
              "Crypto SSL authorization policy";
            type string;
          }
        }
        container diagnose {
          description
            "SSLVPN diagnose";
          leaf error {
            description
              "Start error trace debug";
            type uint16 {
              range "1..1000";
            }
          }
        }
        leaf policy {
          description
            "Define SSL policies";
          type string;
        }
        leaf profile {
          description
            "Define SSL profiles";
          type string;
        }
        container proposal {
          description
            "Define ssl Proposal";
          tailf:cli-add-mode;
          tailf:cli-mode-name "config-crypto-ssl-proposal";
          leaf name {
            tailf:cli-drop-node-name;
            tailf:cli-hide-in-submode;
            type string;
          }
          container protection {
            description
              "Specify the protection algorithms";
            leaf rsa-3des-ede-sha1 {
              description
                "RSA, 3DES and SHA1";
              type empty;
            }
            leaf rsa-aes128-sha1 {
              description
                "RSA, AES128 and SHA1";
              type empty;
            }
            leaf rsa-aes256-sha1 {
              description
                "RSA, AES256 and SHA1";
              type empty;
            }
            leaf rsa-rc4128-md5 {
              description
                "RSA, RC4 and MD5";
              type empty;
            }
          }
        }
      }
      // crypto vpn
      container vpn {
        description
          "Configure crypto vpn commands";
        container anyconnect {
          description
            "Configure anyconnect client package";
          container file {
            tailf:cli-drop-node-name;
            tailf:cli-sequence-commands;
            tailf:cli-compact-syntax;
            leaf filename {
              tailf:cli-drop-node-name;
              type string;
            }
            leaf sequence {
              description
                "client-side download sequence num (priority) of this package";
              tailf:cli-optional-in-sequence;
              type uint8;
            }
          }
          container profile-container {
            tailf:cli-drop-node-name;
            tailf:cli-sequence-commands;
            tailf:cli-compact-syntax;
            leaf profile {
              description
                "Configure anyconnect client profile";
              type string;
            }
            leaf filename {
              tailf:cli-drop-node-name;
              type string;
            }
          }
        }
        leaf csd {
          description
            "Configure Secure Desktop package";
          type string;
        }
      }
      leaf xauth {
        description
          "X-Auth parameters";
        type string;
      }
    }

    /// ========================================================================
    /// cts
    /// ========================================================================
    
    grouping cts-sxp-connection-mode-local-grouping {
      container hold-time {
        tailf:cli-sequence-commands;
        tailf:cli-compact-syntax;
        description "Connection hold time period";
        leaf min-time {
          description "Enter minimum allowed Hold Time in seconds (0: apply global, 65535: no keepalive)";
          tailf:cli-drop-node-name;
          type uint16 {
            range "0..65535";
          }
        }
        leaf max-time {
          description "Enter maximum allowed Hold Time in seconds (0: apply global, 65535: no keepalive)";
          tailf:cli-drop-node-name;
          type uint16 {
            range "0..65535";
          }
        }
        leaf vrf {
          description "Name of the vrf this connection is in";
          tailf:cli-optional-in-sequence;
          type string;
        }
      }
    }
    
    container cts {
      description 
        "Cisco Trusted Security commands";
      container cache {
        description "CTS cache configuration";
        leaf enable {
          description "Enable CTS cache support";
          type empty;
        }
        container nv-storage {
          description "CTS nv-storage options";
          leaf nv-storage {
            tailf:cli-drop-node-name;
            type enumeration {
              enum "bootflash:";
              enum "crashinfo:";
              enum "kinfo:";
              enum "slot0:";
              enum "usb0:";
            }
          }
        }
      }
      leaf critical-authentication-conf {
        tailf:alt-name "critical-authentication";
        tailf:cli-diff-dependency "/ios:native/cts/critical-authentication/default/peer-sgt";
        type empty;
      }
      container critical-authentication {
        description "Critical-Auth configuration commands";
        presence true;
        container default {
          description "Enter default value";
          container peer-sgt {
            description "Default Peer SGT value";
            list  range {
              tailf:cli-drop-node-name;
              tailf:cli-suppress-mode;
              key "range";
              leaf range {
                description "Enter default peer-sgt value";
                type uint16 {
                  range "2..65519";
                }
              }
              leaf trusted {
                description "Trust the Source Group Tags that peer uses for sending";
                  type empty;
              }
            }
          }
          container pmk {
            description "Default PMK value to be used for all SAP";
            tailf:cli-compact-syntax;
            tailf:cli-sequence-commands;
            leaf type {
              tailf:cli-drop-node-name;
              tailf:cli-optional-in-sequence;
              type enumeration {
                enum "0";
                enum "6";
              }
            }
            leaf secret {
              tailf:cli-drop-node-name;
              type string;
            }
          }
        }
        container fallback {
          description "Access policy to be applied in Critical-Auth";
          leaf Cached {
            description "Cached values to be used for existing sessions";
              type empty;
          }
          leaf default {
            description "Configured values to be applied for existing sessions";
              type empty;
          }
        }
      }

      container authorization {
        description
          "CTS global authorization configuration";
        leaf list {
          description
            "Local authorization list to use for CTS";
          type string;
        }
      }
      leaf dot1x-server-timeout {
        description
          "Timeout for Radius Retries";
        type uint16 {
          range "30..65535";
        }
      }
      leaf dot1x-supp-timeout {
        description
          "Timeout for supplicant reply";
        type uint16 {
          range "30..65535";
        }
      }
      leaf logging {
        description
          "Set logging parameters";
        type enumeration {
          enum "verbose";
        }
      }
      container role-based {
        description
          "Role-based Access Control configuration commands";
        leaf sgt-caching {
          description
            "Enable SGT caching";
          type empty;
        }
        container permissions {
          description "Permissions from a source group to a destination group";
          container default {
            description "Default Permission list";
            leaf name {
              description "Role-based Access-list name";
              tailf:cli-drop-node-name;
              type string;
            }
          }
          container from {
            description "Source Group Tag (SGT) of filtered traffic";
            list  range {
              tailf:cli-drop-node-name;
              tailf:cli-suppress-mode;
              key "range";
              leaf range {
                description "Security Group Tag";
                type uint16 {
                  range "0..65519";
                }
              }
              container to {
                description "Destination Group Tag (DGT) of filtered traffic";
                list  range {
                  tailf:cli-drop-node-name;
                  tailf:cli-suppress-mode;
                  key "range";
                  leaf range {
                    description "Security Group Tag";
                    type uint16 {
                      range "0..65519";
                    }
                  }
                  
                  leaf name {
                    tailf:cli-drop-node-name;
                    type string;
                  }
                }
              }
            }
          }
        }
               
        container enforcement {
          description "Enable Role-based Access Control enforcement";
          presence true;
	  tailf:cli-display-separated;
          leaf logging-interval {
            description
              "Configure sgacl logging interval";
            type uint32 {
              range "5..86400";
            }
          }
          list vlan-list {
            description "VLANs on which Role-based ACLs are enforced";
            tailf:cli-suppress-mode;
            key "id";
            leaf id {
              description "VLAN id";
              type union {
                type string;
                type enumeration {
                  enum all;
                }  
              }
            }
          }
        }
        list sgt-map {
          description
            "Assign Security Group Tag (SGT) to IP host or network address";
          tailf:cli-suppress-mode;
          key "ip sgt";
          leaf ip {
            type union {
              type inet:ipv4-address;
              type inet:ipv4-prefix;
              type inet:ipv6-address;
              type inet:ipv6-prefix;
            }
          }
          leaf sgt {
            description
              "Security Group Tag (SGT)";
            tailf:cli-expose-key-name;
            type uint16;
          }
          leaf vrf {
            tailf:cli-prefix-key {
              tailf:cli-before-key "1";
            }
            description
              "Select VPN Routing/Forwarding instance for the binding";
            type string;
          }
          leaf host {
            tailf:cli-prefix-key {
              tailf:cli-before-key "1";
            }
            type empty;
          }
        }
        
        container sgt-map-vlan-list {
          description "VLANs on which Role-based ACLs are enforced";
	  tailf:cli-drop-node-name;
	  list sgt-map {
	    tailf:cli-suppress-mode;
            key "vlan-list";
            leaf vlan-list {
              tailf:cli-expose-key-name;
              description "VLANs id";
              type union {
                type string;
                type enumeration {
                  enum all;
                }
              }  
            }              
            leaf sgt {
              description "Security Group Tag value";
              type int16;
            }
          }
        }
      }
      container server {
        description
          "CTS server list configuration";
        leaf deadtime {
          description
            "Configure server group deadtime to specify how long a servermarked as dead should not be used";
          tailf:cli-full-command;
          type uint32 {
            range "0..864000";
          }
        }
        container key-wrap {
          description
            "CTS key-wrap configuration";
          leaf enable {
            description
              "Enable CTS key-wrap for Private server-list";
            type empty;
          }
        }
        container load-balance {
          description
            "CTS Server group load-balancing options";
          container method {
            description
              "Method by which the next server will be picked";
            container least-outstanding {
              description
                "Pick the server with the least transactions outstanding";
              presence "true";
              tailf:cli-compact-syntax;
              leaf batch-size {
                description
                  "Size of the transaction batch that should be load-balanced";
                type uint32 {
                  range "1..2147483647";
                }
              }
              leaf ignore-preferred-server {
                description
                  "Do not attempt to stick with the same server throughout a session";
                tailf:cli-full-command;
                type empty;
              }
            }
          }
        }
        container test {
          description
            "Configure server automated test for liveness check";
          list server {
            tailf:cli-drop-node-name;
            tailf:cli-suppress-mode;
            key "ip";
            leaf ip {
              type inet:ipv4-address;
            }
            uses cts-server-grouping;
          }
          container all {
            description
              "Configure for all servers";
            uses cts-server-grouping;
          }
        }
      }
      leaf sgt {
        description
          "Local device security group";
        type uint16 {
          range "2..65519";
        }
      }
      container sxp {
        description "CTS sxp configuration";
        container default {
          description "Enter default value";
          container password {
            tailf:cli-compact-syntax;
            tailf:cli-sequence-commands;
            leaf type {
              tailf:cli-drop-node-name;
              tailf:cli-optional-in-sequence;
              type enumeration {
                enum "0";
                enum "6";
                enum "7";
              }
            }
            leaf secret {
              tailf:cli-drop-node-name;
              type string;
            }
          }
        }
        container connection {
          description "CTS SXP Connection Configuration";
          container peer {
            description "SXP Peer IP address";
            list  ipv4 {
              tailf:cli-drop-node-name;
              tailf:cli-suppress-mode;
              key "ipv4";
              leaf ipv4 {
                description "Enter SXP Peer IP address (IPv4)";
                type inet:ipv4-address;
              }
              container source {
                description "Source IP address";
                list  ipv4 {
                  tailf:cli-drop-node-name;
                  tailf:cli-suppress-mode;
                  key "ipv4";
                  leaf ipv4 {
                    description "Enter SXP Source IP address (IPv4)";
                    type inet:ipv4-address;
                  }
                  list password {
                    description "password details";
                    max-elements "1";
                    tailf:cli-suppress-mode;
                    key "password-type";
                    leaf password-type {
                      type enumeration {  
                        enum "default";
                        enum "none";
                      }
                    }
                    container mode {
                      description "Specify SXP connection mode";
                      container local {
                        description "Configure the mode on the local device";
                        presence true;
                        leaf both {
                          description "Configure the mode as both";
                          type empty;
                        }
                        container listener {
                          description "Receive SXP messages on the conn";
                          presence true;
                          uses cts-sxp-connection-mode-local-grouping;
                        }
                        container speaker {
                          description "Send SXP messages on the conn";
                          presence true;
                          uses cts-sxp-connection-mode-local-grouping;
                        }
                      }
                    }
                  }
                }
              }
            }
          }
        }
        leaf enable {
          description "Enable CTS SXP support";
          type empty;
        }
      }
    }
  
    /// ========================================================================
    ///  bfd
    /// ========================================================================
    container bfd {
      description
        "BFD configuration commands";
      leaf l2cos {
        description
          "Value of L2 COS for BFD Pkts over VLAN interfaces";
        type uint8 {
          range "0..6";
        }
      }
      container map {
        description
          "configure bfd map entry for multi-hop sessions";
        container ipv4 {
          description
            "IPv4 Address Family";
          container no-vrf {
            tailf:cli-drop-node-name;
            tailf:cli-sequence-commands;
            tailf:cli-compact-syntax;
            leaf dest-ip {
              tailf:cli-drop-node-name;
              type ios:ipv4-prefix;
            }
            leaf src-ip {
              tailf:cli-drop-node-name;
              tailf:cli-break-sequence-commands;
              type ios:ipv4-prefix;
            }
            leaf template-name {
              tailf:cli-drop-node-name;
              tailf:cli-full-command;
              type string;
            }
          }
          container vrf {
            description
              "Destination VRF name";
            list dst-vrf {
              tailf:cli-drop-node-name;
              tailf:cli-suppress-mode;
              key "dst-vrf";
              leaf dst-vrf {
                description
                  "Destination VRF instance name";
                type string;
              }
              leaf A_PERIOD_B_PERIOD_C_PERIOD_D_SLASH_nn {
                tailf:alt-name "A.B.C.D/nn";
                description
                  "Destination IP prefix/len";
                type empty;
              }
            }
          }
        }
        container ipv6 {
          description
            "IPv6 Address Family";
          list dp-ipv6_prefix {
            tailf:cli-drop-node-name;
            tailf:cli-suppress-mode;
            key "dp-ipv6_prefix";
            leaf dp-ipv6_prefix {
              description
                "Destination IPv6 prefix/len";
              type inet:ipv6-prefix;
            }
            leaf bfd-nm {
              description
                "bfd template name";
              tailf:cli-drop-node-name;
              type string;
            }
            list src-ipv6_prefix0 {
              tailf:cli-drop-node-name;
              tailf:cli-suppress-mode;
              key "src-ipv6_prefix0";
              leaf src-ipv6_prefix0 {
                description
                  "Source IPv6 prefix/len";
                type inet:ipv6-prefix;
              }
              leaf bfd-name {
                description
                  "bfd template name";
                tailf:cli-drop-node-name;
                type string;
              }
            }
            container vrf {
              description
                "Source VRF name";
              list src-vrf {
                tailf:cli-drop-node-name;
                tailf:cli-suppress-mode;
                key "src-vrf";
                leaf src-vrf {
                  description
                    "Source VRF instance name";
                  type string;
                }
                leaf src-ipv6_prefix {
                  description
                    "Source IPv6 prefix/len";
                  tailf:cli-drop-node-name;
                  type inet:ipv6-prefix;
                }
              }
            }
          }
          container vrf {
            description
              "Destination VRF name";
            list dst-vrf {
              tailf:cli-drop-node-name;
              tailf:cli-suppress-mode;
              key "dst-vrf";
              leaf dst-vrf {
                description
                  "Destination VRF instance name";
                type string;
              }
              leaf dst-ipv6_prefix {
                description
                  "Destination IPv6 prefix/len";
                tailf:cli-drop-node-name;
                type inet:ipv6-prefix;
              }
            }
          }
        }
      }
      leaf slow-timers {
        description
          "Value in ms to use for slow timers";
        type uint16 {
          range "1000..30000";
        }
      }
    }

    /// ========================================================================
    ///  bfd-template
    /// ========================================================================
    container bfd-template {
      description
        "BFD-template";
      container single-hop {
        description
          "Single-hop template";
        tailf:cli-add-mode;
        tailf:cli-mode-name "config-bfd";
        leaf name {
          tailf:cli-drop-node-name;
          tailf:cli-hide-in-submode;
          type string;
        }
        container interval {
          description
            "Transmit interval between BFD packets";
          container microseconds {
            description
              "Specify BFD timers in microseconds";
            tailf:cli-compact-syntax;
            tailf:cli-sequence-commands;
            leaf min-tx {
              description
                "Minimum transmit interval capability";
              type uint32 {
                range "3300..999000";
              }
            }
            leaf min-rx {
              description
                "Minimum receive interval capability";
              type uint32 {
                range "3300..999000";
              }
            }
            leaf multiplier {
              description
                "Multiplier value used to compute holddown";
              type uint8 {
                range "3..50";
              }
            }
          }
        }
      }
    }

    /// ========================================================================
    ///  pfr 
    /// ======================================================================== 
    grouping pfr-border-grouping {
      container cost-minimization {
        description
          "Specify an ISP's bw cost related information";
        container calc {
          description
            "Specify how the fee is calculated";
          presence "true";
          leaf combined {
            description
              "Billing based on combination of Egress and Ingress rollup samples";
            type empty;
          }
          leaf separate {
            description
              "Billing based on separate egress and ingress rollup samples";
            type empty;
          }
          leaf sum {
            description
              "Billing based on summed egress and ingress rollup samples";
            type empty;
          }
        }
        container discard {
          description
            "Specify how often and how many rollup samples are discarded";
          presence "true";
          leaf absolute {
            description
              "Specify that the discard is a number of rollup samples discarded";
            type empty;
          }
          leaf daily {
            description
              "Specify if the discard period is daily rather than monthly";
            type empty;
          }
          leaf percent {
            description
              "Specify that the discard is a percentage of rollup samples discarded";
            type empty;
          }
        }
        container end {
          description
            "Specify the billing end date and time zone difference";
          presence "true";
          leaf day-of-month {
            description
              "Specify the day of month that the billing period ends";
            type empty;
          }
        }
        container fixed {
          description
            "Specify that fee is fixed regardless of usage";
          presence "true";
          leaf fee {
            description
              "Fixed fee for billing";
            type empty;
          }
        }
        container nickname {
          description
            "Specify an nickname for the cost structure";
          presence "true";
          leaf nick-str {
            description
              "Specify the nickname alphanumeric string";
            tailf:cli-drop-node-name;
            type string;
          }
        }
        container sampling {
          description
            "Specify the sampling period and rollup details";
          presence "true";
          leaf period {
            description
              "Specify the sampling period";
            type empty;
          }
        }
        container summer-time {
          description
            "Specify summer time start and end";
          presence "true";
          leaf wk-start {
            description
              "Week number to start";
            tailf:cli-drop-node-name;
            type uint8 {
              range "1..4";
            }
          }
          leaf first {
            description
              "First week of the month";
            type empty;
          }
          leaf last {
            description
              "Last week of the month";
            type empty;
          }
        }
        container tier {
          description
            "Specify the top of a tier and the associated fee";
          presence "true";
          leaf tier-cap {
            description
              "Specify the top of the tier as a percentage of capacity";
            tailf:cli-drop-node-name;
            type uint8 {
              range "1..100";
            }
          }
        }
      }
      container downgrade {
        description
          "Specify route downgrade options for this interface";
        container bgp {
          description
            "Specify downgrade options for BGP advertisements";
          presence "true";
          leaf community {
            description
              "Specify downgrade options for BGP advertisements";
            type empty;
          }
        }
      }
      leaf link-group {
        description
          "Specify link group name";
        type string;
      }
      container max-xmit-utilization {
        description
          "Specify the threshold utilization for an external interface";
        container absolute {
          description
            "Specify the utilization as an absolute value";
          presence "true";
          leaf exit-kbps {
            description
              "Specify the kbps threshold for this exit's bandwitdh";
            tailf:cli-drop-node-name;
            type uint32 {
              range "1..1000000000";
            }
          }
        }
        container percentage {
          description
            "Specify the utilization as a percentage of the exit's bandwidth";
          presence "true";
          leaf exit-pct {
            description
              "Specify the percentage of the exit's bandwidth";
            tailf:cli-drop-node-name;
            type uint8 {
              range "1..100";
            }
          }
        }
      }
      container maximum {
        description
          "Specify maximum values";
        container utilization {
          description
            "Specify the utilization parameters";
          presence "true";
          leaf receive {
            description
              "Specify receive utilization parameter";
            type empty;
          }
        }
      }
    }
    container pfr {
      description
        "Performance Routing configuration submodes";
      container border {
        description
          "Enter PfR border router configuration submode";
        tailf:cli-add-mode;
        tailf:cli-mode-name "config-pfr-br";
        presence "true";
        container pfr-Mode__config-pfr-br {
          tailf:cli-drop-node-name;
          container active-probe {
            description
              "Specify active probe parameters";
            container address {
              description
                "Identify probe address parameters";
              container source {
                description
                  "Identify probe source address";
                container interface {
                  description
                    "Identify probe source address from interface";
                  tailf:cli-compact-syntax;
                  tailf:cli-flatten-container;
                  uses interface-grouping;
                }
              }
            }
          }
          container local {
            description
              "Specify the local interface for PfR connection";
            container interface {
              tailf:cli-drop-node-name;
              tailf:cli-compact-syntax;
              tailf:cli-flatten-container;
              uses interface-grouping;
            }
          }
          leaf logging {
            description
              "Event logging";
            type empty;
          }
          container master {
            description
              "Specify the PfR master controller IP address";
            list ipv4 {
              tailf:cli-drop-node-name;
              tailf:cli-suppress-mode;
              key "ipv4";
              leaf ipv4 {
                description
                  "IP address";
                type inet:ipv4-address;
              }
              leaf key-chain {
                description
                  "name of key-chain";
                type string;
              }
            }
          }
          leaf port {
            description
              "Specify PfR port number";
            type uint16 {
              range "1..65535";
            }
          }
          leaf shutdown {
            description
              "Disable PfR border router functionality";
            type empty;
          }
        }
      }
      container master {
        description
          "Enter PfR master controller configuration submode";
        tailf:cli-add-mode;
        tailf:cli-mode-name "config-pfr-mc";
        presence "true";
        container icmp-Mode-config-pfr-mc {
          tailf:cli-drop-node-name;
          container active-probe {
            description
              "Manually create an active probe for a known target";
            leaf echo {
              description
                "IP address of probe target";
              type inet:host;
            }
            container jitter {
              description
                "Perform jitter probe operations (requires a responder)";
              list ipv4-or-hostname {
                tailf:cli-drop-node-name;
                tailf:cli-suppress-mode;
                key "ipv4-or-hostname";
                leaf ipv4-or-hostname {
                  description
                    "IP address of probe target";
                  type inet:host;
                }
                leaf target-port {
                  description
                    "Target Port Number";
                  type uint16 {
                    range "1..65535";
                  }
                }
              }
            }
            container tcp-conn {
              description
                "Perform TCP Connection / Disconnect probe operations";
              list ipv4-or-hostname {
                tailf:cli-drop-node-name;
                tailf:cli-suppress-mode;
                key "ipv4-or-hostname";
                leaf ipv4-or-hostname {
                  description
                    "IP address of probe target";
                  type inet:host;
                }
                leaf target-port {
                  description
                    "Target Port Number";
                  type uint16 {
                    range "1..65535";
                  }
                }
              }
            }
            container udp-echo {
              description
                "Perform UDP Echo probe operations (requires a responder)";
              list ipv4-or-hostname {
                tailf:cli-drop-node-name;
                tailf:cli-suppress-mode;
                key "ipv4-or-hostname";
                leaf ipv4-or-hostname {
                  description
                    "IP address of probe target";
                  type inet:host;
                }
                leaf target-port {
                  description
                    "Target Port Number";
                  type uint16 {
                    range "1..65535";
                  }
                }
              }
            }
          }
          container application {
            description
              "Define application";
            container define {
              description
                "Define application";
              list app-def {
                tailf:cli-drop-node-name;
                tailf:cli-suppress-mode;
                key "app-def";
                leaf app-def {
                  description
                    "Application definition name";
                  type string;
                }
                leaf access-list {
                  description
                    "Application definition access-list name";
                  type string;
                }
                leaf nbar {
                  description
                    "Define nbar application";
                  type empty;
                }
              }
            }
          }
          container backoff {
            description
              "Specify backoff timer parameters";
            list boff {
              tailf:cli-drop-node-name;
              tailf:cli-suppress-mode;
              key "boff";
              leaf boff {
                description
                  "Specify minimum value of backoff timer (secs)";
                type uint16 {
                  range "90..7200";
                }
              }
              list boff0 {
                tailf:cli-drop-node-name;
                tailf:cli-suppress-mode;
                key "boff0";
                leaf boff0 {
                  description
                    "Specify maximum value of backoff timer (secs)";
                  type uint16 {
                    range "90..7200";
                  }
                }
                leaf bstep {
                  description
                    "Specify optional backoff timer step (secs)";
                  tailf:cli-drop-node-name;
                  type uint16 {
                    range "90..7110";
                  }
                }
              }
            }
          }
          leaf bandwidth-resolution {
            description
              "Enable/configure Bandwidth Resolution";
            type empty;
          }
          container border {
            description
              "Enter PfR managed border router configuration submode";
            list ipv4 {
              tailf:cli-drop-node-name;
              tailf:cli-mode-name "config-pfr-mc-br";
              key "ipv4";
              leaf ipv4 {
                description
                  "IP address of border router";
                type inet:ipv4-address;
              }
              list key-chain {
                description
                  "Specify a key-chain";
                tailf:cli-mode-name "config-pfr-mc-br";
                key "kc-name";
                leaf kc-name {
                  description
                    "name of key-chain";
                  type string;
                }
                leaf interface {
                  description
                    "Specify an PfR managed border router interface";
                  type empty;
                }
              }
              leaf interface {
                description
                  "Specify an PfR managed border router interface";
                type empty;
              }
            }
          }
          container delay {
            description
              "Specify delay parameters";
            leaf relative {
              description
                "short/long term in percentage. e.g. 125 is short/long = 1.25";
              type uint16 {
                range "1..1000";
              }
            }
            leaf threshold {
              description
                "Maximum absolute delay threshold (msecs)";
              type uint16 {
                range "1..10000";
              }
            }
          }
          leaf exporter {
            description
              "name of flow exporter";
            type string;
          }
          leaf holddown {
            description
              "Specify hold-down timer parameter (secs)";
            type uint16 {
              range "90..65535";
            }
          }
          container jitter {
            description
              "Specify jitter parameters";
            leaf threshold {
              description
                "Maximum absolute jitter threshold (ms)";
              type uint16 {
                range "1..1000";
              }
            }
          }
          leaf keepalive {
            description
              "Specify keepalive interval in seconds";
            type uint16 {
              range "0..1000";
            }
          }
          container learn {
            description
              "Enter prefix and traffic class learning submode";
            tailf:cli-add-mode;
            tailf:cli-mode-name "config-pfr-mc-learn";
            presence "true";
            container lrn-Mode__config-pfr-mc-learn {
              tailf:cli-drop-node-name;
              container aggregation-type {
                description
                  "Type of prefix to aggregate";
                leaf bgp {
                  description
                    "Aggregate prefixes learned via BGP";
                  type empty;
                }
                leaf non-bgp {
                  description
                    "Aggregate prefixes not learned via BGP";
                  type empty;
                }
                leaf prefix-length {
                  description
                    "Specify the prefix mask";
                  type uint8 {
                    range "1..32";
                  }
                }
              }
              leaf delay {
                description
                  "Learn top prefixes based on delay";
                type empty;
              }
              container expire {
                description
                  "Set expiry criteria for learn prefixes";
                container after {
                  description
                    "Specify expiry criteria for learn prefixes";
                  leaf session {
                    description
                      "Specify the value";
                    type uint16 {
                      range "1..65535";
                    }
                  }
                  leaf time {
                    description
                      "Specify the value";
                    type uint16 {
                      range "1..65535";
                    }
                  }
                }
              }
              container inside {
                description
                  "Learn prefixes inside the network";
                leaf bgp {
                  description
                    "Learn inside prefixes advertised by BGP out PfR External Interfaces";
                  type empty;
                }
              }
              container list {
                description
                  "Create PfR Learn Traffic Class List and enter the sub-mode";
                container seq {
                  description
                    "PfR Learn Traffic Class List sequence number";
                  list pfr-tc {
                    tailf:cli-drop-node-name;
                    tailf:cli-suppress-mode;
                    key "pfr-tc";
                    leaf pfr-tc {
                      description
                        "PfR Learn Traffic Class List sequence number";
                      type uint16 {
                        range "1..65535";
                      }
                    }
                    leaf refname {
                      description
                        "PfR Learn Traffic Class List reference name";
                      type empty;
                    }
                  }
                }
              }
              leaf monitor-period {
                description
                  "Specify the period in minutes";
                type uint16 {
                  range "1..1440";
                }
              }
              leaf periodic-interval {
                description
                  "Specify the interval in minutes";
                type uint16 {
                  range "0..10080";
                }
              }
              container prefixes {
                description
                  "Number of prefixes to learn";
                list prnum {
                  tailf:cli-drop-node-name;
                  tailf:cli-suppress-mode;
                  key "prnum";
                  leaf prnum {
                    description
                      "Specify the number of prefixes";
                    type uint32 {
                      range "0..100000";
                    }
                  }
                  leaf applications {
                    description
                      "Specify the number of appl";
                    type uint16 {
                      range "0..50000";
                    }
                  }
                }
              }
              leaf throughput {
                description
                  "Learn top prefixes based on throughput";
                type empty;
              }
              container traffic-class {
                description
                  "Set traffic class filters";
                container aggregate {
                  description
                    "Traffic class aggregation specification";
                  leaf access-list {
                    description
                      "IP access-list name";
                    type string;
                  }
                }
                container filter {
                  description
                    "Traffic class filter specification";
                  leaf access-list {
                    description
                      "IP access-list name";
                    type string;
                  }
                }
                container keys {
                  description
                    "Specify Learn keys for applications";
                  container dport {
                    description
                      "Learn top appls based on destination port";
                    presence "true";
                    leaf dscp {
                      description
                        "Learn top appls based on DSCP";
                      type empty;
                    }
                    leaf protocol {
                      description
                        "Learn top appls based on protocol";
                      type empty;
                    }
                    leaf sport {
                      description
                        "Learn top appls based on source port";
                      type empty;
                    }
                  }
                  container dscp {
                    description
                      "Learn top appls based on DSCP";
                    presence "true";
                    leaf dport {
                      description
                        "Learn top appls based on destination port";
                      type empty;
                    }
                    leaf protocol {
                      description
                        "Learn top appls based on protocol";
                      type empty;
                    }
                    leaf sport {
                      description
                        "Learn top appls based on source port";
                      type empty;
                    }
                  }
                  container protocol {
                    description
                      "Learn top appls based on protocol";
                    presence "true";
                    leaf dport {
                      description
                        "Learn top appls based on destination port";
                      type empty;
                    }
                    leaf dscp {
                      description
                        "Learn top appls based on DSCP";
                      type empty;
                    }
                    container sport {
                      description
                        "Learn top appls based on source port";
                      presence "true";
                      leaf dport {
                        description
                          "Learn top appls based on destination port";
                        type empty;
                      }
                      leaf dscp {
                        description
                          "Learn top appls based on DSCP";
                        type empty;
                      }
                    }
                  }
                  container sport {
                    description
                      "Learn top appls based on source port";
                    presence "true";
                    leaf dport {
                      description
                        "Learn top appls based on destination port";
                      type empty;
                    }
                    leaf dscp {
                      description
                        "Learn top appls based on DSCP";
                      type empty;
                    }
                    leaf protocol {
                      description
                        "Learn top appls based on protocol";
                      type empty;
                    }
                  }
                }
              }
            }
          }
          leaf logging {
            description
              "Event Logging";
            type empty;
          }
          container loss {
            description
              "Specify loss parameters";
            leaf relative {
              description
                "short/long term in percentage. e.g. 125 is short/long = 1.25";
              type uint16 {
                range "1..1000";
              }
            }
            leaf threshold {
              description
                "Maximum absolute lost packet threshold in percentage e.g., 1 is 0.0001 percent";
              type uint32 {
                range "1..1000000";
              }
            }
          }
          container max {
            description
              "Specify the upper limit";
            container prefix {
              description
                "Specify prefix upper limit";
              container total {
                description
                  "Specify max total prefix limit";
                list maxpr {
                  tailf:cli-drop-node-name;
                  tailf:cli-suppress-mode;
                  key "maxpr";
                  leaf maxpr {
                    description
                      "Specify the max total prefix limit value";
                    type uint32 {
                      range "1..100000";
                    }
                  }
                  leaf learn {
                    description
                      "Specify max learn prefix limit value";
                    type uint32 {
                      range "0..100000";
                    }
                  }
                }
              }
            }
            container range {
              description
                "Specify range value";
              container receive {
                description
                  "Specify receive range";
                leaf percent {
                  description
                    "Specify the percentage range";
                  type uint8 {
                    range "0..100";
                  }
                }
              }
            }
          }
          container max-range-utilization {
            description
              "Configure the maximum range for utilization of all exits";
            leaf percent {
              description
                "Specify the percentage range";
              type uint8 {
                range "1..100";
              }
            }
          }
          container mc-peer {
            description
              "Enable MC-to-MC peering";
            presence "true";
            list ipv4 {
              tailf:cli-drop-node-name;
              tailf:cli-suppress-mode;
              key "ipv4";
              leaf ipv4 {
                description
                  "IP address of head-end MC peer";
                type inet:ipv4-address;
              }
              list interface {
                tailf:cli-drop-node-name;
                tailf:cli-suppress-mode;
                key "interface";
                leaf interface {
                  description
                    "Loopback interface";
                  type string;
                }
                leaf description {
                  description
                    "MC site description (max 40 char)";
                  tailf:cli-multi-value;
                  type string;
                }
                leaf domain {
                  description
                    "Domain value";
                  type uint16 {
                    range "1..65535";
                  }
                }
              }
            }
            leaf description {
              description
                "MC site description (max 40 char)";
              tailf:cli-multi-value;
              type string;
            }
            container domain {
              description
                "SAF domain ID to be used for MC-to-MC peering";
              list dmval {
                tailf:cli-drop-node-name;
                tailf:cli-suppress-mode;
                key "dmval";
                leaf dmval {
                  description
                    "Domain value";
                  type uint16 {
                    range "1..65535";
                  }
                }
                list ipv4 {
                  tailf:cli-drop-node-name;
                  tailf:cli-suppress-mode;
                  key "ipv4";
                  leaf ipv4 {
                    description
                      "IP address of head-end MC peer";
                    type inet:ipv4-address;
                  }
                  leaf interface {
                    description
                      "Loopback interface";
                    tailf:cli-drop-node-name;
                    type string;
                  }
                }
                leaf description {
                  description
                    "MC site description (max 40 char)";
                  tailf:cli-multi-value;
                  type string;
                }
                leaf eigrp {
                  description
                    "Loopback interface";
                  type string;
                }
                leaf head-end {
                  description
                    "Loopback interface";
                  type string;
                }
              }
            }
            container eigrp {
              description
                "Use explicit EIGRP configuration instead of auto-config";
              list interface {
                tailf:cli-drop-node-name;
                tailf:cli-suppress-mode;
                key "interface";
                leaf interface {
                  description
                    "Loopback interface";
                  type string;
                }
                leaf description {
                  description
                    "MC site description (max 40 char)";
                  tailf:cli-multi-value;
                  type string;
                }
                leaf domain {
                  description
                    "Domain value";
                  type uint16 {
                    range "1..65535";
                  }
                }
              }
            }
            container head-end {
              description
                "Specify this router as head-end MC-peer";
              list interface {
                tailf:cli-drop-node-name;
                tailf:cli-suppress-mode;
                key "interface";
                leaf interface {
                  description
                    "Loopback interface";
                  type string;
                }
                leaf description {
                  description
                    "MC site description (max 40 char)";
                  tailf:cli-multi-value;
                  type string;
                }
                leaf domain {
                  description
                    "Domain value";
                  type uint16 {
                    range "1..65535";
                  }
                }
              }
            }
          }
          container mode {
            description
              "Specify PfR operating mode settings";
            container monitor {
              description
                "Specify PfR prefix monitoring policy settings";
              container active {
                description
                  "Enable active monitoring mode";
                presence "true";
                leaf throughput {
                  description
                    "Enable active monitoring with throughput from passive mode";
                  type empty;
                }
              }
              leaf both {
                description
                  "Enable active and passive monitoring modes";
                type empty;
              }
              leaf fast {
                description
                  "Enable fast monitoring mode";
                type empty;
              }
              leaf passive {
                description
                  "Enable passive monitoring mode";
                type empty;
              }
            }
            container route {
              description
                "Specify PfR route control policy settings";
              leaf control {
                description
                  "Enable PfR to control routes automatically";
                type empty;
              }
              container metric {
                description
                  "Specify PfR route protocol related settings";
                container bgp {
                  description
                    "Specify PfR bgp protocol settings";
                  leaf local-pref {
                    description
                      "Specify the local preference for bgp controlled routes";
                    type uint16 {
                      range "1..65535";
                    }
                  }
                }
                container eigrp {
                  description
                    "Specify PfR eigrp routes related settings";
                  leaf tag {
                    description
                      "Specify a tag value for PfR controlled eigrp routes";
                    type uint16 {
                      range "1..65535";
                    }
                  }
                }
                container static {
                  description
                    "Specify PfR static routes related settings";
                  leaf tag {
                    description
                      "Specify a tag value for PfR controlled static routes";
                    type uint16 {
                      range "1..65535";
                    }
                  }
                }
              }
              leaf observe {
                description
                  "PfR offers route control advice, but does not take any action";
                type empty;
              }
              container protocol {
                description
                  "Specify OER route control protocol";
                leaf pbr {
                  description
                    "Specify OER route control protocol Policy-Based-Routing";
                  type empty;
                }
              }
            }
            container verify {
              description
                "Specify verification behavior";
              leaf bidirectional {
                description
                  "Verify bidirectional traffic of applications";
                type empty;
              }
            }
          }
          container mos {
            description
              "Specify mos parameters";
            container threshold {
              description
                "Minimum MOS threshold";
              list mos-thresh {
                tailf:cli-drop-node-name;
                tailf:cli-suppress-mode;
                key "mos-thresh";
                leaf mos-thresh {
                  description
                    "Minimum absolute MOS threshold 1.00 - 5.00";
                  type string;
                }
                leaf percent {
                  description
                    "Maximum percentage probe with MOS below threshold";
                  type uint8 {
                    range "1..100";
                  }
                }
              }
            }
          }
          leaf periodic {
            description
              "Specify periodic rotation timer value (secs)";
            type uint16 {
              range "90..7200";
            }
          }
          leaf policy-rules {
            description
              "pfr-map name";
            type string;
          }
          leaf port {
            description
              "Specify tcp port number for PfR communication";
            type uint16 {
              range "1..65535";
            }
          }
          container probe {
            description
              "Specify number of packets for jitter probe";
            leaf packets {
              description
                "probe packets <number>";
              type uint8 {
                range "1..255";
              }
            }
          }
          container resolve {
            description
              "Specify PfR policy resolver settings";
            leaf cost {
              description
                "Specify PfR cost policy resolver settings";
              type empty;
            }
            container delay {
              description
                "Specify PfR delay policy resolver settings";
              container priority {
                description
                  "Specify the order in which resolver will consider this policy";
                list del-pol {
                  tailf:cli-drop-node-name;
                  tailf:cli-suppress-mode;
                  key "del-pol";
                  leaf del-pol {
                    description
                      "Specify this policy's priority; 1 being highest";
                    type uint8 {
                      range "1..9";
                    }
                  }
                  leaf variance {
                    description
                      "Specify range; e.g. 25 means all exits measuring up to 25% worse than the best exit are considered equivalent";
                    type uint8 {
                      range "1..100";
                    }
                  }
                }
              }
            }
            leaf equivalent-path-round-robin {
              description
                "Specify equivalent-path round-robin resolver";
              type empty;
            }
            container jitter {
              description
                "Specify PfR jitter policy resolver settings";
              container priority {
                description
                  "Specify the order in which resolver will consider this policy";
                list jit-pol {
                  tailf:cli-drop-node-name;
                  tailf:cli-suppress-mode;
                  key "jit-pol";
                  leaf jit-pol {
                    description
                      "Specify this policy's priority; 1 being highest";
                    type uint8 {
                      range "1..9";
                    }
                  }
                  leaf variance {
                    description
                      "Specify range; e.g. 25 means all exits measuring up to 25% worse than the best exit are considered equivalent";
                    type uint8 {
                      range "1..100";
                    }
                  }
                }
              }
            }
            container loss {
              description
                "Specify PfR loss policy resolver settings";
              container priority {
                description
                  "Specify the order in which resolver will consider this policy";
                list loss-pol {
                  tailf:cli-drop-node-name;
                  tailf:cli-suppress-mode;
                  key "loss-pol";
                  leaf loss-pol {
                    description
                      "Specify this policy's priority; 1 being highest";
                    type uint8 {
                      range "1..9";
                    }
                  }
                  leaf variance {
                    description
                      "Specify range; e.g. 25 means all exits measuring up to 25% worse than the best exit are considered equivalent";
                    type uint8 {
                      range "1..100";
                    }
                  }
                }
              }
            }
            container mos {
              description
                "Specify PfR MOS policy resolver settings";
              container priority {
                description
                  "Specify the order in which resolver will consider this policy";
                list mos-pol {
                  tailf:cli-drop-node-name;
                  tailf:cli-suppress-mode;
                  key "mos-pol";
                  leaf mos-pol {
                    description
                      "Specify this policy's priority; 1 being highest";
                    type uint8 {
                      range "1..9";
                    }
                  }
                  leaf variance {
                    description
                      "Specify range; e.g. 25 means all exits measuring up to 25% worse than the best exit are considered equivalent";
                    type uint8 {
                      range "1..100";
                    }
                  }
                }
              }
            }
          }
          container rsvp {
            description
              "Specify rsvp parameters";
            leaf post-dial-delay {
              description
                "RSVP post-dial-delay in msecs";
              type uint16 {
                range "0..500";
              }
            }
            leaf signaling-retries {
              description
                "Number of signaling-retries";
              type uint8 {
                range "0..1";
              }
            }
          }
          leaf shutdown {
            description
              "Disable PfR master controller functionality";
            type empty;
          }
          container target-discovery {
            description
              "Enable/configure Target Discovery";
            presence "true";
            container responder-list {
              description
                "Specify static list of responders";
              list td-num {
                tailf:cli-drop-node-name;
                tailf:cli-suppress-mode;
                key "td-num";
                leaf td-num {
                  description
                    "Prefix-list containing list of responders";
                  type string;
                }
                leaf inside-prefixes {
                  description
                    "Prefix-list containing list of inside prefixes";
                  type string;
                }
              }
            }
          }
          container traceroute {
            description
              "Configure Traceroute global parameters";
            leaf probe-delay {
              description
                "Specify the time between two probes in msec";
              type uint16 {
                range "0..65535";
              }
            }
          }
          leaf trigger-log-percentage {
            description
              "Specify the percentage of out-of-policy TCs that will trigger a syslog";
            type uint8 {
              range "0..100";
            }
          }
          container unreachable {
            description
              "Specify unreachable parameters";
            leaf relative {
              description
                "short/long term in percentage. e.g. 125 is short/long = 1.25";
              type uint16 {
                range "1..1000";
              }
            }
            leaf threshold {
              description
                "Maximum absolute unreachable threshold (flows-per-million)";
              type uint32 {
                range "1..1000000";
              }
            }
          }
        }
      }
    }
    // pfr-map
    list pfr-map {
      description
        "Create pfr-map and enter pfr-map command mode";
      tailf:cli-mode-name "config-pfr-map";
      key "pfr-tg";
      leaf pfr-tg {
        description
          "pfr-map tag";
        type string;
      }
      container pfr-Mode__config-pfr-map {
        tailf:cli-drop-node-name;
        container match {
          description
            "Match values for PfR policy";
          container ip {
            description
              "IP specific information";
            leaf address {
              description
                "Match address";
              type empty;
            }
          }
          container pfr {
            description
              "Match PfR prefixes";
            leaf learn {
              description
                "Match PfR learned prefixes";
              type empty;
            }
          }
          container traffic-class {
            description
              "Specify Traffic class";
            leaf access-list {
              description
                "Specify Traffic class(es) using access-list";
              type empty;
            }
            leaf application {
              description
                "Specify the application to learn";
              type empty;
            }
            leaf prefix-list {
              description
                "Specify Traffic class(es) using prefix-list";
              type empty;
            }
          }
        }
        container set {
          description
            "Set values for PfR policy";
          container active-probe {
            description
              "Manually create an active probe for a known target";
            container echo {
              description
                "Perform ICMP echo probe operations";
              list ipv4-or-hostname {
                tailf:cli-drop-node-name;
                tailf:cli-suppress-mode;
                key "ipv4-or-hostname";
                leaf ipv4-or-hostname {
                  description
                    "IP address of probe target";
                  type inet:host;
                }
                leaf dscp {
                  description
                    "Specify the DSCP value";
                  type empty;
                }
              }
            }
            container jitter {
              description
                "Perform jitter probe operations (requires a responder)";
              list ipv4-or-hostname {
                tailf:cli-drop-node-name;
                tailf:cli-suppress-mode;
                key "ipv4-or-hostname";
                leaf ipv4-or-hostname {
                  description
                    "IP address of probe target";
                  type inet:host;
                }
                leaf target-port {
                  description
                    "Required Target Port for udp-echo or tcp-conn or jitter";
                  type empty;
                }
              }
            }
            container tcp-conn {
              description
                "Perform TCP Connection / Disconnect probe operations";
              list ipv4-or-hostname {
                tailf:cli-drop-node-name;
                tailf:cli-suppress-mode;
                key "ipv4-or-hostname";
                leaf ipv4-or-hostname {
                  description
                    "IP address of probe target";
                  type inet:host;
                }
                leaf target-port {
                  description
                    "Required Target Port for udp-echo or tcp-conn or jitter";
                  type empty;
                }
              }
            }
            container udp-echo {
              description
                "Perform UDP Echo probe operations (requires a responder)";
              list ipv4-or-hostname {
                tailf:cli-drop-node-name;
                tailf:cli-suppress-mode;
                key "ipv4-or-hostname";
                leaf ipv4-or-hostname {
                  description
                    "IP address of probe target";
                  type inet:host;
                }
                leaf target-port {
                  description
                    "Required Target Port for udp-echo or tcp-conn or jitter";
                  type empty;
                }
              }
            }
          }
          container backoff {
            description
              "Specify backoff timer parameters";
            list boff-t {
              tailf:cli-drop-node-name;
              tailf:cli-suppress-mode;
              key "boff-t";
              leaf boff-t {
                description
                  "Specify minimum value of backoff timer (secs)";
                type uint16 {
                  range "90..7200";
                }
              }
              list boff-t0 {
                tailf:cli-drop-node-name;
                tailf:cli-suppress-mode;
                key "boff-t0";
                leaf boff-t0 {
                  description
                    "Specify maximum value of backoff timer (secs)";
                  type uint16 {
                    range "90..7200";
                  }
                }
                leaf boff-rng {
                  description
                    "Specify optional backoff timer step (secs)";
                  tailf:cli-drop-node-name;
                  type uint16 {
                    range "90..7110";
                  }
                }
              }
            }
          }
          container delay {
            description
              "Specify delay parameters";
            leaf relative {
              description
                "Maximum allowable relative change from short to long term";
              type empty;
            }
            leaf threshold {
              description
                "Maximum allowable absolute delay";
              type empty;
            }
          }
          leaf holddown {
            description
              "Specify hold-down timer parameter (secs)";
            type uint16 {
              range "90..65535";
            }
          }
          leaf interface {
            description
              "Set the forwarding interface to Null0";
            type string;
          }
          leaf jitter {
            description
              "Specify jitter parameters";
            type empty;
          }
          container link-group {
            description
              "Specify the link group";
            list lg-name {
              tailf:cli-drop-node-name;
              tailf:cli-suppress-mode;
              key "lg-name";
              leaf lg-name {
                description
                  "Specify primary link group name";
                type string;
              }
              container fallback {
                description
                  "Specify the fallback link group";
                presence "true";
                leaf fall-name {
                  description
                    "Specify Fallback link group name";
                  tailf:cli-drop-node-name;
                  type string;
                }
              }
            }
          }
          container loss {
            description
              "Specify loss parameters";
            leaf relative {
              description
                "short/long term in percentage. e.g. 125 is short/long = 1.25";
              type uint16 {
                range "1..1000";
              }
            }
            leaf threshold {
              description
                "Maximum absolute lost packet threshold in percentage e.g., 1 is 0.0001 percent";
              type uint32 {
                range "1..1000000";
              }
            }
          }
          leaf mode {
            description
              "Specify PfR operating mode settings";
            type empty;
          }
          leaf mos {
            description
              "Specify mos parameters";
            type empty;
          }
          leaf next-hop {
            description
              "Specify the next-hop ip address";
            type empty;
          }
          leaf periodic {
            description
              "Specify periodic rotation timer value";
            type empty;
          }
          leaf probe {
            description
              "Specify active probe parameter";
            type empty;
          }
          leaf resolve {
            description
              "Specify PfR policy resolver settings";
            type empty;
          }
          leaf traceroute {
            description
              "Enable traceroute";
            type empty;
          }
          leaf trap-enable {
            description
              "Enable PfR MIB Traps";
            type empty;
          }
          leaf trigger-log-percentage {
            description
              "Specify the percentage of out-of-policy TCs that will trigger a syslog";
            type empty;
          }
          leaf unreachable {
            description
              "Specify unreachable parameters";
            type empty;
          }
        }
      }
    }

    /// ========================================================================
    ///  ptp
    /// ========================================================================
    container ptp {
      description
        "Precision Time Protocol";
      container clock {
        description
          "Configure PTP clock";
        tailf:cli-add-mode;
        tailf:cli-mode-name "config-ptp-clk";
        container ordinary {
          description
            "Configure PTP Ordinary clock";
          tailf:cli-hide-in-submode;
          tailf:cli-flatten-container;
          leaf domain {
            description
              "PTP domain";
            type int8 {
              range "0..127";
            }
          }
        }
        container clock-port {
          description
            "Configure clock port";
          tailf:cli-add-mode;
          tailf:cli-mode-name "config-ptp-port";
          leaf name {
            description
              "Port name";
            tailf:cli-drop-node-name;
            tailf:cli-incomplete-command;
            tailf:cli-hide-in-submode;
            type string;
          }
          leaf slave {
            description
              "Configure as Slave";
            tailf:cli-hide-in-submode;
            type empty;
          }
          leaf master {
            description
              "Configure as Master";
            tailf:cli-hide-in-submode;
            type empty;
          }
          container transport {
            description
              "Set port transport parameters";
            tailf:cli-compact-syntax;
            tailf:cli-sequence-commands;
            leaf ipv4 {
              description
                "Use IPv4 encapsulation";
              type empty;
            }
            container unicast {
              description
                "Use unicast communication channel";
              tailf:cli-flatten-container;
              tailf:cli-compact-syntax;
              tailf:cli-sequence-commands;
              leaf interface {
                type string;
              }
              leaf negotiation {
                description
                  "Enable unicast negotiation";
                type empty;
              }
            }
          }
          container clock {
            leaf source {
              type inet:ipv4-address;
            }
          }
        }
      }
    }
    
    /// ========================================================================
    /// facility-alarm
    /// ========================================================================
    container facility-alarm {
      description
        "Configure facility alarms";
      tailf:cli-explicit-exit;
      tailf:cli-compact-syntax;
      tailf:cli-sequence-commands;
      leaf severity {
        tailf:cli-drop-node-name;
        tailf:cli-incomplete-command;
        type enumeration {
          enum "critical";
        }
      }
      leaf exceed-action {
        description
          "Behavior on critical threshold exceed";
        type enumeration {
          enum "shutdown";
        }
      }
    }
    

    /// ========================================================================
    /// esmc
    /// ========================================================================
    container esmc {
      description
        "Ethernet Synchronization Messaging Channel";
      tailf:cli-explicit-exit;
      leaf process {
        description
          "process";
        type empty;
      }
    }    


    /// ========================================================================
    /// setup
    /// ========================================================================
    container setup {
      description
        "Configure setup options";
      leaf express {
        description
          "Configure whether express setup mode is enabled";
        tailf:cli-boolean-no;
        tailf:cli-trim-default;
        type boolean;
      }
    }
    
    /// ========================================================================
    /// tod-clock
    /// ========================================================================
    container tod-clock {
      description
        "Tod clock config commands";
      tailf:cli-explicit-exit;
      container input-source {
        description
          "Synchronization Input Source";
        tailf:cli-compact-syntax;
        tailf:cli-sequence-commands;
        leaf priority {
          tailf:cli-drop-node-name;
          type uint8 {
            range "1..250";
          }
        }
        container ptp {
          tailf:cli-flatten-container;
          leaf domain {
            type uint8;
          }
        }
      }
    }
    
    /// ========================================================================
    /// network-clock
    /// ========================================================================
    container network-clock {
      description
        "Network clock config commands";
      tailf:cli-explicit-exit;
      container synchronization {
        description
          "Network clock synchronization selection process";
        leaf automatic {
          description
            "ITU-T G.781/Telcordia standard based";
          type empty;
        }
        leaf mode {
          description
            "synchronization networking mode";
          type enumeration {
            enum "QL-enabled";
          }
        }
      }
      container wait-to-restore {
        description
          "Wait-to-Restore timer";
        tailf:cli-compact-syntax;
        tailf:cli-sequence-commands;
        leaf time {
          description
            "Wait-to-Restore time";
          tailf:cli-drop-node-name;
          type uint32 {
            range "0..86400";
          }
        }
        leaf global {
          description
            "Global";
          type empty;
        }
      }
      container input-source {
        description
          "Synchronization Input Source";
        tailf:cli-compact-syntax;
        tailf:cli-sequence-commands;
        leaf priority {
          tailf:cli-drop-node-name;
          type uint8 {
            range "1..250";
          }
        }
        container interface {
          tailf:cli-optional-in-sequence;
          tailf:cli-flatten-container;
          uses interface-grouping;
        }
        container ptp {
          tailf:cli-optional-in-sequence;
          tailf:cli-flatten-container;
          leaf domain {
            type uint8;
          }
        }
      }
    }
    

    /// ========================================================================
    /// l2vpn
    /// ========================================================================
    container l2vpn {
      description
        "Layer2 VPN commands";
      container pseudowire {
        description
          "Global pseudowire parameters";
        container static-oam {
          description
            "Static PW OAM configuration";
          list class {
            description
              "Static PW OAM class configuration";
            tailf:cli-mode-name "config-st-pw-oam-class";
            key "pw-nm";
            leaf pw-nm {
              type string;
            }
            container timeout {
              description
                "timeout configurations";
              container refresh {
                description
                  "refresh timeout configurations";
                container send {
                  description
                    "refresh send timeout configuration";
                  leaf interval {
                    tailf:cli-drop-node-name;
                    type uint32 {
                      range "1..4095";
                    }
                  }
                }
              }
            }
          }
        }
        container tlv {
          description
            "Global PW TLV configuration";
          list template {
            description
              "PW TLV Template Keyword";
            tailf:cli-mode-name "config-pw-tlv-template";
            key "tlv-nm";
            leaf tlv-nm {
              type string;
            }
            container tlv {
              description
                "TLV config command";
              container tlv-type {
                tailf:cli-drop-node-name;
                leaf type {
                  tailf:cli-drop-node-name;
                  type uint8 {
                    range "1..40";
                  }
                }
              }
              container tlv-description {
                tailf:cli-drop-node-name;
                leaf description {
                  tailf:cli-drop-node-name;
                  type string;
                }
              }
            }
          }
        }
        container group {
          description
            "Configure pseudowire group parameters";
          leaf status {
            description
              "Send pseudowire group status messages";
            type empty;
          }
        }
        leaf routing {
          description
            "Configure l2vpn pseudowire routing";
          type empty;
        }
      }
      container vfi {
        description
          "Configure a Virtual Forwarding Instance (VFI)";
        list context {
          description
            "Layer2 VPN Context";
          tailf:cli-mode-name "config-vfi";
          key "vfi-nm";
          leaf vfi-nm {
            description
              "Virtual Forwarding Instance (VFI) name";
            type string;
          }
          container autodiscovery {
            description
              "Auto Discovery mode";
            container bgp {
              description
                "Use BGP for neighbor discovery";
              container signaling {
                description
                  "Signaling protocol to use";
                container bgp {
                  description
                    "Use BGP signaling and discovery";
                  tailf:cli-add-mode;
                  tailf:cli-mode-name "config-vfi-autodiscovery";
                  presence "true";
                  leaf template {
                    description
                      "Template to be used for autodiscovered pseudowires";
                    tailf:cli-hide-in-submode;
                    type string;
                  }
                }
                container ldp {
                  description
                    "Use LDP signaling";
                  tailf:cli-add-mode;
                  tailf:cli-mode-name "config-vfi-autodiscovery";
                  presence "true";
                  leaf template {
                    description
                      "Template to be used for autodiscovered pseudowires";
                    tailf:cli-hide-in-submode;
                    type string;
                  }
                }
              }
            }
          }
          container vpn {
            description
              "VPN configuration";
            leaf id {
              description
                "VPN id value";
              type uint32 {
                range "1..4294967295";
              }
            }
          }
        }
      }
      container xconnect {
        description
          "Configure a cross connect";
        list context {
          description
            "Layer2 VPN Context";
          tailf:cli-mode-name "config-xconnect";
          key "xc-name";
          leaf xc-name {
            description
              "Configure the cross connect name";
            type string;
          }
          container xc-Mode-config-xconnect {
            tailf:cli-drop-node-name;
            leaf description {
              description
                "Description string";
              tailf:cli-multi-value;
              type string;
            }
            container interworking {
              description
                "Interworking options for the cross connect";
              leaf ethernet {
                description
                  "Ethernet interworking";
                type empty;
              }
              leaf ip {
                description
                  "IP interworking";
                type empty;
              }
              leaf vlan {
                description
                  "VLAN interworking";
                type empty;
              }
            }
            container match {
              description
                "Set Xconnect packet matching criteria";
              container protocol {
                description
                  "Protocol matching criterion";
                leaf ipv6 {
                  description
                    "IPV6";
                  type empty;
                }
              }
            }
            container member {
              description
                "Configure the cross connect member";
              list ipv4 {
                tailf:cli-drop-node-name;
                tailf:cli-suppress-mode;
                key "ipv4";
                leaf ipv4 {
                  description
                    "IP address of the peer";
                  type inet:ipv4-address;
                }
                leaf mem-vcid {
                  description
                    "Enter VC ID value";
                  tailf:cli-drop-node-name;
                  type uint32 {
                    range "1..4294967295";
                  }
                }
              }
              list interface {
                tailf:cli-drop-node-name;
                tailf:cli-suppress-mode;
                key "interface";
                leaf interface {
                  description
                    "GigabitEthernet IEEE 802.3z";
                  type string;
                }
                leaf group {
                  description
                    "Configure the cross connect member redundancy group";
                  type empty;
                }
                leaf service-instance {
                  description
                    "Ethernet Service Instance";
                  type empty;
                }
              }
              leaf Vlan {
                description
                  "Vlan interface number";
                type uint16 {
                  range "1..4094";
                }
              }
            }
            container redundancy {
              description
                "Xconnect redundancy information";
              leaf delay {
                description
                  "Enable delay";
                type uint8 {
                  range "0..180";
                }
              }
              container predictive {
                description
                  "Switch over to backup member without waiting for UP status";
                leaf disabled {
                  description
                    "Disable predictive switchover capability for this xconnect";
                  type empty;
                }
                leaf enabled {
                  description
                    "Enable predictive switchover capability for this xconnect";
                  type empty;
                }
              }
            }
            container remote {
              description
                "L2VPN remote peer configuration commands";
              container circuit {
                description
                  "Remote peer circuit configuration";
                leaf id {
                  description
                    "Remote peer circuit ID";
                  type empty;
                }
              }
              container link {
                description
                  "Link information";
                leaf failure {
                  description
                    "Failure information";
                  type empty;
                }
              }
            }
            leaf shutdown {
              description
                "Shutdown Xconnect";
              type empty;
            }
          }
        }  
      }
    }
    container config-l2vpn {
      tailf:cli-drop-node-name;
      container l2vpn {
        tailf:cli-add-mode;
        tailf:cli-mode-name "config-l2vpn";
        presence "true";
        container logging {
          description
            "Configure logging flags";
          container pseudowire {
            description
              "pseudowire status transition logging";
            leaf status {
              description
                "pseudowire status up/down logging";
              type empty;
            }
          }
          leaf redundancy {
            description
              "xconnect redundancy events";
            type empty;
          }
        }
        container redundancy {
          description
            "Configure L2VPN redundancy parameters";
          container predictive {
            description
              "Switch over to backup member without waiting for UP status";
            leaf enabled {
              description
                "Enable predictive switchover capability for all xconnects";
              type empty;
            }
          }
        }
        leaf router-id {
          description
            "Layer2 router-id value";
          type inet:ipv4-address;
        }
        leaf shutdown {
          description
            "Shutdown Layer2 VPN";
          type empty;
        }
      }
    }
    
    /// ========================================================================
    /// l3vpn
    /// ======================================================================== 
    container l3vpn {
      description
        "l3vpn encapsulation ip commands";
      container encapsulation {
        description
          "l3vpn encapsulation ip";
        list ip {
          description
            "l3vpn encapsulation ip";
          tailf:cli-mode-name "config-l3vpn-encap-ip";
          key "profile-name";
          leaf profile-name {
            type string;
          }
          container transport {
            description
              "transport mode";
            container ipv4 {
              description
                "transport ipv4 mode";
              presence "true";
              leaf source {
                description
                  "transport source";
                type string;
              }
            }
          }
          container protocol {
            description
              "protocol mode";
            container gre {
              description
                "protocol gre";
              presence "true";
              leaf key {
                description
                  "gre key";
                type uint32 {
                  range "0..4294967295";
                }
              }
            }
          }
          container mpls {
            description
              "Configure MPLS interface parameters";
            leaf mtu {
              description
                "Set MPLS Maximum Transmission Unit";
              type union {
                type uint32 {
                  range "64..17916";
                }
                type enumeration {
                  enum "max";
                }
              }
            }
          }
        }
      }
    }

    /// ========================================================================
    /// mpls
    /// ========================================================================
    container mpls {
      description
        "Configure MPLS parameters";
      // mpls atm
      container atm {
        description
          "Configure ATM options";
        leaf disable-headend-vc {
          description
            "Dedicated lsc capability: In this mode headend Tag VCs are disabled.";
          type empty;
        }
      }
      // mpls cos-map
      leaf cos-map {
        description
          "Configure MPLS CoS ATM Multi-VC CoS Map";
        tailf:cli-full-command;
        type uint8 {
          range "1..255";
        }
      }
      // mpls ip
      container ip {
        description
          "Dynamic MPLS forwarding for IP";
        leaf default-route {
          description
            "Allow MPLS forwarding for ip default route";
          tailf:cli-full-command;
          type empty;
        }
        container conf {
          tailf:cli-no-keyword;
          tailf:cli-drop-node-name;
          // mpls ip propagate-tt
          leaf propagate-ttl {
            tailf:cli-boolean-no;
            type boolean;
          }
        }
        container conf-arg {
          tailf:cli-drop-node-name;
          container propagate-ttl {
            tailf:cli-incomplete-command;
            tailf:cli-incomplete-no;
            leaf forwarded {
              tailf:cli-boolean-no;
              tailf:cli-show-with-default;
              type boolean;
            }
          }
        }
        // mpls ip ttl-expiration
        container ttl-expiration {
          description
            "Control MPLS TTL expiration behavior";
          leaf pop {
            description
              "Popping labels on TTL expiration";
            type uint8 {
              range "1..6";
            }
          }
        }
      }
      // mpls label
      container label {
        description
          "Label properties";
        // mpls label atm
        container atm {
          description
            "Configure ATM options";
          leaf disable-headend-vc {
            description
              "Dedicated lsc capability: In this mode headend Tag VCs are disabled.";
            type empty;
          }
        }
        // mpls label protocol
        leaf protocol {
          description
            "Set platform default label distribution protocol";
          tailf:cli-full-command;
          type enumeration {
            enum "ldp" {
              tailf:code-name "label_ldp";
            }
            enum "tdp:" {
              tailf:code-name "label_tdp";
            }
          }
        }
        // mpls label range
        container range {
          description
            "Label range";
          tailf:cli-sequence-commands;
          tailf:cli-compact-syntax;
          leaf min {
            tailf:cli-drop-node-name;
            tailf:cli-incomplete-command;
            type uint32 {
              range "16..1048575";
            }
          }
          leaf max {
            tailf:cli-drop-node-name;
            must ". > ../min" {
              tailf:dependency "../min";
              error-message "Max label value must be > min label value";
            }
            type uint32 {
              range "16..1048575";
            }
          }
          container static {
            description
              "Specify block of labels for static bindings";
            tailf:cli-compact-syntax;
            tailf:cli-sequence-commands;
            tailf:cli-flatten-container;
            leaf min {
              tailf:cli-drop-node-name;
              tailf:cli-incomplete-command;
              type uint32 {
                range "16..1048575";
              }
            }
            leaf max {
              tailf:cli-drop-node-name;
              must ". > ../min" {
                tailf:dependency "../min";
                error-message "Max label value must be > min label value";
              }
              type uint32 {
                range "16..1048575";
              }
            }
          }
        }
      }
      // mpls ldp
      container ldp {
        description
          "Label Distribution Protocol";
        container enable {
          tailf:cli-drop-node-name;
          leaf advertise-labels {
            tailf:cli-boolean-no;
            tailf:cli-trim-default;
            tailf:cli-show-no;
            type boolean;
          }
        }
        container enable2 {
          tailf:cli-drop-node-name;
          container advertise-labels {
            tailf:cli-incomplete-command;
            tailf:cli-incomplete-no;
            description
              "Label advertisements";
            container for {
              description
                "Access-list specifying controls on destination prefixes";
              tailf:cli-sequence-commands;
              tailf:cli-compact-syntax;
              leaf from {
                tailf:cli-drop-node-name;
                type string;
              }
              leaf to {
                description
                  "Access-list specifying controls on LDP peers";
                type string;
              }
            }
            list interface {
              description
                "Advertise /32 interface address";
              tailf:cli-suppress-mode;
              key "name";
              leaf name {
                type string;
              }
            }
            leaf oldstyle {
              description
                "Use old style (TDP) method for matching prefix acl";
              tailf:cli-full-command;
              type empty;
            }
          }
        }
        container atm {
          description
            "Configure ATM MPLS options";
          leaf control-mode {
            description
              "Select LSP setup control mode for MPLS VCs";
            tailf:cli-full-command;
            type enumeration {
              enum "independent";
              enum "ordered";
            }
            tailf:cli-trim-default;
          }
          leaf vc-merge {
            description
              "Select VC merge capability";
            tailf:cli-full-command;
            tailf:cli-boolean-no;
            tailf:cli-trim-default;
            type boolean;
          }
        }
        container backoff {
          description
            "Set LDP session backoff parameters";
          tailf:cli-sequence-commands;
          tailf:cli-compact-syntax;
          leaf initial {
            tailf:cli-drop-node-name;
            tailf:cli-incomplete-command;
            type uint32 {
              range "5..2147483";
            }
          }
          leaf max {
            tailf:cli-drop-node-name;
            type uint32 {
              range "5..2147483";
            }
          }
        }
        container discovery {
          description
            "LDP discovery";
          container hello {
            description
              "LDP discovery Hello";
            leaf holdtime {
              description
                "LDP discovery Hello holdtime";
              type uint16 {
                range "1..65535";
              }
            }
            leaf interval {
              description
                "LDP discovery Hello interval";
              tailf:cli-full-command;
              type uint16 {
                range "1..65535";
              }
            }
          }
          container targeted-hello {
            description
              "LDP discovery Targeted Hello";
            container accept {
              description
                "Accept targeted hellos";
              presence "Accept targeted hellos";
              leaf from {
                description
                  "Access list to specify acceptable targeted hello sources";
                type string;
              }
            }
            leaf holdtime {
              description
                "LDP discovery Hello holdtime";
              type uint16 {
                range "1..65535";
              }
            }
            leaf interval {
              description
                "LDP discovery Hello interval";
              tailf:cli-full-command;
              type uint16 {
                range "1..65535";
              }
            }
          }
        }
        container explicit-null {
          description
            "Advertise Explicit Null label in place of Implicit Null";
          presence "Advertise Explicit Null label in place of Implicit Null";
          leaf for {
            description
              "Access-list specifying controls on destination prefixes";
            type string;
          }
          leaf to {
            description
              "Access-list specifying controls on LDP peers";
            type string;
          }
        }
        container graceful-restart {
          description
            "Configure Graceful Restart timers";
          presence "Configure Graceful Restart timers";
          container timers {
            description
              "Configure Graceful Restart timers";
            leaf forwarding-holding {
              description
                "Forwarding State Holding time";
              tailf:cli-full-command;
              type uint16 {
                range "30..600";
              }
            }
            leaf max-recovery {
              description
                "Max-Recovery time";
              tailf:cli-full-command;
              type uint16 {
                range "15..600";
              }
            }
            leaf neighbor-liveness {
              description
                "Neighbor-Liveness time";
              tailf:cli-full-command;
              type uint16 {
                range "5..600";
              }
            }
          }
        }
        leaf holdtime {
          description
            "LDP session holdtime";
          tailf:cli-full-command;
          type uint32 {
            range "15..2147483";
          }
        }
        container logging {
          description
            "Enable LDP logging";
          leaf neighbor-changes {
            description
              "Log LDP neighbor state changes";
            type empty;
          }
        }
        leaf loop-detection {
          description
            "Enable LDP Loop Detection";
          tailf:cli-full-command;
          type empty;
        }
        leaf maxhops {
          description
            "Limit hop count for LDP LSP setup";
          tailf:cli-full-command;
          type uint8 {
            range "0..255";
          }
        }
        list neighbor {
          description
            "Configure neighbor parameters";
          tailf:cli-suppress-mode;
          tailf:cli-delete-when-empty;
          key "address";
          leaf address {
            type inet:ipv4-address;
          }
          leaf implicit-withdraw {
            description
              "Enable LDP Implicit Withdraw Label";
            tailf:cli-full-command;
            type empty;
          }
          container labels {
            description
              "Configure label binding exchange controls";
            leaf accept {
              description
                "Specify label bindings to accept";
              type string;
            }
          }
          container password {
            description
              "Set a password";
            tailf:cli-compact-syntax;
            leaf enctype {
              tailf:cli-drop-node-name;
              tailf:cli-incomplete-command;
              tailf:cli-reset-container;
              type uint8 {
                range "0..7";
              }
            }
            leaf text {
              tailf:cli-drop-node-name;
              tailf:cli-full-command;
              tailf:cli-multi-value;
              tailf:cli-reset-container;
              type string {
                pattern "[a-zA-Z].*";
              }
            }
          }
          container targeted {
            description
              "Establish targeted session";
            presence "Establish targeted session";
            leaf protocol {
              tailf:cli-drop-node-name;
              type enumeration {
                enum "ldp" {
                  tailf:code-name "target_ldp";
                }
                enum "tdp" {
                  tailf:code-name "target_tdp";
                }
              }
            }
          }
        }
        container request-labels {
          description
            "Access list to specify valid downstream on demand destinations.";
          leaf for {
            description
              "Access list to specify acceptable downstream on demand destinations";
            type string;
          }
        }
        container router-id {
          description
            "Select interface to prefer for LDP identifier address";
          tailf:cli-sequence-commands {
            tailf:cli-reset-siblings;
          }
          tailf:cli-compact-syntax;
          leaf interface {
            tailf:cli-drop-node-name;
            type string;
          }
          leaf force {
            description
              "Forcibly change the LDP router id";
            type empty;
          }
        }
        container tcp {
          description
            "Set TCP parameters for LDP";
          leaf pak-priority {
            description
              "Set (local) priority for LDP session TCP connection";
            type empty;
          }
        }
      }
      // mpls prefix-map
      container prefix-map {
        description
          "Configure MPLS CoS Tag-VC Multi-VC Prefix Map";
        tailf:cli-sequence-commands;
        tailf:cli-compact-syntax;
        leaf nr {
          tailf:cli-drop-node-name;
          tailf:cli-incomplete-command;
          type uint8 {
            range "1..255";
          }
        }
        leaf access-list {
          description
            "Configure access-list for this prefix-map";
          tailf:cli-incomplete-command;
          type uint8 {
            range "1..255";
          }
        }
        leaf cos-map {
          description
            "Configure cos-map for this prefix-map";
          type uint8 {
            range "1..255";
          }
        }
      }
      //mpls static
      container static {
        description
          "MPLS static application";
        presence "true";
        container binding {
          description
            "Establish static label bindings";
          tailf:cli-sequence-commands {
            tailf:cli-reset-all-siblings;
          }
          tailf:cli-compact-syntax;
          container ipv4 {
            description
              "Bind IPv4 destination with label";
            tailf:cli-flatten-container;
            tailf:cli-incomplete-command;
            tailf:cli-compact-syntax;
            list global {
              tailf:cli-drop-node-name;
              tailf:cli-incomplete-command;
              tailf:cli-suppress-mode;
              key "address mask";
              leaf address {
                tailf:cli-incomplete-command;
                type inet:ipv4-address;
              }
              leaf mask {
                tailf:cli-incomplete-command;
                type inet:ipv4-address;
              }
              uses mpls-static-binding-ipv4-grouping;
            }
            list vrf {
              tailf:cli-suppress-mode;
              tailf:cli-incomplete-command;
              tailf:cli-diff-dependency "/ios:native/ip/vrf";
              tailf:cli-diff-dependency "/ios:native/vrf/definition";
              key "name address mask";
              leaf name {
                type string;
              }
              leaf address {
                tailf:cli-drop-node-name;
                tailf:cli-incomplete-command;
                type inet:ipv4-address;
              }
              leaf mask {
                tailf:cli-drop-node-name;
                tailf:cli-incomplete-command;
                type inet:ipv4-address;
              }
              uses mpls-static-binding-ipv4-grouping;
            }
          }
        }
      }
      // mpls traffic-eng
      container traffic-eng {
        description
          "Configure Traffic Engineering parameters";
        container auto-bw {
          description
            "auto-bw parameters";
          container timers {
            description
              "Enable auto-bw Timers Collection and Application";
            presence "Enable auto-bw Timers Collection and Application";
            leaf frequency {
              description
                "Interval between auto-bw data collection";
              type uint32 {
                range "1..604800";
              }
            }
          }
        }
        container auto-tunnel {
          description
            "Configure automatic TE tunnels";
          container backup {
            description
              "Configure auto-tunnel backup tunnel";
            presence "true";
            container config {
              description
                "Config commands to apply to all backup auto-tunnels";
              container affinity {
                description
                  "desired link attributes for links comprising tunnel";
                list aff-val {
                  tailf:cli-drop-node-name;
                  tailf:cli-suppress-mode;
                  key "aff-val";
                  leaf aff-val {
                    description
                      "<0x0-0xFFFFFFFF>;;affinity value";
                    type string;
                  }
                  leaf mask {
                    description
                      "mask on desired link attributes";
                    type string;
                  }
                }
              }
              container unnumbered-interface {
                description
                  "Configure the interface to use for unnumbered";
                leaf interface {
                  description
                    "Virtual ACR interface";
                  tailf:cli-drop-node-name;
                  type string;
                }
                leaf controller {
                  description
                    "Telecom-Bus Clock Controller";
                  tailf:cli-drop-node-name;
                  type string;
                }
                leaf Tunnel {
                  description
                    "Tunnel interface number";
                  type uint32 {
                    range "0..2147483647";
                  }
                }
                leaf Tunnel-tp {
                  description
                    "Tunnel-tp interface number";
                  type uint16 {
                    range "0..65535";
                  }
                }
                leaf VPN {
                  description
                    "VPN interface number";
                  type uint32 {
                    range "0..2147483647";
                  }
                }
                leaf VirtualPortGroup {
                  description
                    "VirtualPortGroup interface number";
                  type uint8 {
                    range "0..31";
                  }
                }
                leaf Vlan {
                  description
                    "Vlan interface number";
                  type uint16 {
                    range "1..4094";
                  }
                }
                leaf vasileft {
                  description
                    "vasileft interface number";
                  type uint16 {
                    range "1..2000";
                  }
                }
                leaf vasiright {
                  description
                    "vasiright interface number";
                  type uint16 {
                    range "1..2000";
                  }
                }
              }
            }
            leaf nhop-only {
              description
                "Automatically create n-hop backup tunnels only";
              type empty;
            }
            container srlg {
              description
                "Shared Risk Link Groups influence backup tunnel path selection";
              container exclude {
                description
                  "Backup tunnels avoid SRLGs of protected interfaces";
                leaf force {
                  description
                    "Backup tunnels MUST not use SRLGs of protected interfaces";
                  type empty;
                }
                leaf preferred {
                  description
                    "Backup tunnels try to avoid using SRLGs of protected interfaces";
                  type empty;
                }
              }
            }
            container timers {
              description
                "Configure timers for backup auto-tunnels";
              container removal {
                description
                  "Configure timer for removal of backup tunnel";
                leaf unused {
                  description
                    "seconds between scanning to remove not in use tunnels";
                  type uint32 {
                    range "0..604800";
                  }
                }
              }
            }
            container tunnel-num {
              description
                "Configure tunnel I/F numbers for backup auto-tunnels";
              container min {
                description
                  "Configure the starting id-range";
                list tnr-range {
                  tailf:cli-drop-node-name;
                  tailf:cli-suppress-mode;
                  key "tnr-range";
                  leaf tnr-range {
                    description
                      "starting tunnel number range";
                    type uint16 {
                      range "0..65535";
                    }
                  }
                  leaf max {
                    description
                      "Configure the ending id-range";
                    type empty;
                  }
                }
              }
            }
          }
          container mesh {
            description
              "Automatically create mesh tunnels";
            presence "true";
            container tunnel-num {
              description
                "Configure tunnel I/F numbers for mesh auto-tunnels";
              container min {
                description
                  "Configure the starting id-range";
                list mesh-range {
                  tailf:cli-drop-node-name;
                  tailf:cli-suppress-mode;
                  key "mesh-range";
                  leaf mesh-range {
                    description
                      "starting tunnel number range";
                    type uint16 {
                      range "0..65535";
                    }
                  }
                  leaf max {
                    description
                      "Configure the ending id-range";
                    type empty;
                  }
                }
              }
            }
          }
          container primary {
            description
              "Automatically create one-hop primary tunnels";
            container config {
              description
                "Config commands to apply to all primary auto-tunnels";
              container mpls {
                description
                  "Configure dynamic MPLS forwarding";
                leaf ip {
                  description
                    "Configure dynamic MPLS forwarding for ip";
                  type empty;
                }
              }
              container unnumbered-interface {
                description
                  "Configure the interface to use for unnumbered";
                leaf interface {
                  description
                    "Virtual ACR interface";
                  tailf:cli-drop-node-name;
                  type string;
                }
                leaf controller {
                  description
                    "Telecom-Bus Clock Controller";
                  tailf:cli-drop-node-name;
                  type string;
                }
                leaf Tunnel {
                  description
                    "Tunnel interface number";
                  type uint32 {
                    range "0..2147483647";
                  }
                }
                leaf Tunnel-tp {
                  description
                    "Tunnel-tp interface number";
                  type uint16 {
                    range "0..65535";
                  }
                }
                leaf VPN {
                  description
                    "VPN interface number";
                  type uint32 {
                    range "0..2147483647";
                  }
                }
                leaf VirtualPortGroup {
                  description
                    "VirtualPortGroup interface number";
                  type uint8 {
                    range "0..31";
                  }
                }
                leaf Vlan {
                  description
                    "Vlan interface number";
                  type uint16 {
                    range "1..4094";
                  }
                }
                leaf vasileft {
                  description
                    "vasileft interface number";
                  type uint16 {
                    range "1..2000";
                  }
                }
                leaf vasiright {
                  description
                    "vasiright interface number";
                  type uint16 {
                    range "1..2000";
                  }
                }
              }
            }
            leaf onehop {
              description
                "Automatically create tunnel to all next-hops";
              type empty;
            }
            container timers {
              description
                "Configure timers for primary auto-tunnels";
              container removal {
                description
                  "Configure removal of primary tunnels";
                leaf rerouted {
                  description
                    "seconds how long auto-tunnel primary can stay frr active";
                  type uint32 {
                    range "30..604800";
                  }
                }
              }
            }
            container tunnel-num {
              description
                "Configure tunnel I/F numbers for primary auto-tunnels";
              container min {
                description
                  "Configure the starting id-range";
                list tnr-range {
                  tailf:cli-drop-node-name;
                  tailf:cli-suppress-mode;
                  key "tnr-range";
                  leaf tnr-range {
                    description
                      "starting tunnel number range";
                    type uint16 {
                      range "0..65535";
                    }
                  }
                  leaf max {
                    description
                      "Configure the ending id-range";
                    type empty;
                  }
                }
              }
            }
          }
        }
        container ds-te {
          description
            "Configure standard DS-TE parameters";
          container bc-model {
            description
              "Configure BC model";
            leaf mam {
              description
                "BC Maximum allocation model";
              type empty;
            }
          }
          container mode {
            description
              "Configure DS-TE migration mode";
            leaf ietf {
              description
                "Configure DS-TE standard mode";
              type empty;
            }
            leaf migration {
              description
                "Configure DS-TE migration mode";
              type empty;
            }
          }
          container te-classes {
            description
              "Specify TE-Class parameters";
            tailf:cli-add-mode;
            tailf:cli-mode-name "config-te-class";
            presence "true";
            container te-Mode__config-te-class {
              tailf:cli-drop-node-name;
              leaf list {
                description
                  "Re-list all the TE-Classes";
                type empty;
              }
              container te-class {
                description
                  "Configure a TE-Class";
                list te-idx {
                  tailf:cli-drop-node-name;
                  tailf:cli-suppress-mode;
                  key "te-idx";
                  leaf te-idx {
                    description
                      "Specify the TE-Class index";
                    type uint8 {
                      range "0..7";
                    }
                  }
                  leaf class-type {
                    description
                      "Specify Class-Type value (0 for Global and 1 for Sub-Pool)";
                    type uint8 {
                      range "0..1";
                    }
                  }
                  leaf unused {
                    description
                      "Specify that this TE-Class index is unused";
                    type empty;
                  }
                }
              }
            }
          }
        }
        container fast-reroute {
          description
            "fast-reroute parameters";
          container backup-prot-preempt {
            description
              "Preemption algorithm for backup tunnels";
            leaf optimize-bw {
              description
                "Reduce bandwidth wastage (default: minimize LSPs preempted)";
              type empty;
            }
          }
          container timers {
            description
              "configure fast-reroute timer";
            leaf promotion {
              description
                "seconds between promotions (0 disables promotion.)";
              type uint32 {
                range "0..604800";
              }
            }
          }
        }
        container link-management {
          description
            "Link Management configuration";
          container timers {
            description
              "Link Management timers configuration";
            leaf bandwidth-hold {
              description
                "Link Management bandwidth hold timer";
              tailf:cli-full-command;
              type uint16 {
                range "1..300";
              }
            }
            leaf periodic-flooding {
              description
                "Link Management periodic flooding interval";
              tailf:cli-full-command;
              type uint16 {
                range "0..3600";
              }
            }
          }
        }
        container logging {
          description
            "Trap logging configuration";
          container lsp {
            description
              "LSP-specific traps logging configuration";
            container path-errors {
              description
                "Log LSP Path Error traps";
              presence "Log LSP Path Error traps";
              leaf access-list {
                tailf:cli-drop-node-name;
                type access-list-type;
              }
            }
            container preemption {
              description
                "Log LSP Preemption traps";
              presence "Log LSP Preemption traps";
              leaf access-list {
                tailf:cli-drop-node-name;
                type access-list-type;
              }
            }
            container reservation-errors {
              description
                "Log LSP Reservation Error traps";
              presence "Log LSP Reservation Error traps";
              leaf access-list {
                tailf:cli-drop-node-name;
                type access-list-type;
              }
            }
            container setups {
              description
                "Log LSP Establishment Traps";
              presence "Log LSP Establishment Traps";
              leaf access-list {
                tailf:cli-drop-node-name;
                type access-list-type;
              }
            }
            container teardowns {
              description
                "Log LSP Teardown Traps";
              presence "Log LSP Teardown Traps";
              leaf access-list {
                tailf:cli-drop-node-name;
                type access-list-type;
              }
            }
          }
          container tunnel {
            description
              "Tunnel-specific traps logging configuration";
            container lsp-selection {
              description
                "Log Tunnel LSP Selection traps";
              presence "Log Tunnel LSP Selection traps";
              leaf access-list {
                tailf:cli-drop-node-name;
                type access-list-type;
              }
            }
            container path {
              description
                "Log Tunnel Path-related traps";
              container change {
                description
                  "Log Tunnel Path change traps";
                presence "Log Tunnel Path change traps";
                leaf access-list {
                  tailf:cli-drop-node-name;
                  type access-list-type;
                }
              }
            }
          }
        }
        container lsp {
          description
            "Configure LSP parameters";
          list attributes {
            description
              "Configure LSP attributes";
            tailf:cli-mode-name "config-lsp-attr";
            key "lsp-att";
            leaf lsp-att {
              description
                "Name of LSP attribute list";
              type string;
            }
            container flag-Mode__config-lsp-attr {
              tailf:cli-drop-node-name;
              container affinity {
                description
                  "Specify attribute flags for links comprising LSP";
                list fl-val {
                  tailf:cli-drop-node-name;
                  tailf:cli-suppress-mode;
                  key "fl-val";
                  leaf fl-val {
                    description
                      "<0x0-0xFFFFFFFF>;;affinity value";
                    type string;
                  }
                  leaf mask {
                    description
                      "mask on desired link attributes";
                    type empty;
                  }
                }
              }
              container auto-bw {
                description
                  "Specify automatic bandwidth configuration";
                presence "true";
                leaf adjustment-threshold {
                  description
                    "Percent bandwidth change to trigger adjustment";
                  type uint8 {
                    range "1..99";
                  }
                }
                leaf collect-bw {
                  description
                    "Just collect bandwidth info";
                  type empty;
                }
                leaf frequency {
                  description
                    "seconds between applying auto-bw";
                  type uint32 {
                    range "300..604800";
                  }
                }
                leaf max-bw {
                  description
                    "Maximum bandwidth to apply (kbps)";
                  type uint32 {
                    range "0..4294967295";
                  }
                }
                leaf min-bw {
                  description
                    "Minimum bandwidth to apply (kbps)";
                  type uint32 {
                    range "0..4294967295";
                  }
                }
                leaf overflow-limit {
                  description
                    "Number of consecutive samples exceeding threshold";
                  type uint8 {
                    range "1..10";
                  }
                }
              }
              container bandwidth {
                description
                  "Specify LSP bandwidth";
                leaf bnd-kbp {
                  description
                    "bandwidth requirement in kbps";
                  tailf:cli-drop-node-name;
                  type uint32 {
                    range "0..4294967295";
                  }
                }
                leaf sub-pool {
                  description
                    "bandwidth requirement in kbps";
                  type uint32 {
                    range "1..4294967295";
                  }
                }
              }
              leaf list {
                description
                  "Re-list all of the attribute list entries";
                type empty;
              }
              leaf lockdown {
                description
                  "Lockdown the LSP--disable reoptimization";
                type empty;
              }
              container priority {
                description
                  "Specify LSP priority";
                list lss-pri {
                  tailf:cli-drop-node-name;
                  tailf:cli-suppress-mode;
                  key "lss-pri";
                  leaf lss-pri {
                    description
                      "setup priority";
                    type uint8 {
                      range "0..7";
                    }
                  }
                  leaf lss-pri0 {
                    description
                      "hold priority";
                    tailf:cli-drop-node-name;
                    type uint8 {
                      range "0..7";
                    }
                  }
                }
              }
              container protection {
                description
                  "Enable failure protection";
                presence "true";
                container fast-reroute {
                  description
                    "Enable fast-reroute failure protection";
                  presence "true";
                  leaf bw-protect {
                    description
                      "Enable BW protection";
                    type empty;
                  }
                }
              }
              leaf record-route {
                description
                  "Record the route used by the LSP";
                type empty;
              }
            }
          }
        }
        leaf nsr {
          description
            "TE NSR configuration";
          type empty;
        }
        container path-option {
          description
            "Configure path-option";
          container list {
            description
              "Configure path-option list";
            list identifier {
              description
                "Specify path-option list by number";
              tailf:cli-mode-name "cfg-pathoption-list";
              key "po-num";
              leaf po-num {
                description
                  "Enter number";
                type uint16 {
                  range "1..65535";
                }
              }
            }
            list name {
              description
                "Specify path-option list by name";
              tailf:cli-mode-name "cfg-pathoption-list";
              key "spo-name";
              leaf spo-name {
                description
                  "Enter name";
                type string;
              }
            }
          }
        }
        container path-selection {
          description
            "Path Selection Configuration";
          uses mpls-te-path-selection-common;
          container overload {
            description
              "Overload Node Configuration";
            container allow {
              description
                "Allow overloaded nodes in CSPFs";
              tailf:cli-sequence-commands;
	      tailf:cli-compact-syntax;
              leaf head {
                description
                  "Allow overloaded head node in TE CSPF";
                tailf:cli-optional-in-sequence;
                tailf:cli-reset-container;
                type empty;
              }
              leaf middle {
                description
                  "Allow overloaded middle node in TE CSPF";
                tailf:cli-optional-in-sequence;
                tailf:cli-reset-container;
                type empty;
              }
              leaf tail {
                description
                  "Allow overloaded middle node in TE CSPF";
                tailf:cli-optional-in-sequence;
                tailf:cli-reset-container;
                type empty;
              }
            }
          }
        }
        container reoptimize {
          description
            "Reoptimization parameters";
          container events {
            description
              "Reoptimization triggers";
            leaf link-up {
              description
                "Reoptimize tunnels on link up events";
              type empty;
            }
          }
          container timers {
            description
              "Reoptimization timers";
            container delay {
              description
                "Delay reoptimization action";
              leaf cleanup {
                description
                  "Delay cleanup of reoptimized LSP";
                tailf:cli-full-command;
                type uint8 {
                  range "0..60";
                }
              }
              leaf installation {
                description
                  "Delay replacement of current LSP by reoptimized LSP";
                tailf:cli-full-command;
                type uint16 {
                  range "0..3600";
                }
              }
            }
            leaf frequency {
              description
                "Interval between reoptimization scans";
              tailf:cli-full-command;
              type uint32 {
                range "0..604800";
              }
            }
          }
        }
        container signalling {
          description
            "Traffic Engineering Signalling Parameters";
          container advertise {
            description
              "Signalling advertisement parameters";
            container implicit-null {
              description
                "Use MPLS encoding for Implicit-Null Label in signalling messages";
              presence "Use MPLS encoding for Implicit-Null Label in signalling messages";
              leaf nr {
                tailf:cli-drop-node-name;
                type uint8 {
                  range "1..99";
                }
              }
            }
          }
          container forwarding {
            description
              "Control interaction of LSP signalling and LFIB maintenance";
            leaf sync {
              description
                "Program linecard LFIBs before signalling LSP label upstream";
              type empty;
            }
          }
          container restart {
            description
              "Signalling restart parameters";
            container neighbors {
              description
                "Identify signalling restart capable neighbors";
              presence "Identify signalling restart capable neighbors";
              leaf nr {
                tailf:cli-drop-node-name;
                type uint8 {
                  range "1..99";
                }
              }
            }
          }
        }
        container topology {
          description
            "Topology Database Configuration";
          container holddown {
            description
              "Topology Database hold down timers";
            leaf sigerr {
              description
                "Link hold down time for signalling errors";
              type uint16 {
                range "0..300";
              }
            }
          }
        }
        container trace {
          description
            "Trace configuration";
          container buffer-size {
            description
              "Trace buffer size configuration";
            leaf error {
              description
                "trace error buffer size in kB (default 32kB)";
              type uint16 {
                range "1..500";
              }
            }
            leaf event {
              description
                "trace event buffer size in kB (default 1% of system memory)";
              type uint16 {
                range "1..2500";
              }
            }
            leaf warning {
              description
                "trace warning buffer size in kB (default 32kB)";
              type uint8 {
                range "1..250";
              }
            }
          }
        }
        leaf tunnels {
          description
            "Traffic Engineering tunnels";
          tailf:cli-full-command;
          type empty;
        }
      }
      container tp {
        description
          "Configure MPLS Transport Profile parameters";
        presence "true";
      }
    }


    /// ========================================================================
    /// router
    /// ========================================================================
    container router {
      description
        "Enable a routing process";

      // router bgp *
      list bgp {
        description
          "Border Gateway Protocol (BGP)";
        tailf:cli-mode-name "config-router";
        tailf:cli-diff-dependency "/ios:native/vrf/definition";
        tailf:cli-diff-dependency "/ios:native/ip/vrf";
        key "id";
        max-elements "1";
        leaf id {
          tailf:cli-suppress-range;
          type bgp-as-number-type;
        }
        uses bgp-address-family-grouping;
        // router bgp * / address-family
        container address-family {
          description
            "Enter Address Family command mode";
          // router bgp * / address-family ipv4 vrf
          container with-vrf {
            tailf:cli-drop-node-name;
            list ipv4 {
              description
                "Address family";
              tailf:cli-suppress-mode;
              tailf:cli-delete-when-empty;
              tailf:cli-incomplete-command;
              key "af-name";
              leaf af-name {
                type bgp_ipv4_af_type;
                tailf:key-default "unicast";
              }
              // router bgp * / address-family ipv4 vrf *
              list vrf {
                tailf:cli-mode-name "config-router-af";
                tailf:cli-full-command;
                tailf:cli-diff-dependency "/ios:native/ip/vrf";
                tailf:cli-diff-dependency "/ios:native/vrf/definition";
                tailf:cli-exit-command "exit-address-family";
                key "name";
                leaf name {
                  type string;
                }
                uses bgp-address-family-grouping;
              }
            }
            // router bgp * / address-family ipv6
            list ipv6 {
              description
                "Address family";
              tailf:cli-suppress-mode;
              tailf:cli-delete-when-empty;
              tailf:cli-incomplete-command;
              tailf:cli-exit-command "exit-address-family";
              key "af-name";
              leaf af-name {
                type bgp_ipv6_af_type;
                tailf:key-default "unicast";
              }
              list vrf {
                tailf:cli-full-command;
                tailf:cli-diff-dependency "/ios:native/vrf/definition";
                tailf:cli-exit-command "exit-address-family";
                key "name";
                leaf name {
                  type string;
                }
                uses bgp-address-family-grouping;
              }
            }
          }
          container no-vrf {
            tailf:cli-drop-node-name;
            list ipv4 {
              description
                "Address family";
              tailf:cli-full-command;
              tailf:cli-delete-when-empty;
              tailf:cli-exit-command "exit-address-family";
              key "af-name";
              leaf af-name {
                type bgp_ipv4_af_type;
                tailf:key-default "unicast";
              }
              uses bgp-address-family-grouping;
            }
            list ipv6 {
              description
                "Address family";
              tailf:cli-delete-when-empty;
              tailf:cli-full-command;
              tailf:cli-exit-command "exit-address-family";
              key "af-name";
              leaf af-name {
                type bgp_ipv6_af_type;
                tailf:key-default "unicast";
              }
              uses bgp-address-family-grouping;
            }
            // router bgp * / address-family vpnv4
            list vpnv4 {
              description
                "Address family";
              tailf:cli-exit-command "exit-address-family";
              key "af-name";
              leaf af-name {
                type enumeration {
                  enum "unicast" {
                    tailf:code-name "bgp_af_vpnv4_unicast";
                  }
                  enum "multicast" {
                    tailf:code-name "bgp_af_vpnv4_multicast";
                  }
                  enum "flowspec" {
                    tailf:code-name "bgp_af_vpnv4_flowspec";
                  }
                }
                tailf:key-default "unicast";
              }
              uses bgp-address-family-grouping;
            }
            // router bgp * / address-family vpnv6
            list vpnv6 {
              description
                "Address family";
              tailf:cli-exit-command "exit-address-family";
              key "af-name";
              leaf af-name {
                type enumeration {
                  enum "unicast" {
                    tailf:code-name "bgp_af_vpnv6_unicast";
                  }
                  enum "multicast" {
                    tailf:code-name "bgp_af_vpnv6_multicast";
                  }
                  enum "flowspec" {
                    tailf:code-name "bgp_af_vpnv6_flowspec";
                  }
                }
                tailf:key-default "unicast";
              }
              uses bgp-address-family-grouping;
            }
            // router bgp * / address-family nsap
            list nsap {
              description
                "Address family";
              tailf:cli-exit-command "exit-address-family";
              key "af-name";
              leaf af-name {
                type enumeration {
                  enum "unicast" {
                    tailf:code-name "nsap_unicast";
                  }
                }
                tailf:key-default "unicast";
              }
              uses bgp-address-family-grouping;
            }
            // router bgp * / address-family l2vpn 
            list l2vpn {
              description
                "Address family";
              tailf:cli-exit-command "exit-address-family";
              key "af-name";
              leaf af-name {
                type enumeration {
                  enum "evpn" {
                    tailf:code-name "bgp_af_l2vpn_evpn";
                  }
                  enum "vpls" {
                    tailf:code-name "bgp_af_l2vpn_vpls";
                  }
                }
                tailf:key-default "evpn";
              }
              uses bgp-address-family-grouping;
            }
            // router bgp * / address-family rtfilter
            list rtfilter {
              description
                "Address family";
              tailf:cli-exit-command "exit-address-family";
              key "af-name";
              leaf af-name {
                type enumeration {
                  enum "unicast" {
                    tailf:code-name "rtfilter_unicast";
                  }
                }
                tailf:key-default "unicast";
              }
              uses bgp-address-family-grouping;
            }
          }
        }
        // router bgp * / template
        container template {
          description
            "Enter template command mode";
          list peer-policy {
            description
              "Template configuration for policy parameters";
            tailf:cli-mode-name "config-router-ptmp";
            tailf:cli-exit-command "exit-peer-policy";
            key "name";
            leaf name {
              type string;
            }
            list route-map {
              description
                "Apply route map to neighbor";
              tailf:cli-suppress-mode;
              key "name";
              leaf name {
                type string;
              }
              leaf in {
                description
                  "Apply map to incoming routes";
                type empty;
              }
              leaf out {
                description
                  "Apply map to outgong routes";
                type empty;
              }
            }
          }
          list peer-session {
            description
              "Template configuration for session parameters";
            tailf:cli-exit-command "exit-peer-session";
            key "name";
            leaf name {
              type string;
            }
          }
        }
        // router bgp * / timers
        container timers {
          description
            "Adjust routing timers";
          container bgp {
            description
              "BGP timers";
            tailf:cli-compact-syntax;
            tailf:cli-sequence-commands {
              tailf:cli-reset-siblings;
            }
            leaf keepalive-interval {
              tailf:cli-drop-node-name;
              type uint16 {
                range "0..65535";
              }
            }
            leaf holdtime {
              tailf:cli-drop-node-name;
              type uint16 {
                range "0..65535";
              }
            }
            leaf minimum-neighbor-hold {
              tailf:cli-drop-node-name;
              tailf:cli-optional-in-sequence;
              type uint16 {
                range "0..65535";
              }
            }
          }
        }
      }
      // router ospfv3 *
      list ospfv3 {
        tailf:cli-mode-name "config-router";
        description
          "OSPFv3";
        key "id";
        leaf id {
          tailf:cli-suppress-range;
          type uint16 {
            range "1..65535";
          }
        }
        uses ospf-ospfv3-common-grouping;
        uses ospfv3-grouping;
        // router ospfv3 * / address-family
        container address-family {
          description
            "Enter Address Family command mode";
          container ipv4 {
            description
              "IPv4 Address family";
            container unicast {
              description
                "Address Family Modifier";
              tailf:cli-add-mode;
              tailf:cli-mode-name "config-router-af";
              tailf:cli-exit-command "exit-address-family";
              presence "true";
              uses ospf-ospfv3-common-grouping;
              uses ospf-ospfv3-common-address-family-grouping;
              uses ospfv3-address-family-grouping;
            }
            list vrf {
              description
                "Specify parameters for a VPN Routing/Forwarding instance";
              tailf:cli-diff-dependency "/ios:native/ip/vrf";
              tailf:cli-diff-dependency "/ios:native/vrf/definition";
              tailf:cli-mode-name "config-router-af";
              tailf:cli-exit-command "exit-address-family";
              key "name";
              leaf name {
                type string;
              }
              uses ospf-ospfv3-common-grouping;
              uses ospf-ospfv3-common-address-family-grouping;
              uses ospfv3-address-family-grouping;
            }
          }
          container ipv6 {
            description
              "IPv6 Address family";
            container unicast {
              tailf:cli-add-mode;
              tailf:cli-mode-name "config-router-af";
              tailf:cli-exit-command "exit-address-family";
              presence "true";
              uses ospf-ospfv3-common-grouping;
              uses ospf-ospfv3-common-address-family-grouping;
              uses ospfv3-address-family-grouping;
            }
            list vrf {
              description
                "Specify parameters for a VPN Routing/Forwarding instance";
              tailf:cli-diff-dependency "/ios:native/ip/vrf";
              tailf:cli-diff-dependency "/ios:native/vrf/definition";
              tailf:cli-mode-name "config-router-af";
              tailf:cli-exit-command "exit-address-family";
              key "name";
              leaf name {
                type string;
              }
              uses ospf-ospfv3-common-grouping;
              uses ospf-ospfv3-common-address-family-grouping;
              uses ospfv3-address-family-grouping;
            }
            uses ospfv3-af-ipv6-summary-prefix-grouping;
          }
        }
      }
      // router ospf *
      list ospf {
        tailf:cli-mode-name "config-router";
        description
          "Open Shortest Path First (OSPF)";
        key "id";
        leaf id {
          tailf:cli-suppress-range;
          type uint16 {
            range "1..65535";
          }
        }
        // router ospf * / vrf *
        leaf vrf {
          description
            "VPN Routing/Forwarding Instance";
          tailf:cli-full-command;
          tailf:cli-hide-in-submode;
          tailf:cli-diff-dependency "/ios:native/ip/vrf";
          tailf:cli-diff-dependency "/ios:native/vrf/definition";
          type string;
        }
        // router ospf * / address-family
        container address-family {
          description
            "Enter Address Family command mode";
          container ipv4_1 {
            tailf:cli-drop-node-name;
            container ipv4 {
              description
                "Address family";
              tailf:cli-add-mode;
              tailf:cli-mode-name "config-router-af";
              tailf:cli-full-command;
              tailf:cli-exit-command "exit-address-family";
              uses ospf-address-family-grouping;
            }
          }
          container ipv4 {
            description
              "Address family";
            container unicast {
              description
                "Address Family Modifier";
              tailf:cli-add-mode;
              tailf:cli-mode-name "config-router-af";
              tailf:cli-full-command;
              tailf:cli-exit-command "exit-address-family";
              uses ospf-address-family-grouping;
            }
            container multicast {
              description
                "Address Family Modifier";
              tailf:cli-add-mode;
              tailf:cli-mode-name "config-router-af";
              tailf:cli-full-command;
              tailf:cli-exit-command "exit-address-family";
              uses ospf-address-family-grouping;
            }
          }
        }
        uses ospf-ospfv3-common-grouping;
        uses ospf-ospfv3-common-address-family-grouping;
        uses distribute-list-grouping;
        container domain-id {
          description
            "OSPF domain-id";
          choice domain-id-choice {
            leaf ip-format {
              tailf:cli-drop-node-name;
              type inet:ipv4-address;
            }
            container ip-format-secondary {
              tailf:cli-drop-node-name;
              tailf:cli-compact-syntax;
              tailf:cli-sequence-commands;
              leaf ip {
                tailf:cli-drop-node-name;
                type inet:ipv4-address;
              }
              leaf secondary {
                description
                  "Secondary Domain-ID";
                type empty;
              }
            }
            leaf Null {
              description
                "Null Domain-ID";
              tailf:cli-full-command;
              type empty;
            }
            container type {
              description
                "OSPF domain ID type in Hex format";
              tailf:cli-sequence-commands;
              tailf:cli-compact-syntax;
              leaf type-leaf {
                tailf:cli-drop-node-name;
                tailf:cli-incomplete-command;
                type enumeration {
                  enum "0005";
                  enum "0105";
                  enum "0205";
                  enum "8005";
                }
              }
              leaf value {
                description
                  "OSPF domain ID value in Hex format";
                type string {
                  pattern "[0-9a-fA-F]{12}";
                }
              }
            }
          }
        }
        leaf domain-tag {
          description
            "OSPF domain-tag";
          tailf:cli-full-command;
          type uint32 {
            range "1 .. 4294967295";
          }
        }
        container fast-reroute {
          description
            "LFA FastReroute parameters";
          leaf keep-all-paths {
            description
              "Keep LFA FRR audit trail";
            tailf:cli-full-command;
            type empty;
          }
          container per-prefix {
            description
              "Per-prefix LFA FRR parameters";
            container enable {
              description
                "Enable LFA Fast Reroute";
              tailf:cli-compact-syntax;
              leaf area {
                description
                  "Area to enable LFA FRR in";
                tailf:cli-incomplete-command;
                type ospf-area-type;
              }
              leaf prefix-priority {
                description
                  "Priority of prefixes to be protected";
                type enumeration {
                  enum "high";
                  enum "low";
                }
              }
            }
            container remote-lfa {
              description
                "Remote LFA FastReroute parameters";
              leaf area {
                description
                  "Area for remote LFA command";
                tailf:cli-incomplete-command;
                type ospf-area-type;
              }
              leaf maximum-cost {
                description
                  "Maximum distance to tunnel endpoint";
                tailf:cli-full-command;
                type uint32 {
                  range "1..16777214";
                }
              }
              leaf tunnel {
                description
                  "Remote LFA tunnel type";
                tailf:cli-full-command;
                type enumeration {
                  enum "mpls-ldp";
                }
              }
            }
            container tie-break {
              description
                "LFA FRR repair path selection policy tiebreaks";
              container broadcast-interface-disjoint {
                description
                  "Interface protection attribute";
                tailf:cli-compact-syntax;
                uses tie-break-index;
              }
              container downstream {
                description
                  "Downstream repair path attribute";
                tailf:cli-compact-syntax;
                uses tie-break-index;
              }
              container linecard-disjoint {
                description
                  "Line card protection attribute";
                tailf:cli-compact-syntax;
                uses tie-break-index;
              }
              container lowest-metric {
                description
                  "Lowest metric repair path attribute";
                tailf:cli-compact-syntax;
                uses tie-break-index;
              }
              container node-protecting {
                description
                  "Node protecting repair path attribute";
                tailf:cli-compact-syntax;
                uses tie-break-index;
              }
              container primary-path {
                description
                  "Equal cost multipath attribute";
                tailf:cli-compact-syntax;
                uses tie-break-index;
              }
              container secondary-path {
                description
                  "Not-equal cost multipath attribute";
                tailf:cli-compact-syntax;
                uses tie-break-index;
              }
              container srlg {
                description
                  "Shared risk link group attribute";
                tailf:cli-compact-syntax;
                uses tie-break-index;
              }
            }
          }
        }
        container graceful-restart {
          presence "true";
          description
            "Graceful-restart options";
          leaf disable {
            description
              "Graceful restart disable";
            type empty;
          }
          container helper {
            description
              "helper support";
            presence "true";
            leaf disable {
              description
                "disable helper support";
              type empty;
            }
            leaf strict-lsa-checking {
              description
                "enable helper strict LSA checking";
              type empty;
            }
          }
          leaf restart-interval {
            description
              "Graceful restart interval";
            type uint16;
          }
        }
        container ignore {
          description
            "Do not complain about specific event";
          container lsa {
            description
              "Do not complain upon receiving LSA of the specified type";
            leaf mospf {
              description
                "MOSPF Type 6 LSA";
              type empty;
            }
          }
        }
        leaf ispf {
          description
            "Enable incremental SPF computation";
          tailf:cli-full-command;
          type empty;
        }
        container limit {
          description
            "Limit a specific OSPF feature";
          tailf:cli-compact-syntax;
          container retransmissions {
            description
              "LS update, DBD, and LS request retransmissions";
            leaf non-dc {
              description
                "Non-demand-circuit retransmissions";
              type limit-dc-non-dc-type;
            }
            leaf dc {
              description
                "Demand circuit retransmissions";
              type limit-dc-non-dc-type;
            }
          }
        }
        container local-rib-criteria {
          description
            "Enable or disable usage of local RIB as route criteria";
          tailf:cli-compact-syntax;
          leaf forwarding-address {
            description
              "Local RIB used to validate external/NSSA forwarding addresses";
            type empty;
          }
          leaf inter-area-summary {
            description
              "Local RIB used as criteria for inter-area summaries";
            type empty;
          }
          leaf nssa-translation {
            description
              "Local RIB used as criteria for NSSA translation";
            type empty;
          }
        }
        container microloop {
          description
            "Traffic microloop control parameters";
          container avoidance {
            description
              "Traffic microloop avoidance parameters";
            presence "true";
            leaf disable {
              description
                "Microloop avoidance auto-enable prohibited";
              tailf:cli-full-command;
              type empty;
            }
            leaf protected {
              description
                "Microloop avoidance for protected prefixes only";
              tailf:cli-full-command;
              type empty;
            }
            leaf rib-update-delay {
              description
                "Delay before updating the RIB";
              tailf:cli-full-command;
              type uint32 {
                range "1..600000";
              }
            }
          }
        }
        container mpls {
          description
            "Configure MPLS routing protocol parameters";
          container ldp {
            description
              "routing protocol commands for MPLS LDP";
            container autoconfig {
              description
                "Configure LDP automatic configuration";
              presence "Configure LDP automatic configuration";
              leaf area {
                description
                  "Configure an OSPF area to run MPLS LDP";
                type ospf-area-type;
              }
            }
            container sync {
              description
                "Configure LDP-IGP Synchronization";
              presence "Configure LDP-IGP Synchronization";
            }
          }
          container traffic-eng {
            description
              "routing protocol commands for MPLS Traffic Engineering";
            tailf:cli-compact-syntax;
            leaf multicast-intact {
              description
                "MPLS TE and PIM interaction";
              tailf:cli-full-command;
              type empty;
            }
            leaf area {
              description
                "configure an ospf area to run MPLS Traffic Engineering";
              tailf:cli-full-command;
              type ospf-area-type;
            }
            container autoroute-exclude {
              description
                "MPLS TE autoroute exclude";
              leaf prefix-list {
                description
                  "Filter prefixes";
                type string;
              }
            }
            container interface {
              description
                "MPLS TE interface configuration for this OSPF process";
              tailf:cli-sequence-commands;
              tailf:cli-compact-syntax;
              leaf name {
                tailf:cli-drop-node-name;
                tailf:cli-incomplete-command;
                type string;
              }
              leaf id {
                tailf:cli-drop-node-name;
                tailf:cli-optional-in-sequence;
                type uint32;
              }
              leaf area {
                description
                  "advertise MPLS TE information for this interface into area";
                type uint32;
              }
            }
            container mesh-group-container {
              tailf:cli-drop-node-name;
              tailf:cli-sequence-commands;
              tailf:cli-compact-syntax;
              leaf mesh-group {
                description
                  "Traffic Engineering Mesh-Group advertisement";
                tailf:cli-incomplete-command;
                type uint32 {
                  range "0 .. 4294967295";
                }
              }
              leaf interface {
                description
                  "Interface";
                tailf:cli-incomplete-command;
                tailf:cli-drop-node-name;
                type string;
              }
              leaf id {
                tailf:cli-drop-node-name;
                tailf:cli-optional-in-sequence;
                type uint32;
              }
              list area {
                description
                  "configure flooding scope as area";
                tailf:cli-suppress-mode;
                tailf:cli-delete-when-empty;
                key "id";
                leaf id {
                  tailf:cli-suppress-range;
                  type ospf-area-type;
                }
              }
            }
            container router-id {
              description
                "Traffic Engineering stable IP address for system";
              tailf:cli-sequence-commands;
              tailf:cli-compact-syntax;
              leaf interface {
                description
                  "Interface";
                tailf:cli-drop-node-name;
                type string;
              }
              leaf id {
                tailf:cli-drop-node-name;
                tailf:cli-optional-in-sequence;
                type uint32;
              }
            }
          }
        }
        list neighbor {
          description
            "Specify a neighbor router";
          tailf:cli-suppress-mode;
          tailf:cli-delete-when-empty;
          key "ip";
          leaf ip {
            type inet:ipv4-address;
          }
          leaf cost {
            description
              "OSPF cost for point-to-multipoint neighbor";
            type uint32 {
              range "1 .. 65535";
            }
          }
          container database-filter {
            description
              "Filter OSPF LSA during synchronization and flooding for point-to-multipoint neighbor";
            tailf:cli-flatten-container;
            container all {
              description
                "Filter all LSA";
              tailf:cli-compact-syntax;
              tailf:cli-flatten-container;
              leaf out {
                description
                  "Outgoing LSA";
                type empty;
              }
            }
          }
          leaf poll-interval {
            description
              "OSPF dead-router polling interval";
            type uint32 {
              range "0 .. 65535";
            }
          }
          leaf priority {
            description
              "OSPF priority of non-broadcast neighbor";
            type uint32 {
              range "0 .. 255";
            }
          }
        }
        list network {
          description
            "Enable routing on an IP network";
          tailf:cli-incomplete-command;
          tailf:cli-suppress-mode;
          tailf:cli-delete-when-empty;
          key "ip mask";
          leaf ip {
            type inet:ipv4-address;
          }
          leaf mask {
            type inet:ipv4-address;
          }
          leaf area {
            description
              "Set the OSPF area ID";
            type ospf-area-type;
          }
        }
        container nsf {
          description
            "Non-stop forwarding";
          presence "true";
          container cisco {
            description
              "Cisco Non-stop forwarding";
            presence "true";
            container helper {
              description
                "helper support";
              presence "helper support";
              leaf disable {
                tailf:cli-reset-container;
                description
                  "disable helper support";
                type empty;
              }
            }
          }
          container ietf {
            description
              "IETF graceful restart";
            container helper {
              description
                "helper support";
              presence "helper support";
              leaf disable {
                tailf:cli-reset-container;
                tailf:cli-delete-container-on-delete;
                description
                  "disable helper support";
                type empty;
              }
              leaf strict-lsa-checking {
                description
                  "enable helper strict LSA checking";
                type empty;
              }
            }
          }
        }
        container prefix-priority {
          description
            "OSPF prefix priority";
          tailf:cli-compact-syntax;
          tailf:cli-sequence-commands;
          leaf high {
            description
              "High prefix priority";
            type empty;
          }
          leaf route-map {
            description
              "Prefix priority selection by route-map";
            type string;
          }
        }
        leaf prefix-suppression {
          description
            "OSPF prefix suppression";
          tailf:cli-full-command;
          type empty;
        }
        leaf priority {
          description
            "OSPF topology priority";
          type uint8 {
            range "0..127";
          }
        }
        container process-min-time {
          description
            "Percentage of quantum to be used before releasing CPU";
          leaf percent {
            description
              "percent";
            type uint32 {
              range "1 .. 100";
            }
          }
        }
        leaf shutdown {
          description
            "Shutdown the OSPF protocol under the current instance";
          tailf:cli-boolean-no;
          type boolean;
        }
        uses router-snmp-grouping;
        list summary-address {
          description
            "Configure IP address summaries";
          tailf:cli-suppress-mode;
          tailf:cli-delete-when-empty;
          key "ip wildcard";
          leaf ip {
            type inet:ipv4-address;
          }
          leaf wildcard {
            type inet:ipv4-address;
          }
          choice tag-no-advertise-choice {
            leaf nssa-only {
              description
                "Limit summary to NSSA areas";
              type empty;
            }
            leaf tag {
              description
                "Set tag";
              tailf:cli-full-command;
              type uint32 {
                range "0 .. 4294967295";
              }
            }
            leaf not-advertise {
              description
                "Do not advertise when translating OSPF type-7 LSA";
              type empty;
              tailf:cli-full-command;
            }
          }
        }
      }
      //router eigrp *
      list eigrp {
        description
          "Enhanced Interior Gateway Routing Protocol (EIGRP)";
        tailf:cli-mode-name "config-router";
        tailf:cli-diff-dependency "/ios:native/interface";
        key "id";
        leaf id {
          description
            "Autonomous System ID";
          type union {
            type uint16 {
              range "1..65535";
            }
            type string;
          }
        }
        container passive-interface {
          description "Suppress routing updates on an interface";
          leaf interface {
            description "interface name";
            tailf:cli-drop-node-name;
            type string;
          }
          leaf Tunnel {
            description "Tunnel interface number";
            type uint32 {
              range "0..2147483647";
            }
          }
          leaf Vlan {
            description "Vlan interface number";
            type uint16 {
              range "1..4094";
            }
          }
          leaf default {
            description "Suppress routing updates on all interfaces";
            type empty;
          }
        }
        container address-family {
          description
            "Enter Address Family command mode";
          container ipv4 {
            description
              "Address Family IPv4";
            list af-list {
              tailf:cli-drop-node-name;
              description
                "Specify Address-Family Autonomous System Number";
              tailf:cli-mode-name "config-router-af";
              tailf:cli-exit-command "exit-address-family";
              tailf:cli-full-command;
              key "autonomous-system";
              leaf autonomous-system {
                tailf:cli-expose-key-name;
                description
                  "Specify Address-Family Autonomous System Number";
                type uint16;
              }
              leaf unicast-multicast {
                tailf:cli-drop-node-name;
                tailf:cli-prefix-key;
                type enumeration {
                  enum "unicast";
                  enum "multicast";
                }
              }
              leaf vrf {
                tailf:cli-prefix-key;
                description
                  "Virtual Routing/Forwarding instance name";
                type string;
              }
              list af-interface {
                description
                  "Enter Address Family interface configuration";
                tailf:cli-mode-name "config-router-af-interface";
                tailf:cli-exit-command "exit-af-interface";
                key "name";
                leaf name {
                  type string;
                }
                leaf hello-interval {
                  description
                    "Configures hello interval";
                  type uint16;
                }
                leaf hold-time {
                  description
                    "Configures hold time";
                  type uint16;
                }
                leaf passive-interface {
                  description
                    "Suppress address updates on an interface";
                  type empty;
                }
                leaf split-horizon {
                  description
                    "Perform split horizon";
                  tailf:cli-boolean-no;
                  tailf:cli-trim-default;
                  type boolean;
                }
                container authentication {
                  description
                    "authentication subcommands";
                  container mode {
                    description
                      "authentication mode";
                    leaf md5 {
                      description
                        "Keyed message digest";
                      tailf:cli-full-command;
                      type empty;
                    }
                    container hmac-sha-256 {
                      description
                        "HMAC-SHA-256 Authentication";
                      tailf:cli-compact-syntax;
                      leaf auth-type {
                        tailf:cli-drop-node-name;
                        type uint8;
                      }
                      leaf auth-key {
                        tailf:cli-drop-node-name;
                        tailf:cli-full-command;
                        tailf:cli-multi-value;
                        type string;
                      }
                    }
                  }
                  leaf key-chain {
                    description
                      "key-chain";
                    tailf:cli-full-command;
                    type string;
                  }
                }
                container summary-address {
                  tailf:cli-sequence-commands;
                  tailf:cli-compact-syntax;
                  leaf address {
                    tailf:cli-drop-node-name;
                    type inet:ipv4-address;
                  }
                  leaf mask {
                    tailf:cli-drop-node-name;
                    type inet:ipv4-address;
                  }
                }
              }
              list topology {
                description
                  "Topology configuration mode";
                tailf:cli-mode-name "config-router-af-topology";
                tailf:cli-exit-command "exit-af-topology";
                key "name";
                leaf name {
                  type string;
                }
                container distribute-list {
                  description
                    "Filter entries in eigrp updates";
                  list route-map {
                    description
                      "Filter prefixes based on the route-map";
                    tailf:cli-suppress-mode;
                    key "name";
                    leaf name {
                      type string;
                    }
                    leaf in {
                      description
                        "Filter incoming service updates";
                      type string;
                    }
                    leaf out {
                      description
                        "Filter outgoing service updates";
                      type string;
                    }
                  }
                }
              }
              list network {
                description
                  "Enable routing on an IP network";
                tailf:cli-suppress-mode;
                key number;
                leaf number {
                  description
                    "Network number";
                  type inet:ipv4-address;
                }
                leaf wild-card {
                  description
                    "EIGRP wild card bits";
                  tailf:cli-drop-node-name;
                  type inet:ipv4-address;
                }
              }
              container eigrp {
                description
                  "EIGRP Address Family specific commands";
                leaf router-id {
                  description
                    "router id for this EIGRP process";
                  tailf:cli-full-command;
                  type inet:ipv4-address;
                }
                container stub {
                  description
                    "Set address-family in stubbed mode";
                  tailf:cli-compact-syntax;
                  presence "true";
                  leaf connected {
                    description
                      "Do advertise connected routes";
                    type empty;
                  }
                  leaf summary {
                    description
                      "Do advertise summary routes";
                    type empty;
                  }
                  leaf redistributed {
                    description
                      "Do advertise redistributed routes";
                    type empty;
                  }
                  leaf leak-map {
                    description
                      "Allow dynamic prefixes based on the leak-map";
                    tailf:cli-full-command;
                    type string;
                  }
                  leaf receive-only {
                    description
                      "Set receive only neighbor";
                    type empty;
                  }
                  leaf static {
                    description
                      "Do advertise static routes";
                    type empty;
                  }
                }
              }
              leaf nsf {
                description
                  "Non-stop forwarding";
                tailf:cli-full-command;
                type empty;
              }
            }
          }
        }
        leaf auto-summary {
          description
            "Enable automatic network number summarization";
          type empty;
        }
        container bfd {
          description
            "BFD configuration commands";
          leaf all-interfaces {
            description
              "Enable BFD on all interfaces";
            type empty;
          }
          container interface {
            description
              "Enable BFD on specific interface";
            tailf:cli-compact-syntax;
            tailf:cli-flatten-container;
            uses interface-grouping;
          }
        }
        container default-information {
          description
            "Control distribution of default information";
          container in {
            description
              "Accept input default routing information";
            presence "true";
            leaf sa-num {
              description
                "A standard expanded IP access list number";
              tailf:cli-drop-node-name;
              type uint16 {
                range "1300..1999";
              }
            }
            leaf sa-name {
              description
                "Standard Access-list name";
              tailf:cli-drop-node-name;
              type string;
            }
          }
          container out {
            description
              "Accept output default routing information";
            presence "true";
            leaf sa-out-num {
              description
                "A standard expanded IP access list number";
              tailf:cli-drop-node-name;
              type uint16 {
                range "1300..1999";
              }
            }
            leaf sa-out-name {
              description
                "Standard Access-list name";
              tailf:cli-drop-node-name;
              type string;
            }
          }
        }
        container default-metric {
          description
            "Set metric of redistributed routes";
          list dm-rdr {
            tailf:cli-drop-node-name;
            tailf:cli-suppress-mode;
            key "dm-rdr";
            leaf dm-rdr {
              description
                "Bandwidth in Kbits per second";
              type uint32 {
                range "1..4294967295";
              }
            }
            list dm-rdr0 {
              tailf:cli-drop-node-name;
              tailf:cli-suppress-mode;
              key "dm-rdr0";
              leaf dm-rdr0 {
                description
                  "delay metric in 10 microsecond units";
                type uint32 {
                  range "0..4294967295";
                }
              }
              leaf dm-rdr-pct {
                description
                  "Reliability metric where 255 is 100% reliable";
                tailf:cli-drop-node-name;
                type uint8 {
                  range "0..255";
                }
              }
            }
          }
        }
        container distance {
          description
            "Define an administrative distance";
          list rad-dis {
            tailf:cli-drop-node-name;
            tailf:cli-suppress-mode;
            key "rad-dis";
            leaf rad-dis {
              description
                "Set route administrative distance";
              type uint8 {
                range "1..255";
              }
            }
            list ipv4 {
              tailf:cli-drop-node-name;
              tailf:cli-suppress-mode;
              key "ipv4";
              leaf ipv4 {
                description
                  "IP Source address";
                type inet:ipv4-address;
              }
              leaf ipv40 {
                description
                  "Wildcard bits";
                tailf:cli-drop-node-name;
                type inet:ipv4-address;
              }
            }
          }
          container eigrp {
            description
              "Set distance for internal and external routes";
            list di-rt {
              tailf:cli-drop-node-name;
              tailf:cli-suppress-mode;
              key "di-rt";
              leaf di-rt {
                description
                  "Distance for internal routes";
                type uint8 {
                  range "1..255";
                }
              }
              leaf di-rt0 {
                description
                  "Distance for external routes";
                tailf:cli-drop-node-name;
                type uint8 {
                  range "1..255";
                }
              }
            }
          }
        }
        container distribute-list {
          description
            "Filter entries in eigrp updates";
          list eig-filt {
            tailf:cli-drop-node-name;
            tailf:cli-suppress-mode;
            key "eig-filt";
            leaf eig-filt {
              description
                "IP expanded access list number";
              type exp-acl-type;
            }     
            container in {
              description
                "Filter incoming service updates";
              presence "true";
              leaf-list interface_name {
                description
                  "Interface name";
                tailf:cli-drop-node-name;
                tailf:cli-list-syntax;
                type string;
              }
            }
            container out {
              description
                "Filter outgoing service updates";
              presence "true";
              leaf-list interface_name {
                description
                  "Interface name";
                tailf:cli-drop-node-name;
                tailf:cli-list-syntax;
                type string;
              }
            }
          }
          container gateway {
            description
              "Filtering incoming address updates based on gateway";
            list gw-list {
              tailf:cli-drop-node-name;
              tailf:cli-suppress-mode;
              key "gw-list";
              leaf gw-list {
                description
                  "Name of an IP prefix-list";
                type string;
              }
              leaf in {
                description
                  "Filter incoming service updates";
                type empty;
              }
              leaf out {
                description
                  "Filter outgoing service updates";
                type empty;
              }
            }
          }
          container prefix {
            description
              "Filter prefixes in address updates";
            list pl-name {
              tailf:cli-drop-node-name;
              tailf:cli-suppress-mode;
              key "pl-name";
              leaf pl-name {
                description
                  "Name of an IP prefix-list";
                type string;
              }
              leaf gateway {
                description
                  "Filtering incoming address updates based on gateway";
                type empty;
              }
              leaf in {
                description
                  "Filter incoming service updates";
                type empty;
              }
              leaf out {
                description
                  "Filter outgoing service updates";
                type empty;
              }
            }
          }
          container route-map {
            description
              "Filter prefixes based on the route-map";
            list rmap-name {
              tailf:cli-drop-node-name;
              tailf:cli-suppress-mode;
              key "rmap-name";
              leaf rmap-name {
                description
                  "route-map name";
                type string;
              }
              leaf in {
                description
                  "Filter incoming service updates";
                type empty;
              }
              leaf out {
                description
                  "Filter outgoing service updates";
                type empty;
              }
            }
          }
        }
        container eigrp {
          description
            "EIGRP specific commands";
          leaf event-log-size {
            description
              "Max event log entries";
            type uint32 {
              range "0..12356402";
            }
          }
          leaf log-neighbor-changes {
            description
              "Enable/Disable EIGRP neighbor logging";
            type empty;
          }
          container log-neighbor-warnings {
            description
              "Enable/Disable EIGRP neighbor warnings";
            presence "true";
            leaf warn-sec {
              description
                "Neighbor warning interval in seconds";
              tailf:cli-drop-node-name;
              type uint16 {
                range "1..65535";
              }
            }
          }
          leaf router-id {
            description
              "EIGRP Router-ID in IP address format";
            type inet:ipv4-address;
          }
          container stub {
            description
              "Set address-family in stubbed mode";
            presence "true";
            container connected {
              description
                "Do advertise connected routes";
              presence "true";
              leaf leak-map {
                description
                  "Allow dynamic prefixes based on the leak-map";
                type empty;
              }
              leaf redistributed {
                description
                  "Do advertise redistributed routes";
                type empty;
              }
              leaf static {
                description
                  "Do advertise static routes";
                type empty;
              }
              leaf summary {
                description
                  "Do advertise summary routes";
                type empty;
              }
            }
            leaf leak-map {
              description
                "leak-map name";
              type string;
            }
            leaf receive-only {
              description
                "Set receive only neighbor";
              type empty;
            }
            container redistributed {
              description
                "Do advertise redistributed routes";
              presence "true";
              leaf connected {
                description
                  "Do advertise connected routes";
                type empty;
              }
              leaf leak-map {
                description
                  "Allow dynamic prefixes based on the leak-map";
                type empty;
              }
              leaf static {
                description
                  "Do advertise static routes";
                type empty;
              }
              leaf summary {
                description
                  "Do advertise summary routes";
                type empty;
              }
            }
            container static {
              description
                "Do advertise static routes";
              presence "true";
              leaf connected {
                description
                  "Do advertise connected routes";
                type empty;
              }
              leaf leak-map {
                description
                  "Allow dynamic prefixes based on the leak-map";
                type empty;
              }
              leaf redistributed {
                description
                  "Do advertise redistributed routes";
                type empty;
              }
              leaf summary {
                description
                  "Do advertise summary routes";
                type empty;
              }
            }
            container summary {
              description
                "Do advertise summary routes";
              presence "true";
              leaf connected {
                description
                  "Do advertise connected routes";
                type empty;
              }
              leaf leak-map {
                description
                  "Allow dynamic prefixes based on the leak-map";
                type empty;
              }
              leaf redistributed {
                description
                  "Do advertise redistributed routes";
                type empty;
              }
              leaf static {
                description
                  "Do advertise static routes";
                type empty;
              }
            }
          }
          leaf upgrade-cli {
            description
              "EIGRP Virtual-Instance Name";
            type string;
          }
        }
        leaf maximum-paths {
          description
            "Number of paths";
          type uint8 {
            range "1..32";
          }
        }
        container metric {
          description
            "Modify metrics and parameters for advertisement";
          leaf maximum-hops {
            description
              "Hop count";
            type uint8 {
              range "1..255";
            }
          }
          leaf weights {
            description
              "Type (Only TOS 0 supported)";
            type uint8 {
              range "0..8";
            }
          }
        }
        container neighbor {
          description
            "Specify a neighbor router";
          list ipv4 {
            tailf:cli-drop-node-name;
            tailf:cli-suppress-mode;
            key "ipv4";
            leaf ipv4 {
              description
                "Neighbor address";
              type inet:ipv4-address;
            }
            container interface {
              tailf:cli-drop-node-name;
              description
                "Specify interface for global address";
              tailf:cli-compact-syntax;
              tailf:cli-flatten-container;
              uses interface-grouping;
            }
          }
        }
        container network {
          description
            "Enable routing on an IP network";
          list ipv4 {
            tailf:cli-drop-node-name;
            tailf:cli-suppress-mode;
            key "ipv4";
            leaf ipv4 {
              description
                "Network number";
              type inet:ipv4-address;
            }
            leaf ipv40 {
              description
                "EIGRP wild card bits";
              tailf:cli-drop-node-name;
              type inet:ipv4-address;
            }
          }
        }
        leaf nsf {
          description
            "Non-stop forwarding";
          type empty;
        }
        container offset-list {
          description
            "Add or subtract offset from EIGRP metrics";
          list nsr-list {
            tailf:cli-drop-node-name;
            tailf:cli-suppress-mode;
            key "nsr-list";
            leaf nsr-list {
              description
                "Access list of networks to apply offset (extended range)";
              type uint16 {
                range "1300..1999";
              }
            }
            leaf in {
              description
                "Perform offset on incoming updates";
              type empty;
            }
            leaf out {
              description
                "Perform offset on outgoing updates";
              type empty;
            }
          }
          list ol-acl {
            tailf:cli-drop-node-name;
            tailf:cli-suppress-mode;
            key "ol-acl";
            leaf ol-acl {
              description
                "Access-list name";
              type string;
            }
            leaf in {
              description
                "Perform offset on incoming updates";
              type empty;
            }
            leaf out {
              description
                "Perform offset on outgoing updates";
              type empty;
            }
          }
        }
        container redistribute {
          description
            "Redistribute IPv4 routes from another routing protocol";
          list bgp {
            description
              "Border Gateway Protocol (BGP)";
            tailf:cli-suppress-mode;
            tailf:cli-compact-syntax;
            key "rdr-as";
            leaf rdr-as {
              description
                "Autonomous system number";
              type bgp-as-number-type;
            }
            container metric {
              description
                "Metric for redistributed routes";
              tailf:cli-flatten-container;
              tailf:cli-compact-syntax;
              tailf:cli-sequence-commands;
              leaf bandwith {
                tailf:cli-drop-node-name;
                description
                  "Bandwidth metric in Kbits per second";
                type uint32 {
                  range "1..4294967295";
                }
              }
              leaf delay {
                tailf:cli-drop-node-name;
                description
                  "EIGRP delay metric, in 10 microsecond units";
                type uint32 {
                  range "0..4294967295";
                }
              }
              leaf reliability {
                tailf:cli-drop-node-name;
                description
                  "EIGRP reliability metric where 255 is 100% reliable";
                type uint8 {
                  range "0..255";
                }
              }
              leaf Effective {
                tailf:cli-drop-node-name;
                description
                  "EIGRP Effective bandwidth metric (Loading) where 255 is 100% loaded";
                type uint8 {
                  range "1..255";
                }
              }
              leaf mtu {
                tailf:cli-drop-node-name;
                description
                  "EIGRP MTU of the path";
                type uint16 {
                  range "1..65535";
                }
              }
            }
            leaf route-map {
              description
                "Route map reference";
              type string;
            }
            leaf rd-LESSER_1_PERIOD_0-XX_PERIOD_YY_GREATER_ {
              tailf:alt-name "_LT_1.0-XX.YY_GT_";
              description
                "Autonomous system number";
              type empty;
            }
          }
          container connected {
            description
              "Connected";
            presence "true";
            leaf metric {
              description
                "Metric for redistributed routes";
              type empty;
            }
            leaf route-map {
              description
                "Route map reference";
              type empty;
            }
          }
          list eigrp {
            description
              "Enhanced Interior Gateway Routing Protocol (EIGRP)";
            tailf:cli-suppress-mode;
            tailf:cli-compact-syntax;
            key autonomous-system-number;
            leaf autonomous-system-number{
              type uint16 {
                range "1..65535";
              }
            }
            uses router-eigrp-redistribute-grouping;
          }
          container isis {
            description
              "ISO IS-IS";
            presence "true";
            leaf is-tag {
              description
                "ISO routing area tag";
              tailf:cli-drop-node-name;
              type string;
            }
            leaf level-1 {
              description
                "IS-IS level-1 routes only";
              type empty;
            }
            leaf level-1-2 {
              description
                "IS-IS level-1 and level-2 routes";
              type empty;
            }
            leaf level-2 {
              description
                "IS-IS level-2 routes only";
              type empty;
            }
            leaf metric {
              description
                "Metric for redistributed routes";
              type empty;
            }
            leaf route-map {
              description
                "Route map reference";
              type empty;
            }
          }
          container lisp {
            description
              "Locator ID Separation Protocol (LISP)";
            presence "true";
            leaf metric {
              description
                "Metric for redistributed routes";
              type empty;
            }
            leaf route-map {
              description
                "Route map reference";
              type empty;
            }
          }
          container mobile {
            description
              "Mobile routes";
            presence "true";
            leaf metric {
              description
                "Metric for redistributed routes";
              type empty;
            }
            leaf route-map {
              description
                "Route map reference";
              type empty;
            }
          }
          container odr {
            description
              "On Demand stub Routes";
            presence "true";
            leaf metric {
              description
                "Metric for redistributed routes";
              type empty;
            }
            leaf route-map {
              description
                "Route map reference";
              type empty;
            }
          }
          list ospf {
            description
              "Open Shortest Path First (OSPF)";
            tailf:cli-suppress-mode;
            tailf:cli-compact-syntax;
            key process-id;
            leaf process-id {
              type uint16 {
                range "1..65535";
              }
            }
            uses router-eigrp-redistribute-grouping;            
          }
          container rip {
            description
              "Routing Information Protocol (RIP)";
            presence "true";
            leaf metric {
              description
                "Metric for redistributed routes";
              type empty;
            }
            leaf route-map {
              description
                "Route map reference";
              type empty;
            }
          }
          container static {
            description
              "Static routes";
            presence "true";
            leaf metric {
              description
                "Metric for redistributed routes";
              type empty;
            }
            leaf route-map {
              description
                "Route map reference";
              type empty;
            }
          }
          container vrf {
            description
              "Specify a source virtual routing/forwarding instance";
            leaf name {
              description
                "Virtual Routing/Forwarding instance name";
              tailf:cli-drop-node-name;
              type string;
            }
            leaf global {
              description
                "global VRF";
              type empty;
            }
          }
        }
        leaf shutdown {
          description
            "Shutdown this instance of EIGRP";
          type empty;
        }
        container summary-metric {
          description
            "Specify summary to apply metric/filtering";
          list ipv4 {
            tailf:cli-drop-node-name;
            tailf:cli-suppress-mode;
            key "ipv4";
            leaf ipv4 {
              description
                "Summary to configure static metric";
              type inet:ipv4-address;
            }
            leaf mask {
              description
                "Network mask";
              tailf:cli-drop-node-name;
              type inet:ipv4-address;
            }
          }
          leaf A_PERIOD_B_PERIOD_C_PERIOD_D_SLASH_nn {
            tailf:alt-name "A.B.C.D/nn";
            description
              "Summary <network>/<length>, e.g., 192.168.0.0/16";
            type empty;
          }
        }
        container timers {
          description
            "Adjust routing timers";
          container active-time {
            description
              "time limit for active state";
            leaf atimer {
              description
                "active state time limit in minutes";
              tailf:cli-drop-node-name;
              type uint16 {
                range "1..65535";
              }
            }
            leaf disabled {
              description
                "disable time limit for active state";
              type empty;
            }
          }
          container graceful-restart {
            description
              "EIGRP Graceful Restart timer";
            leaf purge-time {
              description
                "EIGRP stale route purge time";
              type empty;
            }
          }
          container nsf {
            description
              "EIGRP NSF timer";
            leaf converge {
              description
                "EIGRP time limit for convergence after switchover";
              type empty;
            }
            leaf signal {
              description
                "EIGRP time limit for signaling NSF restart";
              type empty;
            }
          }
        }
        container traffic-share {
          description
            "How to compute traffic share over alternate paths";
          leaf balanced {
            description
              "Share inversely proportional to metric";
            type empty;
          }
          container min {
            description
              "All traffic shared among min metric paths";
            leaf across-interfaces {
              description
                "Use different interfaces for equal-cost paths";
              type empty;
            }
          }
        }
        leaf variance {
          description
            "Metric variance multiplier";
          type uint8 {
            range "1..128";
          }
        }
      }

      // router isis
      container isis {
        tailf:cli-add-mode;
        description
          "ISO IS-IS";
        tailf:cli-mode-name "config-router";
        tailf:cli-show-no;
        tailf:cli-delete-when-empty;
        presence "true";
        uses isis-main-grouping;
      }
      // router isis *
      container isis-container {
        tailf:cli-drop-node-name;
        list isis {
          description
            "ISO IS-IS";
          tailf:cli-mode-name "config-router";
          key "area-tag";
          leaf area-tag {
            type string;
          }
          uses isis-main-grouping;
        }
      }

      // router rip
      container rip {
        tailf:cli-add-mode;
        tailf:cli-mode-name "config-router";
        tailf:cli-show-no;
        tailf:cli-delete-when-empty;
        presence true;

        description
          "Routing Information Protocol (RIP)";
        uses router-rip-grouping;
        container address-family {
          description
            "Enter Address Family command mode";
          container ipv4 {
            description
              "Address family";
            container unicast {
              tailf:cli-add-mode;
              tailf:cli-mode-name "config-router-af";
              tailf:cli-full-command;
              tailf:cli-exit-command "exit-address-family";
              uses router-rip-grouping;
            }
            list vrf {
              description
                "Specify parameters for a VPN Routing/Forwarding instance";
              tailf:cli-full-command;
              tailf:cli-mode-name "config-router-af";
              tailf:cli-diff-dependency "/ios:native/ip/vrf";
              tailf:cli-diff-dependency "/ios:native/vrf/definition";
              tailf:cli-exit-command "exit-address-family";
              key "name";
              leaf name {
                type string;
              }
              uses address-family-vrf-grouping;
            }
          }
        }
        container default {
          description
            "Set a command to its defaults";
          container address-family {
            description
              "Enter Address Family command mode";
            container ipv4 {
              presence "true";
              description
                "Address family";
              leaf unicast {
                description
                  "Address Family Modifier";
                type empty;
              }
              list vrf {
                description
                  "Specify parameters for a VPN Routing/Forwarding instance";
                tailf:cli-suppress-mode;
                tailf:cli-delete-when-empty;
                tailf:cli-diff-dependency "/ios:native/ip/vrf";
                tailf:cli-diff-dependency "/ios:native/vrf/definition";
                key "name";
                leaf name {
                  type string;
                }
              }
            }
          }
          uses default-router-rip-grouping;
          container default-information {
            description
              "Control distribution of default information";
            leaf originate {
              description
                "Distribute a default route";
              type empty;
            }
          }
          leaf default-metric {
            tailf:cli-full-command;
            description
              "Set metric of redistributed routes";
            type empty;
          }
          uses distance-grouping;
          uses distribute-list-grouping;
          leaf flash-update-threshold {
            tailf:cli-full-command;
            description
              "Specify flash update threshold in second";
            type empty;
          }
          leaf input-queue {
            tailf:cli-full-command;
            description
              "Specify input queue depth";
            type empty;
          }
          uses offset-list-grouping;
          leaf output-delay {
            tailf:cli-full-command;
            description
              "Interpacket delay for RIP updates";
            type empty;
          }
          uses passive-interface-grouping;
          container redistribute {
            description
              "Redistribute information from another routing protocol";
            uses default-redistribute-grouping;
          }
          container timers {
            description
              "Adjust routing timers";
            leaf basic {
              description
                "Basic routing protocol update timers";
              type empty;
            }
          }
          container traffic-share {
            description
              "How to compute traffic share over alternate paths";
            container min {
              description
                "All traffic shared among min metric paths";
              leaf across-interfaces {
                description
                  "Use different interfaces for equal-cost paths";
                type empty;
              }
            }
          }
          leaf version {
            tailf:cli-full-command;
            description
              "Set routing protocol version";
            type empty;
          }
        }
      }

      //router lisp
      container lisp {
        description
          "Locator/ID Separation Protocol";
        tailf:cli-add-mode;
        tailf:cli-mode-name "config-router-lisp";
        tailf:cli-show-no;
        tailf:cli-delete-when-empty;
        presence true;

        uses router-lisp-grouping;
      }
      list lisp-list {
        tailf:cli-drop-node-name;
        description
          "Locator/ID Separation Protocol";
        tailf:cli-mode-name "config-router-lisp";
        key "lisp";
        leaf lisp {
          description
            "Locator/ID Separation Protocol";
          tailf:cli-expose-key-name;
          type uint16;
        }
        uses router-lisp-grouping;
      }
    }

/// ========================================================================
/// service-chain
/// ========================================================================

    grouping config-service-chain-grouping {
      leaf description {
        description
          "Service function forwarder description";
        tailf:cli-multi-value;
        type string {
          length "1..256";
        }
      }
      container ip {
        description
          "IP address for Service Function Forwarder";
        leaf address {
          description
            "Set IPv4 address";
          type inet:ipv4-address;
        }
      }
    }
    container service-chain {
      description
        "Service Chain mode";
      list service-function {
        description
          "Service function details";
        tailf:cli-mode-name "config-service-chain-sf";
        key "name";
        leaf name {
          description
            "WORD;;Service function name";
          type string;
        }
        container config-service-chain-sf-mode {
          tailf:cli-drop-node-name;
          leaf description {
            description
              "Service function description";
            tailf:cli-multi-value;
            tailf:cli-full-command;
            type string {
              length "1..256";
            }
          }
          container encapsulation {
            description
              "Service node encapsulation";
            choice mode-choice {
              container gre {
                description
                  "Service node encapsulation type";
                presence "true";
                leaf enhanced {
                  description
                    "Add enhanced NSH TLV information";
                  type enumeration {
                    enum "copy";
                    enum "divert";
                  }
                }
              }
              leaf none {
                description
                  "Service node encapsulation type";
                type empty;
              }
            }
          }
          container ip {
            description
              "Service node";
            leaf address {
              type inet:ipv4-address;
            }
          }
        }
      }
      container service-function-forwarder {
        description
          "Service function forwarder details";
        list service-ff-name {
          tailf:cli-drop-node-name;
          tailf:cli-mode-name "config-service-chain-sff";
          key "name";
          leaf name {
            description
              "WORD;;Service function forwarder name";
            type string;
          }
          uses config-service-chain-grouping;
        }
        container local {
          description
            "Local service function forwarder";
          tailf:cli-add-mode;
          tailf:cli-mode-name "config-service-chain-sff";
          presence "true";
          uses config-service-chain-grouping;
        }
      }
      list service-path {
        description
          "Service Path Entries";
        tailf:cli-mode-name "config-service-chain-path";
        key "service-path-id";
        leaf service-path-id {
          type uint32 {
            range "0..16777215";
          }
        }
        container config-service-chain-path-mode {
          tailf:cli-drop-node-name;
          leaf description {
            description
              "Path Description";
            tailf:cli-multi-value;
            tailf:cli-full-command;
            type string {
              length "1..256";
            }
          }
          container service-index {
            description
              "Service Index";
            list services {
              tailf:cli-drop-node-name;
              tailf:cli-suppress-mode;
              key "service-index-id";
              leaf service-index-id {
                type uint8 {
                  range "2..255";
                }
              }
              choice service-type-choice {
                leaf service-function {
                  description
                    "Service Function name";
                  type string;
                }
                leaf service-function-forwarder {
                  description
                    "Service Function Forwarder name";
                  type string;
                }
                leaf terminate {
                  description
                    "Terminate(Proxy)";
                  type empty;
                }
              }
            }
          }
        }
      }
    }

    /// ========================================================================
    /// service-routing
    /// ========================================================================
    container service-routing {
      description
        "Configure service-routing";
      leaf capabilities-manager {
        description
          "Service-Routing Capabilities Manager configuration";
        tailf:cli-boolean-no;
        tailf:cli-trim-default;
        type boolean;
      }
    }
    


    /// ========================================================================
    /// performance monitor (ezPM)
    /// ========================================================================
    container performance {
      description
        "Global Performance monitor configuration";
      container monitor {
        description
          "monitor";
        list context {
          description
            "Define ezPM context";
          tailf:cli-mode-name "config-perf-mon";
          key "name";
          leaf name {
            type string;
          }
          leaf profile {
            description
              "Select ezPM profile";
            tailf:cli-hide-in-submode;
            type enumeration {
              enum "application-experience";
              enum "application-performance";
              enum "application-statistics";
            }
          }
          container default {
            description
              "Set a command to its defaults";
            leaf description {
              description
                "Provide a description for ezPM context";
              tailf:cli-full-command;
              type empty;
            }
            uses performance-monitor-context-default-grouping;
          }
          leaf description {
            description
              "Provide a description for ezPM context";
            tailf:cli-multi-value;
            tailf:cli-full-command;
            type string;
          }
          uses performance-monitor-context-grouping;
        }
        container observation-point {
          description
            "Select observation point";
          leaf encrypted-text {
            description
              "Select clear text for observation";
            tailf:cli-full-command;
            type empty;
          }
        }
      }
    }


  /// ========================================================================
  /// otv
  /// ========================================================================
    container otv {
      description
        "Configure OTV information";
      container fragmentation {
        description
          "Clear the DF (Don't Fragment) bit in the IP header";
        container join-interface {
          description
            "Allow fragmentation for overlays using this join-interface";
          uses interface-grouping;
        }
      }
      container isis {
        description
          "OTV ISIS instance subcommands";
        list Overlay {
          description
            "Overlay interface";
          tailf:cli-mode-name "config-otv-isis";
          key "number";
          leaf number {
            type uint16 {
              range "0..512";
            }
          }
          uses otv-isis-overlay-grouping;
        }
        container site {
          description
            "Site Instance";
          tailf:cli-add-mode;
          tailf:cli-mode-name "config-otv-isis";
          uses otv-isis-site-grouping;
        }
      }
      list site {
        description
          "OTV site network configuration";
        tailf:cli-mode-name "config-otv-site";
        key "bridge-domain";
        leaf bridge-domain {
          description
            "Bridge-domain to discover local OTV enabled devices";
          tailf:cli-expose-key-name;
          tailf:cli-full-command;
          type uint16 {
            range "1..8192";
          }
        }
        container default {
          description
            "Set a command to its defaults";
          container otv {
            description
              "OTV site configuration subcommands";
            uses otv-isis-grouping;
          }
        }
        container otv {
          description
            "OTV site configuration subcommands";
          uses otv-isis-grouping;
        }
      }
      leaf site-identifier {
        description
          "OTV site id";
        tailf:cli-full-command;
        type union {
          type uint32;
          type string;
        }
      }
    }

  /// ========================================================================
  /// utd
  /// ========================================================================
    container utd {
      description
        "Global Unified Threat Defense";
      tailf:cli-add-mode;
      tailf:cli-mode-name "config-utd";
      presence "true";
    }
    container utd-engine {
      description
        "Global Unified Threat Defense Engine";
      tailf:cli-drop-node-name;
      container utd {
        container engine {
          description
            "UTD engine";
          container advanced {
            description
              "UTD engine advanced";
            tailf:cli-add-mode;
            tailf:cli-mode-name "config-utd-eng-adv";
            container default {
              description
                "Set a command to its defaults";
              container threat {
                description
                  "Provide threat detection";
                presence "true";
              }
            }
            container threat {
              description
                "Provide threat detection";
              presence "true";
              leaf detection {
                description
                  "Provide threat detection";
                type empty;
              }
            }
          }
          container standard {
            description
              "UTD engine standard";
            tailf:cli-add-mode;
            tailf:cli-mode-name "config-utd-eng-std";
            status deprecated;
            container default {
              description
                "Set a command to its defaults";
              leaf policy {
                description
                  "Provide the policy option (default=balanced)";
                tailf:cli-full-command;
                type empty;
              }
              leaf threat {
                description
                  "Provide the threat detection/protection option (default=detection)";
                tailf:cli-full-command;
                type empty;
              }
            }
            uses utd-engine-standard-grouping;
          }
        }
        container whitelist {
          description
            "UTD whitelist config submode";
          tailf:cli-add-mode;
          tailf:cli-mode-name "config-utd-whitelist";
          status deprecated;
          container signature {
            description
              "Provide signatures for the whitelist";
            tailf:cli-sequence-commands;
            tailf:cli-compact-syntax;
            leaf id {
              description
                "Provide signature id for the whitelist";
              type uint64 {
                range "0..4294967295";
              }
            }
            leaf comment {
              description
                "Provide a comment for the signature";
              tailf:cli-optional-in-sequence;
              tailf:cli-multi-value;
              type string;
            }
          }
        }
      }  
    }

  /// ========================================================================
  /// remote-management 
  /// ========================================================================
    container remote-management {
      description
        "Enable the remote managment";
      tailf:cli-add-mode;
      tailf:cli-mode-name "config-remote-mgmt";
      leaf dmi {
        description
          "data-model-interface";
        tailf:cli-full-command;
        type empty;
      }
      leaf restful-api {
        description
          "RESTful API";
        tailf:cli-boolean-no;
        tailf:cli-trim-default;
        type boolean;
      }
    }
    
  /// ========================================================================
  /// virtual-service
  /// ========================================================================
    list virtual-service {
      description
        "Configure virtual service";
      tailf:cli-mode-name "config-virt-serv";
      key "name";
      leaf name {
        type string {
          length "1..63";
        }
      }
      container ip {
        description
          "ip configured virtual service";
        container shared {
          description
            "Ip shared host-interface";
          container host-interface {
            description
              "Ip shared host-interface";
            leaf FastEthernet {
              description
                "FastEthernet IEEE 802.3";
              tailf:cli-allow-join-with-value {
                tailf:cli-display-joined;
              }
              type string;
            }
            leaf TenGigabitEthernet {
              description
                "Ten Gigabit Ethernet";
              tailf:cli-allow-join-with-value {
                tailf:cli-display-joined;
              }
              type string;
            }
            leaf Loopback {
              description
                "Loopback interface";
              type uint64 {
                range "0..2147483647";
              }
            }
            leaf Vlan {
              description
                "Vlan interface number";
              type uint16 {
                range "1..4094";
              }
            }
          }
        }
      }
      leaf activate {
        description
          "Activate configured virtual service";
        tailf:cli-full-command;
        type empty;
      }
      leaf profile {
        type string;
      }
      container vnic {
        description
          "Guest vnic configuration";
        container gateway {
          description
            "Gateway interface to connect to the guest vnic";
          list VirtualPortGroup {
            description
              "Virtual Port Group";
            tailf:cli-mode-name "config-virt-serv-vnic";
            tailf:cli-allow-join-with-key {
              tailf:cli-display-joined;
            }
            key "number";
            leaf number {
              type uint16 {
                range "0..31";
              }
            }
            container guest {
              description
                "Configure guest vnic address";
              choice ip-address {
                case ipv4-case {
                  container ip {
                    description
                      "Guest vnic IP address";
                    leaf address {
                      description
                        "Set the IP address of virtual interface on guest";
                      type inet:ipv4-address;
                    }
                  }
                }
                case ipv6-case {
                  container ipv6 {
                    description
                      "Guest vnic IPv6 address";
                    leaf address {
                      description
                        "Set the IPv6 address of virtual interface on guest";
                      type inet:ipv6-address;
                    }
                  }
                }
              }
            }
          }
        }
        container management {
          description
            "Gateway interface to connect to the guest vnic";
          tailf:cli-add-mode;
          tailf:cli-mode-name "config-virt-serv-vnic";
          leaf GigabitEthernet0 {
            description
              "Management Ethernet Interface";
            tailf:cli-hide-in-submode;
            type empty;
          }
          container guest {
            description
              "Configure guest vnic address";
            choice ip-address {
              case ipv4-case {
                container ip {
                  description
                    "Guest vnic IP address";
                  leaf address {
                    description
                      "Set the IP address of virtual interface on guest";
                    type inet:ipv4-address;
                  }
                }
              }
              case ipv6-case {
                container ipv6 {
                  description
                    "Guest vnic IPv6 address";
                  leaf address {
                    description
                      "Set the IPv6 address of virtual interface on guest";
                    type inet:ipv6-address;
                  }
                }
              }
            }
          }
        }
      }
    }

  } // native
  

  augment "/ios:native/router/rip/default/distribute-list/accesslist" {
    leaf id {
      tailf:cli-drop-node-name;
      tailf:cli-prefix-key;
      mandatory true;
      tailf:cli-disallow-value "prefix|gateway|route-map";
      type default-access-list-id-type;
    }
  }
  augment "/ios:native/router/rip/distribute-list/accesslist" {
    leaf id {
      tailf:cli-drop-node-name;
      tailf:cli-prefix-key;
      mandatory true;
      tailf:cli-disallow-value "prefix|gateway|route-map";
      type access-list-id-type;
    }
  }
  augment "/ios:native/router/rip/default/distribute-list/accesslist-ifname" {
    leaf id {
      tailf:cli-drop-node-name;
      tailf:cli-prefix-key;
      mandatory true;
      tailf:cli-disallow-value "prefix|gateway|route-map";
      type default-access-list-id-type;
    }
  }
  augment "/ios:native/router/rip/distribute-list/accesslist-ifname" {
    leaf id {
      tailf:cli-drop-node-name;
      tailf:cli-prefix-key;
      mandatory true;
      tailf:cli-disallow-value "prefix|gateway|route-map";
      type access-list-id-type;
    }
  }
  augment "/ios:native/router/rip/default/distance/distance-list" {
    leaf access-list {
      tailf:cli-drop-node-name;
      type default-access-list-standard-id-type;
    }
  }
  augment "/ios:native/router/rip/distance/distance-list" {
    leaf access-list {
      tailf:cli-drop-node-name;
      type access-list-standard-id-type;
    }
  }
  augment "/ios:native/router/rip/default/offset-list" {
    leaf id {
      tailf:cli-incomplete-command;
      tailf:cli-drop-node-name;
      tailf:cli-prefix-key {
        tailf:cli-before-key "1";
      }
      mandatory true;
      tailf:cli-disallow-value "in|out";
      type default-offset-list-id-type;
    }
  }
  augment "/ios:native/router/rip/offset-list" {
    leaf id {
      tailf:cli-incomplete-command;
      tailf:cli-drop-node-name;
      tailf:cli-prefix-key {
        tailf:cli-before-key "1";
      }
      mandatory true;
      tailf:cli-disallow-value "in|out";
      type offset-list-id-type;
    }
  }
  augment "/ios:native/router/ospf/distribute-list/accesslist" {
    leaf id {
      tailf:cli-drop-node-name;
      tailf:cli-prefix-key;
      mandatory true;
      tailf:cli-disallow-value "prefix|gateway|route-map";
      type access-list-id-type;
    }
  }
  augment "/ios:native/router/ospf/distribute-list/accesslist-ifname" {
    leaf id {
      tailf:cli-drop-node-name;
      tailf:cli-prefix-key;
      mandatory true;
      tailf:cli-disallow-value "prefix|gateway|route-map";
      type access-list-id-type;
    }
  }
  augment "/ios:native/segment-routing/mpls/mcfg-srmpls/mapping-server/mcfg-srmpls-mapserver/prefix-sid-map/mcfg-srmpls-mapserver-sidmap/address-family/ipv4/mcfg-srmpls-mapserver-sidmap-af/prefixes/index" {
    leaf attach {
      type empty;
    }
  }


/// ========================================================================
/// snmp
/// ========================================================================
  augment "/ios:native" {
    container snmp {
      description
        "Modify non engine SNMP parameters";
      // snmp ifmib
      container ifmib {
        description
          "IF-MIB commands";
        // snmp ifmib ifindex
        container ifindex {
          description
            "ifindex persistence";
          leaf persist {
            description
              "Persist interface indices";
            type empty;
          }
        }
        // snmp ifmib ifalias long
        container ifalias {
          description
            "ifAlias description option, by default it is limited to 64 character";
          leaf long {
            description
              "ifAlias description can be up to 256 characters";
            type empty;
          }
        }
      }
      // snmp mib
      container mib {
        description 
	  "MIB commands";
        container community-map {
          description "Community Mapping as per RFC-2576";
          list community-map-list {
            tailf:cli-drop-node-name;
            tailf:cli-suppress-mode;
            description "SNMP community string";
            key "name";
            leaf name {
              type string;
            }
            leaf engineid { 
              description "Engine ID for the community mapping";
              tailf:cli-diff-dependency "/ios:native/snmp-server/community/name";
              type string;
            }
          }
        }
        
        // snmp mib bulkstat
        container bulkstat {
          description
            "Bulkstat Configuration commands";
          list object-list {
            description
              "Configure an Object List.";
            tailf:cli-suppress-mode;
            tailf:cli-delete-when-empty;
            key "name";
            leaf name {
              type string;
            }
          }
        }
        // snmp mib persist
        leaf persist {
          description
            "Persistence for MIBS";
          tailf:cli-full-command;
          type enumeration {
            enum "cbqos";
            enum "circuit";
          }
        }
      }
    }

    /// ========================================================================
    /// snmp-server
    /// ========================================================================
    container snmp-server {
      description
        "Modify SNMP engine parameters";
      // snmp-server chassis-id *       String to uniquely identify this chassis
      leaf chassis-id {
        description
          "String to uniquely identify this chassis";
        tailf:cli-multi-value;
        type string;
      }
      // snmp-server community *
      list community {
        description
          "Enable SNMP; set community string and access privs";
        tailf:cli-suppress-mode;
        tailf:cli-delete-when-empty;
        tailf:cli-compact-syntax;
        tailf:cli-sequence-commands {
          tailf:cli-reset-siblings;
        }
        key "name";
        leaf name {
          type string;
        }
        leaf view {
          description
            "Restrict this community to a named MIB view";
          tailf:cli-optional-in-sequence;
          type string;
        }
        choice access-choice {
          leaf RO {
            description
              "Read-only access with this community string";
            tailf:cli-optional-in-sequence;
            type empty;
          }
          leaf RW {
            description
              "Read-write access with this community string";
            tailf:cli-optional-in-sequence;
            type empty;
          }
        }
        choice access-list-choice {
          case ipv6 {
            leaf ipv6 {
              description
                "Specify IPv6 Named Access-List";
              type string;
            }
          }
          case ipv4 {
            leaf access-list-name {
              tailf:cli-drop-node-name;
              type std-acl-type;
            }
          }
        }
      }
      leaf contact {
        description
          "Text for mib object sysContact";
        tailf:cli-multi-value;
        type string;
      }
      // context           Create/Delete a context apart from default
      // drop              Silently drop SNMP packets

      // snmp-server enable
      container enable {
        description
          "Enable SNMP Traps or Informs";
        leaf all-traps {
          tailf:alt-name "traps";
          type empty;
        }  
        choice enable-choice {
          case informs {
            leaf informs {
              description
                "Enable SNMP Informs";
              type empty;
            }
          }
          case traps {
            // snmp-server enable traps
            container traps {
              description
                "Enable SNMP Traps";
              leaf aaa_server {
                description
                  "Enable SNMP AAA Server traps";
                tailf:cli-full-command;
                type empty;
              }
              container trustsec-sxp {
                tailf:cli-sequence-commands;
                tailf:cli-compact-syntax;
                description "Enable SNMP CISCO-TRUSTSEC-SXP-MIB traps";
                presence true;
                leaf binding-conflict {
                  type empty;
                }
                leaf binding-err {
                  type empty;
                }
                leaf binding-expn-fail {
                  type empty;
                }
                leaf conn-config-err {
                  type empty;
                }
                leaf conn-down {
                  type empty;
                }
                leaf conn-srcaddr-err {
                  type empty;
                }
                leaf conn-up {
                  type empty;
                }
                leaf msg-parse-err {
                  type empty;
                }
                leaf oper-nodeid-change {
                  type empty;
                }
              }
              container vswitch {
                description "Enable SNMP Virtual Switch notifications";
                presence true;
                container dual-active {
                  description "Enable SNMP Virtual Switch (Dual Active) notification";
                  presence true;
                  leaf vsl {
                    description "Enable SNMP Virtual Switch Link (VSL) notification";
                    type empty;
                  }
                }
              }
              container trustsec-server {
                description "Enable SNMP CISCO-TRUSTSEC-SERVER-MIB traps";
                presence true;
                container radius-server {
                  description "Enable ctsvNoRadiusServerNotif notification";
                  presence true;
                  leaf provision-secret {
                    description "Enable ctsvNoProvisionSecretNotif notification";
                    type empty;
                  }
                }
              }
              container trustsec {
                description "Enable SNMP CISCO-TRUSTSEC-MIB traps";
                presence true;
                container authz-file-error {
                  description "Enable ctsAuthzCacheFileErrNotif notifications";
                  presence true;
                  container cache-file-error {
                    description "Enable ctsCacheFileAccessErrNotif notifications";
                    presence true;
                    container keystore-file-error {
                      description "Enable ctsSwKeystoreFileErrNotif notifications";
                      presence true;
                      container keystore-sync-fail {
                        description "Enable ctsSwKeystoreSyncFailNotif notifications";
                        presence true;
                        container random-number-fail {
                          description "Enable ctsSapRandonNumberFailNotif notifications";
                          presence true;
                          leaf src-entropy-fail {
                            description "Enable ctsSrcEntropyFailNotif notifications";
                            type empty;
                          }
                        }
                      }
                    }
                  }
                }
              }
              container trustsec-interface {
                description "Enable SNMP CISCO-TRUSTSEC-INTERFACE-MIB traps";
                presence true;
                container unauthorized {
                  description "Enable ctsiIfUnauthorizedNotifEnable trap";
                  presence true;
                  container sap-fail {
                    description "Enable ctsiIfSapNegotiationFailNotif trap";
                    presence true;
                    container authc-fail {
                      description "Enable ctsiIfAuthenticationFailNotif trap";
                      presence true;
                      container supplicant-fail {
                        description "Enable ctsiIfAddSupplicantFailNotif trap";
                        presence true;
                        leaf authz-fail {
                          description "Enable ctsiAuthorizationFailNotif trap";
                          type empty;
                        }
                      }
                    }
                  }
                }
              }
              container trustsec-policy {
                description "Enable SNMP CISCO-TRUSTSEC-POLICY-MIB traps";
                presence true;
                container peer-policy-updated {
                  description "Enable ctspPeerPolicyUpdatedNotif notifications";
                  presence true;
                  leaf authz-sgacl-fail {
                    description "Enable ctspAuthorizationSgaclFailNotif notifications";
                    type empty;
                  }
                }
              }
              container ospfv3 {
                description "Enable OSPFv3 traps";
                leaf state-change {
                  description "State change traps";
                  type empty;
                }
                leaf errors {
                  description "Error traps";
                  type empty;
                }
              }
              container ike {
                description "Enable IKE traps";
                container policy {
                  description "Enable IKE Policy traps";
                  leaf add {
                    description "Enable IKE Policy add trap";
                    type empty;
                  }
                  leaf delete {
                    description "Enable IKE Policy delete trap";
                    type empty;
                  }
                }
                container tunnel {
                  description "Enable IKE Tunnel traps";
                  leaf start {
                    description "Enable IKE Tunnel start trap";
                    type empty;
                  }
                  leaf stop {
                    description "Enable IKE Tunnel stop trap";
                    type empty;
                  }
                }
              }
              leaf local-auth {
                description "Enable SNMP local auth traps";
                type empty;
              }
              
              
              container alarms {
                description
                  "Enable SNMP alarms traps";
                tailf:cli-delete-when-empty;
                presence "true";
                leaf alarm-type {
                  tailf:cli-drop-node-name;
                  type union {
                    type uint8 {
                      range "1..4";
                    }
                    type enumeration {
                      enum "critical";
                      enum "informational";
                      enum "major";
                      enum "minor";
                    }
                  }
                }
              }
              container atm {
                description
                  "Enable SNMP atm traps";
                container pvc {
                  description
                    "Enable SNMP atm pvc traps";
                  tailf:cli-sequence-commands;
		  tailf:cli-compact-syntax;
                  tailf:cli-delete-when-empty;
                  presence "true";
                  container extension {
                    description
                      "Enable SNMP atm pvc extension traps";
                    tailf:cli-optional-in-sequence;
                    leaf down {
                      description
                        "Enable SNMP atm pvc extended down trap";
                      tailf:cli-full-command;
                      type empty;
                    }
                    leaf up {
                      description
                        "Enable SNMP atm pvc extended up traps";
                      tailf:cli-full-command;
                      type empty;
                    }
                    leaf mibversion {
                      description
                        "Extension MIB version to be used";
                      tailf:cli-full-command;
                      type enumeration {
                        enum "1";
                        enum "2";
                      }
                    }
                    container oam {
                      description
                        "Enable SNMP atm pvc extended oam trap";
                      container failure {
                        description
                          "Enable SNMP atm pvc extended any oam failure trap";
                        leaf loopback {
                          description
                            "Enable SNMP atm pvc extended oam loopback failure trap";
                          tailf:cli-full-command;
                          type empty;
                        }
                      }
                    }
                  }
                  leaf interval {
                    description
                      "minimum period between successive traps";
                    tailf:cli-optional-in-sequence;
                    type uint16 {
                      range "1..3600";
                    }
                  }
                  leaf fail-interval {
                    description
                      "minimum period for storing the failed timestamp";
                    type uint16 {
                      range "0..3600";
                    }
                  }
                }
                container subif {
                  description
                    "Enable SNMP atm subinterface traps";
                  tailf:cli-sequence-commands;
		  tailf:cli-compact-syntax;
                  tailf:cli-delete-when-empty;
                  presence "true";
                  leaf interval {
                    description
                      "Interval duration in which to limit the number of traps sent";
                    tailf:cli-optional-in-sequence;
                    type uint16 {
                      range "0..3600";
                    }
                  }
                  leaf count {
                    description
                      "Maximum number of traps sent per interval";
                    type uint16 {
                      range "1..1000";
                    }
                  }
                }
              }
              leaf authenticate-fail {
                description
                  "Enable SNMP 802.11 Authentication Fail Trap";
                tailf:cli-full-command;
                type empty;
              }
              container auth-framework {
                tailf:cli-delete-when-empty;
                presence "true";
                leaf sec-violation {
                  type empty;
                }
              }
              leaf bfd {
                tailf:cli-full-command;
                type empty;
              }
              container bgp-conf {
                tailf:cli-drop-node-name;
                leaf cbgp2 {
                  description "Enable BGP MIBv2 traps";
                  type empty;
                }
              }
              leaf bgp {
                description
                  "Enable BGP traps";
                tailf:cli-full-command;
                type empty;
              }
              container bridge {
                tailf:cli-delete-when-empty;
                presence "true";
                leaf newroot {
                  type empty;
                }
                leaf topologychange {
                  type empty;
                }
              }
              leaf bstun {
                description
                  "Enable SNMP BSTUN traps";
                tailf:cli-full-command;
                type empty;
              }
              container bulkstat {
                description
                  "Enable Data-Collection-MIB Collection notifications";
                tailf:cli-compact-syntax;
                tailf:cli-delete-when-empty;
                presence "true";
                leaf collection {
                  description
                    "Enable Data-Collection-MIB Collection notifications";
                  type empty;
                }
                leaf transfer {
                  description
                    "Enable Data-Collection-MIB Transfer notifications";
                  type empty;
                }
              }
              container call-home {
                description
                  "Enable CISCO-CALLHOME-MIB traps";
                tailf:cli-delete-when-empty;
                presence "true";
                leaf message-send-fail {
                  type empty;
                }
                leaf server-fail {
                  type empty;
                }
              }
              leaf c2900 {
                description
                  "Enable SNMP c2900 traps";
                tailf:cli-full-command;
                type empty;
              }
              container c6kxbar {
                description
                  "Enable SNMP CISCO-CAT6K-CROSSBAR-MIB traps";
                tailf:cli-delete-when-empty;
                presence "true";
                leaf intbus-crcexcd {
                  description
                    "Enable SNMP cc6kxbarIntBusCRCErrExcdNotif notification";
                  type empty;
                }
                leaf intbus-crcrcvrd {
                  description
                    "Enable SNMP cc6kxbarIntBusCRCErrRcvrdNotif notification";
                  type empty;
                }
                leaf swbus {
                  description
                    "Enable SNMP cc6kxbarSwBusStatusChangeNotif notification";
                  type empty;
                }
              }
              leaf casa {
                description
                  "Enable SNMP casa traps";
                tailf:cli-full-command;
                type empty;
              }
              leaf ccme {
                tailf:cli-full-command;
                type empty;
              }
              container cef {
                leaf resource-failure {
                  type empty;
                }
                leaf peer-state-change {
                  type empty;
                }
                leaf peer-fib-state-change {
                  type empty;
                }
                leaf inconsistency {
                  type empty;
                }
              }
              leaf cluster {
                description
                  "Enable Cluster traps";
                type empty;
              }
              leaf channel {
                description
                  "Enable SNMP channel traps";
                tailf:cli-full-command;
                type empty;
              }
              leaf chassis {
                description
                  "Enable SNMP chassis traps";
                type empty;
              }
              leaf cnpd {
                description
                  "Enable NBAR Protocol Discovery traps";
                tailf:cli-full-command;
                type empty;
              }
              leaf config {
                description
                  "Enable SNMP config traps";
                tailf:cli-full-command;
                type empty;
              }
              leaf copy-config {
                description
                  "Enable SNMP copy-config traps";
                tailf:cli-full-command;
                type empty;
              }
              leaf config-copy {
                description
                  "Enable SNMP config-copy traps";
                tailf:cli-full-command;
                type empty;
              }
              leaf config-ctid {
                tailf:cli-full-command;
                type empty;
              }
              // snmp-server enable traps cpu
              container cpu {
                description
                  "Allow cpu related traps";
                tailf:cli-delete-when-empty;
                presence "true";
                leaf threshold {
                  description
                    "Allow CPU utilization threshold violation traps";
                  type empty;
                }
              }
              leaf cpu_threshold {
                description
                  "Enables CPU threshold notifications";
                tailf:cli-full-command;
                type empty;
              }
              container csg {
                description
                  "Enable SNMP CSG traps";
                tailf:cli-delete-when-empty;
                presence "true";
                leaf agent {
                  description
                    "Enable SNMP Agent Server traps";
                  type empty;
                }
                leaf database {
                  description
                    "Enable SNMP CSG database traps";
                  type empty;
                }
                leaf quota-server {
                  description
                    "Enable SNMP Quota Server traps";
                  type empty;
                }
              }
              leaf dial {
                description
                  "Enable SNMP dial control traps";
                tailf:cli-full-command;
                type empty;
              }
              leaf director {
                description
                  "Enable SNMP Distributed Director traps";
                tailf:cli-full-command;
                type empty;
              }
              leaf dlsw {
                description
                  "Enable SNMP dlsw traps";
                tailf:cli-full-command;
                type empty;
              }
              leaf deauthenticate {
                description
                  "Enable SNMP 802.11 Deauthentication Trap";
                tailf:cli-full-command;
                type empty;
              }
              leaf disassociate {
                description
                  "Enable SNMP 802.11 Disassociation Trap";
                tailf:cli-full-command;
                type empty;
              }
              leaf dnis {
                description
                  "Enable SNMP DNIS traps";
                tailf:cli-full-command;
                type empty;
              }
              leaf dot11-qos {
                description
                  "Enable SNMP 802.11 QoS Change Trap";
                tailf:cli-full-command;
                type empty;
              }
              container dot1x {
                leaf auth-fail-vlan {
                  type empty;
                }
                leaf guest-vlan {
                  type empty;
                }
                leaf no-auth-fail-vlan {
                  type empty;
                }
                leaf no-guest-vlan {
                  type empty;
                }
              }
              leaf ds0-busyout {
                description
                  "Enable ds0-busyout traps";
                tailf:cli-full-command;
                type empty;
              }
              leaf ds1 {
                description
                  "Enable SNMP DS1 traps";
                tailf:cli-full-command;
                type empty;
              }
              leaf ds1-loopback {
                description
                  "Enable ds1-loopback traps";
                tailf:cli-full-command;
                type empty;
              }
              leaf ds3 {
                description
                  "Enable SNMP DS3 traps";
                tailf:cli-full-command;
                type empty;
              }
              container dsp {
                description
                  "Enable SNMP dsp traps";
                tailf:cli-delete-when-empty;
                presence "true";
                leaf card-status {
                  description
                    "Enable SNMP card status of dsp traps";
                  type empty;
                }
                leaf oper-state {
                  type empty;
                }
              }
              leaf eigrp {
                description
                  "Enable SNMP EIGRP traps";
                tailf:cli-full-command;
                type empty;
              }
              container energywise {
                tailf:cli-delete-when-empty;
                presence "true";
                leaf event-occured {
                  type empty;
                }
                leaf level-change {
                  type empty;
                }
                leaf neighbor-added {
                  type empty;
                }
                leaf neighbor-deleted {
                  type empty;
                }
              }
              leaf entity {
                description
                  "Enable SNMP entity traps";
                tailf:cli-full-command;
                type empty;
              }
              container entity-diag {
                description
                  "Enable SNMP CISCO-ENTITY-DIAG-MIB traps";
                tailf:cli-delete-when-empty;
                presence "true";
                leaf boot-up-fail {
                  description
                    "Enable SNMP ceDiagBootUpFailedNotif traps";
                  type empty;
                }
                leaf hm-test-recover {
                  description
                    "Enable SNMP ceDiagHMTestRecoverNotif traps";
                  type empty;
                }
                leaf hm-thresh-reached {
                  description
                    "Enable SNMP ceDiagHMThresholdReachedNotif traps";
                  type empty;
                }
                leaf scheduled-test-fail {
                  description
                    "Enable SNMP ceDiagScheduledTestFailedNotif traps";
                  type empty;
                }
              }
              container envmon {
                description
                  "Enable SNMP environmental monitor traps";
                tailf:cli-delete-when-empty;
                presence "true";
                leaf fan {
                  type empty;
                }
                leaf shutdown {
                  type empty;
                }
                leaf supply {
                  type empty;
                }
                leaf temperature {
                  type empty;
                }
                leaf status {
                  type empty;
                }
              }
              container errdisable {
                description
                  "Enable SNMP errdisable notifications";
                tailf:cli-delete-when-empty;
                presence "true";
                leaf notification-rate {
                  description
                    "Number of notifications per minute";
                  type uint16 {
                    range "0..10000";
                  }
                }
              }
              leaf ether-oam {
                tailf:cli-full-command;
                type empty;
              }
              container ethernet {
                container cfm {
                  leaf alarm {
                    description
                      "Enable SNMP Ethernet CFM fault alarm trap";
                    type empty;
                  }
                  // snmp-server enable traps ethernet cfm cc
                  container cc {
                    tailf:cli-delete-when-empty;
                    presence "true";
                    leaf config {
                      type empty;
                    }
                    leaf cross-connect {
                      type empty;
                    }
                    leaf loop {
                      type empty;
                    }
                    leaf mep-down {
                      type empty;
                    }
                    leaf mep-up {
                      type empty;
                    }
                  }
                  // snmp-server enable traps ethernet cfm crosscheck
                  container crosscheck {
                    tailf:cli-delete-when-empty;
                    presence "true";
                    leaf mep-missing {
                      type empty;
                    }
                    leaf mep-unknown {
                      type empty;
                    }
                    leaf service-up {
                      type empty;
                    }
                  }
                }
                container evc {
                  description
                    "Enable SNMP Ethernet EVC traps";
                  tailf:cli-delete-when-empty;
                  presence "true";
                  leaf create {
                    description
                      "Enable SNMP Ethernet EVC create traps";
                    type empty;
                  }
                  leaf delete {
                    description
                      "Enable SNMP Ethernet EVC delete traps";
                    type empty;
                  }
                  leaf status {
                    description
                      "Enable SNMP Ethernet EVC status traps";
                    type empty;
                  }
                }
              }
              leaf event-manager {
                description
                  "Enable SNMP Embedded Event Manager traps";
                tailf:cli-full-command;
                type empty;
              }
              container firewall {
                tailf:cli-delete-when-empty;
                presence "true";
                leaf serverstatus {
                  type empty;
                }
              }
              container flash {
                description
                  "Enable SNMP FLASH notifications";
                tailf:cli-delete-when-empty;
                presence "true";
                leaf insertion {
                  description
                    "Enable SNMP Flash Insertion notifications";
                  type empty;
                }
                leaf removal {
                  description
                    "Enable SNMP Flash Removal notifications";
                  type empty;
                }
              }
              leaf flowmon {
                description
                  "Enabel SNMP flowmon notifications";
                type empty;
              }
              container flex-links {
                description
                  "Enable SNMP FLEX Links traps";
                tailf:cli-delete-when-empty;
                presence "true";
                leaf status {
                  description
                    "Enable SNMP FLEX Links status change traps";
                  type empty;
                }
              }
              container frame-relay {
                description
                  "Enable SNMP frame-relay traps";
                tailf:cli-delete-when-empty;
                presence "true";
                container multilink {
                  description
                    "Enable MFR traps";
                  leaf bundle-mismatch {
                    description
                      "Enable MFR trap for inconsistent bundle event";
                    type empty;
                  }
                }
                container subif {
                  description
                    "Enable SNMP frame-relay subinterface traps";
                  tailf:cli-delete-when-empty;
                  presence "true";
                }
              }
              leaf fru-ctrl {
                description
                  "Enable SNMP entity FRU control traps";
                tailf:cli-full-command;
                type empty;
              }
              leaf gatekeeper {
                description
                  "Enable SNMP gatekeeper traps";
                tailf:cli-full-command;
                type empty;
              }
              leaf hsrp {
                description
                  "Enable SNMP HSRP traps";
                tailf:cli-full-command;
                type empty;
              }
              leaf icsudsu {
                description
                  "Enable SNMP ICSUDSU traps";
                tailf:cli-full-command;
                type empty;
              }
              leaf ima {
                description
                  "Enable SNMP ATM IMA traps";
                tailf:cli-full-command;
                type empty;
              }
              leaf ipmobile {
                description
                  "Enable SNMP ipmobile traps";
                tailf:cli-full-command;
                type empty;
              }
              leaf ipmulticast {
                description
                  "Enable SNMP ipmulticast traps";
                tailf:cli-full-command;
                type empty;
              }
              container ipsec {
                description
                  "Enable IPsec traps";
                container cryptomap {
                  leaf add {
                    description
                      "Enable IPsec Cryptomap add trap";
                    tailf:cli-full-command;
                    type empty;
                  }
                  leaf attach {
                    description
                      "Enable IPsec Cryptomap Attach trap";
                    tailf:cli-full-command;
                    type empty;
                  }
                  leaf delete {
                    description
                      "Enable IPsec Cryptomap delete trap";
                    tailf:cli-full-command;
                    type empty;
                  }
                  leaf detach {
                    description
                      "Enable IPsec Cryptomap Detach trap";
                    tailf:cli-full-command;
                    type empty;
                  }
                }
                container tunnel {
                  description
                    "Enable IPsec Tunnel traps";
                  leaf start {
                    description
                      "Enable IPsec Tunnel Start trap";
                    tailf:cli-full-command;
                    type empty;
                  }
                  leaf stop {
                    description
                      "Enable IPsec Tunnel Stop trap";
                    tailf:cli-full-command;
                    type empty;
                  }
                }
                leaf too-many-sas {
                  description
                    "Enable IPsec Tunnel Start trap";
                  type empty;
                }
              }
              container isakmp {
                description
                  "Enable ISAKMP traps traps";
                container policy {
                  description
                    "Enable ISAKMP traps";
                  leaf add {
                    description
                      "Enable ISAKMP Policy add trap";
                    type empty;
                  }
                  leaf delete {
                    description
                      "Enable ISAKMP Policy delete trap";
                    type empty;
                  }
                }
                container tunnel {
                  description
                    "Enable ISAKMP Tunnel traps";
                  leaf start {
                    description
                      "Enable ISAKMP Tunnel start trap";
                    type empty;
                  }
                  leaf stop {
                    description
                      "Enable ISAKMP Tunnel stop trap";
                    type empty;
                  }
                }
              }
              container isdn {
                description
                  "Enable SNMP isdn traps";
                tailf:cli-delete-when-empty;
                presence "true";
                leaf call-information {
                  description
                    "Enable SNMP isdn call information traps";
                  type empty;
                }
                leaf chan-not-avail {
                  description
                    "Enable SNMP isdn channel not avail traps";
                  type empty;
                }
                leaf ietf {
                  description
                    "Enable SNMP isdn ietf traps";
                  type empty;
                }
                leaf layer2 {
                  description
                    "Enable SNMP isdn layer2 transition traps";
                  type empty;
                }
              }
              leaf ipsla {
                description
                  "Enable IPSLA traps traps";
                tailf:cli-full-command;
                type empty;
              }
              leaf isis {
                description
                  "Enable ISIS traps traps";
                tailf:cli-full-command;
                type empty;
              }
              container l2tc {
                description
                  "Enable SNMP L2 Tunnel Config traps";
                tailf:cli-delete-when-empty;
                presence "true";
                tailf:cli-compact-syntax;
                leaf sys-threshold {
                  description
                    "Enable SNMP L2TC System threshold traps";
                  type empty;
                }
                leaf threshold {
                  description
                    "Enable SNMP L2 Tunnel Config threshold traps";
                  type empty;
                }
              }
              container l2tun {
                description
                  "Enable SNMP L2 tunnel protocol traps";
                leaf session {
                  description
                    "Enable SNMP l2tun session traps";
                  tailf:cli-full-command;
                  type empty;
                }
                container pseudowire {
                  leaf status {
                    type empty;
                  }
                }
              }
              container license {
                description
                  "Enable license traps";
                tailf:cli-compact-syntax;
                leaf deploy {
                  description
                    "Enable license deployment traps";
                  //tailf:cli-show-no;
                  type empty;
                }
                leaf error {
                  description
                    "Enable license error traps";
                  type empty;
                }
                leaf usage {
                  description
                    "Enable license usage traps";
                  type empty;
                }
              }
              container mac-notification {
                description
                  "Enable SNMP MAC Notification traps";
                tailf:cli-compact-syntax;
                tailf:cli-delete-when-empty;
                presence "true";
                leaf change {
                  description
                    "Enable SNMP Change traps";
                  type empty;
                }
                leaf move {
                  description
                    "Enable SNMP Move traps";
                  type empty;
                }
                leaf threshold {
                  description
                    "Enable SNMP Threshold traps";
                  type empty;
                }
              }
              container mac-notification2 {
                tailf:alt-name "MAC-Notification";
                description
                  "Enable SNMP MAC Notification traps";
                tailf:cli-delete-when-empty;
                presence "true";
                leaf change {
                  description
                    "Enable SNMP Change traps";
                  type empty;
                }
                leaf move {
                  description
                    "Enable SNMP Move traps";
                  type empty;
                }
                leaf threshold {
                  description
                    "Enable SNMP Threshold traps";
                  type empty;
                }
              }
              container memory {
                description
                  "Enable SNMP Memory traps";
                presence "true";
                leaf bufferpeak {
                  description
                    "Enable SNMP Memory Bufferpeak traps";
                  tailf:cli-full-command;
                  type empty;
                }
              }
              leaf module {
                description
                  "Enable SNMP module traps";
                type empty;
              }
              // snmp-server enable traps mpls
              container mpls {
                description
                  "Enable SNMP MPLS traps";
                tailf:cli-delete-when-empty;
                presence "true";
                container traffic-eng {
                  tailf:cli-delete-when-empty;
                  presence "true";
                }
                // snmp-server enable traps mpls fast-reroute
                container fast-reroute {
                  tailf:cli-delete-when-empty;
                  presence "true";
                  leaf protected {
                    type empty;
                  }
                }
                container rfc {
                  tailf:cli-delete-when-empty;
                  presence "true";
                  leaf ldp {
                    type empty;
                  }
                }
                container ldp {
                  description
                    "SNMP MPLS label distribution protocol traps";
                  tailf:cli-delete-when-empty;
                  presence "true";
                  leaf pv-limit {
                    description
                      "Enable MPLS LDP path vector limit mismatch traps";
                    type empty;
                  }
                  leaf session-down {
                    description
                      "Enable MPLS LDP session down traps";
                    type empty;
                  }
                  leaf session-up {
                    description
                      "Enable MPLS LDP session up traps";
                    type empty;
                  }
                  leaf threshold {
                    description
                      "Enable MPLS LDP threshold exceeded traps";
                    type empty;
                  }
                }
                leaf vpn {
                  type empty;
                }
              }
              leaf msdp {
                description
                  "Enable SNMP MSDP traps";
                tailf:cli-full-command;
                type empty;
              }
              leaf mvpn {
                description
                  "Enable Multicast Virtual Private Networks traps";
                tailf:cli-full-command;
                type empty;
              }
              container nhrp {
                tailf:cli-delete-when-empty;
                presence "true";
                container nhs {
                  presence "true";
                }
                container nhc {
                  presence "true";
                }
                container nhp {
                  presence "true";
                }
                container quota-exceeded {
                  presence "true";
                }
              }
              container ospf {
                description
                  "Enable OSPF traps";
                container state-change {
                  description
                    "State change traps";
                  tailf:cli-delete-when-empty;
                  presence "true";
                  leaf if-state-change {
                    description
                      "Non-virtual interface state changes";
                    type empty;
                  }
                  leaf neighbor-state-change {
                    description
                      "Non-virtual neighbor state changes";
                    type empty;
                  }
                  leaf virtif-state-change {
                    description
                      "Virtual interface state changes";
                    type empty;
                  }
                  leaf virtneighbor-state-change {
                    description
                      "Non-virtual neighbor state changes";
                    type empty;
                  }
                }
                container errors {
                  description
                    "Error traps";
                  tailf:cli-delete-when-empty;
                  presence "true";
                }
                container retransmit {
                  description
                    "Packet retransmit traps";
                  tailf:cli-delete-when-empty;
                  presence "true";
                  leaf packets {
                    description
                      "Packet retransmission on non-virtual interfaces";
                    type empty;
                  }
                  leaf virt-packets {
                    description
                      "Packet retransmission on virtual interfaces";
                    type empty;
                  }
                }
                container lsa {
                  description
                    "Lsa related traps";
                  tailf:cli-delete-when-empty;
                  presence "true";
                  leaf lsa-maxage {
                    description
                      "Lsa aged to maxage";
                    type empty;
                  }
                  leaf lsa-originate {
                    description
                      "New lsa originated";
                    type empty;
                  }
                }
                container cisco-specific {
                  description
                    "Cisco specific traps";
                  tailf:cli-delete-when-empty;
                  presence "true";
                  container state-change {
                    description
                      "State change traps";
                    tailf:cli-delete-when-empty;
                    presence "true";
                    leaf nssa-trans-change {
                      description
                        "Nssa translator state changes";
                      type empty;
                    }
                    container shamlink {
                      description
                        "Sham link state change traps";
                      tailf:cli-delete-when-empty;
                      presence "true";
                      leaf interface {
                        description
                          "Sham link interface state changes";
                        type empty;
                      }
                      leaf interface-old {
                        description
                          "Sham link interface state changes (deprecated)";
                        type empty;
                      }
                      leaf neighbor {
                        description
                          "Sham link neighbor state changes";
                        type empty;
                      }
                    }
                  }
                  container errors {
                    description
                      "Error traps";
                    tailf:cli-delete-when-empty;
                    presence "true";
                  }
                  container errdisable {
                    description
                      "Enable SNMP errdisable notifications";
                    tailf:cli-delete-when-empty;
                    presence "true";
                    leaf notification-rate {
                      description
                        "Number of notifications per minute";
                      type uint16 {
                        range "0..10000";
                      }
                    }
                  }
                  container retransmit {
                    description
                      "Packet retransmit traps";
                    tailf:cli-delete-when-empty;
                    presence "true";
                  }
                  container lsa {
                    description
                      "Lsa related traps";
                    tailf:cli-delete-when-empty;
                    presence "true";
                    leaf lsa-maxage {
                      description
                        "Lsa aged to maxage";
                      type empty;
                    }
                    leaf lsa-originate {
                      description
                        "New lsa originated";
                      type empty;
                    }
                  }
                }
              }
              container pim {
                description
                  "Enable SNMP PIM traps";
                tailf:cli-delete-when-empty;
                presence "true";
                leaf invalid-pim-message {
                  description
                    "Enable invalid pim message trap";
                  type empty;
                }
                leaf neighbor-change {
                  description
                    "Enable neighbor change trap";
                  type empty;
                }
                leaf rp-mapping-change {
                  description
                    "Enable rp mapping change trap";
                  type empty;
                }
              }
              container plogd {
                description
                  "Enable SNMP plogd traps";
                presence "true";
              }
              container port-security {
                description
                  "Enable SNMP port security traps";
                tailf:cli-delete-when-empty;
                presence "true";
                leaf trap-rate {
                  description
                    "Number of traps per second";
                  type uint16 {
                    range "0..1000";
                  }
                }
              }
              container power-ethernet {
                description
                  "Enable SNMP power ethernet traps";
                leaf group {
                  description
                    "Enable SNMP inline power group based traps";
                  type string;
                }
                leaf police {
                  description
                    "Enable Policing Trap";
                  type empty;
                }
              }
              leaf pppoe {
                description
                  "Enable SNMP pppoe traps";
                tailf:cli-full-command;
                type empty;
              }
              container pw {
                tailf:cli-delete-when-empty;
                presence "true";
                leaf vc {
                  type empty;
                }
              }
              leaf rep {
                tailf:cli-full-command;
                type empty;
              }
              leaf resource-policy {
                tailf:cli-full-command;
                type empty;
              }
              leaf rf {
                description
                  "Enable all SNMP traps defined in CISCO-RF-MIB";
                tailf:cli-full-command;
                type empty;
              }
              leaf rogue-ap {
                description
                  "Enable SNMP 802.11 Rogue AP Trap";
                tailf:cli-full-command;
                type empty;
              }
              leaf rsvp {
                description
                  "Enable RSVP flow change traps";
                tailf:cli-full-command;
                type empty;
              }
              leaf rtr {
                description
                  "Enable SNMP Response Time Reporter traps";
                tailf:cli-full-command;
                type empty;
              }
              container slb {
                description
                  "Enable SNMP SLB traps";
                tailf:cli-delete-when-empty;
                presence "true";
                leaf csrp {
                  description
                    "Enable SNMP SLB Fault Tolerance Replication Protocol traps";
                  type empty;
                }
                leaf real {
                  description
                    "Enable SNMP SLB Real Server traps";
                  type empty;
                }
                leaf virtual {
                  description
                    "Enable SNMP SLB Virtual Server traps";
                  type empty;
                }
              }
              container snmp {
                description
                  "Enable SNMP traps";
                tailf:cli-compact-syntax;
                leaf authentication {
                  description
                    "Enable authentication trap";
                  type empty;
                }
                leaf coldstart {
                  description
                    "Enable coldStart trap";
                  type empty;
                }
                leaf linkdown {
                  description
                    "Enable linkDown trap";
                  type empty;
                }
                leaf linkup {
                  description
                    "Enable linkUp trap";
                  type empty;
                }
                leaf warmstart {
                  description
                    "Enable warmStart trap";
                  type empty;
                }
              }
              leaf sonet {
                description
                  "Enable SNMP SONET traps";
                type empty;
              }
              leaf srst {
                tailf:cli-full-command;
                type empty;
              }
              leaf srp {
                description
                  "Enable SRP protocol traps";
                tailf:cli-full-command;
                type empty;
              }
              container stackwise {
                description
                  "Enable SNMP stackwise traps";
                tailf:cli-delete-when-empty;
                presence "true";
                leaf GLS {
                  description
                    "Enable STACKWISE stack power GLS trap";
                  type empty;
                }
                leaf ILS {
                  description
                    "Enable STACKWISE stack power ILS trap";
                  type empty;
                }
                leaf SRLS {
                  description
                    "Enable STACKWISE stack power SRLS trap";
                  type empty;
                }
                leaf insufficient-power {
                  description
                    "Enable STACKWISE stack power unbalanced power supplies trap";
                  type empty;
                }
                leaf invalid-input-current {
                  description
                    "Enable STACKWISE stack power invalid input current trap";
                  type empty;
                }
                leaf invalid-output-current {
                  description
                    "Enable STACKWISE stack power invalid output current trap";
                  type empty;
                }
                leaf member-removed {
                  description
                    "Enable STACKWISE stack member removed trap";
                  type empty;
                }
                leaf member-upgrade-notification {
                  description
                    "Enable STACKWISE member to be reloaded for upgrade trap";
                  type empty;
                }
                leaf new-master {
                  description
                    "Enable STACKWISE new master trap";
                  type empty;
                }
                leaf new-member {
                  description
                    "Enable STACKWISE stack new member trap";
                  type empty;
                }
                leaf port-change {
                  description
                    "Enable STACKWISE port change trap";
                  type empty;
                }
                leaf power-budget-warning {
                  description
                    "Enable STACKWISE stack power budget warning trap";
                  type empty;
                }
                leaf power-invalid-topology {
                  description
                    "Enable STACKWISE stack power invalid topology trap";
                  type empty;
                }
                leaf power-link-status-changed {
                  description
                    "Enable STACKWISE stack power link status changed trap";
                  type empty;
                }
                leaf power-oper-status-changed {
                  description
                    "Enable STACKWISE stack power port oper status changed trap";
                  type empty;
                }
                leaf power-priority-conflict {
                  description
                    "Enable STACKWISE stack power priority conflict trap";
                  type empty;
                }
                leaf power-version-mismatch {
                  description
                    "Enable STACKWISE stack power version mismatch discovered trap";
                  type empty;
                }
                leaf ring-redundant {
                  description
                    "Enable STACKWISE stack ring redundant trap";
                  type empty;
                }
                leaf stack-mismatch {
                  description
                    "Enable STACKWISE stack mismatch trap";
                  type empty;
                }
                leaf unbalanced-power-supplies {
                  description
                    "Enable STACKWISE stack power unbalanced power supplies trap";
                  type empty;
                }
                leaf under-budget {
                  description
                    "Enable STACKWISE stack power under budget trap";
                  type empty;
                }
                leaf under-voltage {
                  description
                    "Enable STACKWISE stack power under voltage trap";
                  type empty;
                }
              }
              container stpx {
                tailf:cli-delete-when-empty;
                tailf:cli-compact-syntax;
                presence "true";
                leaf inconsistency {
                  type empty;
                }
                leaf root-inconsistency {
                  type empty;
                }
                leaf loop-inconsistency {
                  type empty;
                }
              }
              leaf stun {
                description
                  "Enable SNMP STUN traps";
                tailf:cli-full-command;
                type empty;
              }
              leaf switch-over {
                description
                  "Enable SNMP 802.11 Standby Switch-over Trap";
                tailf:cli-full-command;
                type empty;
              }
              leaf syslog {
                description
                  "Enable SNMP syslog traps";
                tailf:cli-full-command;
                type empty;
              }
              container transceiver {
                leaf all {
                  type empty;
                }
              }
              leaf tty {
                description
                  "Enable TCP connection traps";
                tailf:cli-full-command;
                type empty;
              }
              container udld {
                description
                  "Enable SNMP CISCO-UDLDP-MIB traps";
                tailf:cli-compact-syntax;
                tailf:cli-delete-when-empty;
                presence "true";
                leaf link-fail-rpt {
                  description
                    "Enable SNMP cudldpFastHelloLinkFailRptNotification traps";
                  type empty;
                }
                leaf status-change {
                  description
                    "Enable SNMP cudldpFastHelloStatusChangeNotification traps";
                  type empty;
                }
              }
              leaf vlancreate {
                tailf:cli-full-command;
                type empty;
              }
              leaf vlandelete {
                tailf:cli-full-command;
                type empty;
              }
              leaf vlan-mac-limit {
                description
                  "Enable SNMP L2 Control VLAN MAC Limit notifications";
                type empty;
              }
              leaf vlan-membership {
                tailf:cli-full-command;
                type empty;
              }
              leaf voice {
                description
                  "Enable SNMP voice traps";
                tailf:cli-full-command;
                type empty;
              }
              container vrfmib {
                leaf vrf-up {
                  type empty;
                }
                leaf vrf-down {
                  type empty;
                }
                leaf vnet-trunk-up {
                  type empty;
                }
                leaf vnet-trunk-down {
                  type empty;
                }
              }
              leaf vrrp {
                description
                  "Enable SNMP vrrp traps";
                tailf:cli-full-command;
                type empty;
              }
              leaf vsimaster {
                description
                  "Allow SNMP vsimaster traps";
                tailf:cli-full-command;
                type empty;
              }
              container vstack {
                description
                  "Enable SNMP Smart Install traps";
                tailf:cli-delete-when-empty;
                presence "true";
                tailf:cli-compact-syntax;
                leaf addition {
                  description
                    "Enable client added trap";
                  type empty;
                }
                leaf failure {
                  description
                    "Enable file upload/download failure trap";
                  type empty;
                }
                leaf lost {
                  description
                    "Enable client lost trap";
                  type empty;
                }
                leaf operation {
                  description
                    "Enable operation mode change trap";
                  type empty;
                }
              }
              leaf vtp {
                tailf:cli-full-command;
                type empty;
              }
              leaf wlan-wep {
                description
                  "Enable SNMP 802.11 WLAN WEP Trap";
                tailf:cli-full-command;
                type empty;
              }
              leaf xgcp {
                description
                  "Enable XGCP protocol traps";
                tailf:cli-full-command;
                type empty;
              }
            }
          }
        }
      }
      // snmp-server engine-id
      container engineID {
        description
          "Configure a local or remote SNMPv3 engineID";
        leaf local {
          description
            "engineID of the local agent";
          type string {
            length "1..24";
          }
        }
        container remote;
      }
      // file-transfer     File transfer related commands

      // snmp-server group *
      list group {
        description
          "Define a User Security Model group";
        tailf:cli-suppress-mode;
        tailf:cli-delete-when-empty;
        tailf:cli-compact-syntax;
        tailf:cli-sequence-commands;
        key "id";
        leaf id {
          type string;
        }
        choice security-model {
          container v1;
          container v2c;
          container v3 {
            description
              "group using the User Security Model (SNMPv3)";
            tailf:cli-compact-syntax;
            tailf:cli-sequence-commands {
              tailf:cli-reset-siblings;
            }
            leaf security-level {
              tailf:cli-drop-node-name;
              type enumeration {
                enum "auth";
                enum "noauth";
                enum "priv";
              }
            }
            leaf context {
              tailf:cli-optional-in-sequence;
              description
                "specify a context to associate these views for the group";
              type string;
            }
            leaf match {
              tailf:cli-optional-in-sequence;
              description
                "context name match criteria";
              type enumeration {
                enum "exact";
                enum "prefix";
              }
            }
            leaf read {
              tailf:cli-optional-in-sequence;
              description
                "specify a read view for the group";
              type string;
            }
            leaf write {
              tailf:cli-optional-in-sequence;
              description
                "specify a write view for the group";
              type string;
            }
            leaf notify {
              tailf:cli-optional-in-sequence;
              description
                "specify a notify view for the group";
              type string;
            }
            leaf access {
              description
                "specify an access-list associated with this group";
              type union {
                type uint8 {
                  range "1..99";
                }
                type string;
              }
            }
          }
        }
      }// snmp-server host *
      list host {
        description
          "Specify hosts to receive SNMP notifications";
        tailf:cli-suppress-mode;
        tailf:cli-delete-when-empty;
        key "ip-address community-string";
        leaf ip-address {
          type host-type;
        }
        // snmp-server host * community-string
        leaf community-string {
          type string;
        }
        leaf vrf {
          description
            "VPN Routing instance for this host";
          tailf:cli-diff-dependency "/ios:native/ip/vrf";
          tailf:cli-diff-dependency "/ios:native/vrf/definition";
          tailf:cli-prefix-key {
            tailf:cli-before-key "2";
          }
          type string;
        }
        choice informs-traps-choice {
          leaf informs {
            description
              "Send Inform messages to this host";
            tailf:cli-prefix-key {
              tailf:cli-before-key "2";
            }
            type empty;
          }
          leaf traps {
            description
              "Send Trap messages to this host";
            tailf:cli-prefix-key {
              tailf:cli-before-key "2";
            }
            type empty;
          }
        }
        // snmp-server host * version
        leaf version {
          description
            "SNMP version to use for notification messages";
          tailf:cli-prefix-key {
            tailf:cli-before-key "2";
          }
          type enumeration {
            enum "1";
            enum "2c";
            enum "3";
          }
        }
        leaf security-level {
          when "../version = '3'";
          tailf:cli-drop-node-name;
          tailf:cli-prefix-key {
            tailf:cli-before-key "2";
          }
          type enumeration {
            enum "auth";
            enum "noauth";
            enum "priv";
          }
        }
        container trap-enable {
          tailf:cli-drop-node-name;
          leaf aaa_server {
            description
              "Allow SNMP AAA traps";
            type empty;
          }
          leaf alarms {
            description
              "Allow SNMP alarms traps";
            type empty;
          }
          leaf atm {
            description
              "Allow SNMP atm traps";
            type empty;
          }
          leaf bfd {
            description
              "Allow SNMP BFD traps";
            type empty;
          }
          leaf bgp {
            description
              "Allow BGP state change traps";
            type empty;
          }
          leaf bstun {
            description
              "Allow bstun event traps";
            type empty;
          }
          leaf bulkstat {
            description
              "Allow Data-Collection-MIB traps";
            type empty;
          }
          leaf call-home {
            description
              "Allow SNMP CISCO-CALLHOME-MIB traps";
            type empty;
          }
          leaf casa {
            description
              "Allow casa event traps";
            type empty;
          }
          leaf cef {
            description
              "Allows cef traps";
            type empty;
          }
          leaf cnpd {
            description
              "Allow NBAR Protocol Discovery traps";
            type empty;
          }
          leaf config {
            description
              "Allow SNMP config traps";
            type empty;
          }
          leaf config-copy {
            description
              "Allow SNMP config-copy traps";
            type empty;
          }
          leaf config-ctid {
            description
              "Allow SNMP config-ctid traps";
            type empty;
          }
          leaf cpu {
            description
              "Allow cpu related traps";
            type empty;
          }
          leaf dhcp {
            description
              "Allow dhcp traps";
            type empty;
          }
          leaf dlsw {
            description
              "Allow dlsw traps";
            type empty;
          }
          leaf ds1 {
            description
              "Allow SNMP ds1 traps";
            type empty;
          }
          leaf dsp {
            description
              "Allow SNMP DSP traps";
            type empty;
          }
          leaf dspu {
            description
              "Allow dspu event traps";
            type empty;
          }
          leaf eigrp {
            description
              "Allow SNMP EIGRP traps";
            type empty;
          }
          leaf entity {
            description
              "Allow SNMP entity traps";
            type empty;
          }
          leaf entity-diag {
            description
              "Allow SNMP CISCO-ENTITY-DIAG-MIB traps";
            type empty;
          }
          leaf entity-qfp {
            description
              "Allow SNMP CISCO-ENTITY-QFP-MIB traps";
            type empty;
          }
          leaf entity-state {
            description
              "Allow ENTITY-STATE-MIB traps";
            type empty;
          }
          leaf ethernet-cfm {
            description
              "Allow SNMP Ethernet CFM traps";
            type empty;
          }
          leaf evc {
            description
              "Allow SNMP EVC traps";
            type empty;
          }
          leaf event-manager {
            description
              "Allow SNMP Embedded Event Manager traps";
            type empty;
          }
          leaf firewall {
            description
              "Allow SNMP Firewall traps";
            type empty;
          }
          leaf flash {
            description
              "Allow SNMP FLASH traps";
            type empty;
          }
          leaf flowmon {
            description
              "Allow SNMP flow monitor notifications";
            type empty;
          }
          leaf frame-relay {
            description
              "Allow SNMP frame-relay traps";
            type empty;
          }
          leaf fru-ctrl {
            description
              "Allow entity FRU control traps";
            type empty;
          }
          leaf gdoi {
            description
              "Allows gdoi traps";
            type empty;
          }
          leaf hsrp {
            description
              "Allow SNMP HSRP traps";
            type empty;
          }
          leaf iplocalpool {
            description
              "Allow SNMP IP Local Pool traps";
            type empty;
          }
          leaf ipmulticast {
            description
              "Allow SNMP ipmulticast traps";
            type empty;
          }
          leaf ipsec {
            description
              "Allow SNMP IPsec traps";
            type empty;
          }
          leaf ipsla {
            description
              "Allow SNMP Host IP SLA traps";
            type empty;
          }
          leaf isakmp {
            description
              "Allow SNMP ISAKMP traps";
            type empty;
          }
          leaf isg-mib {
            description
              "Allow SNMP isgmib traps";
            type empty;
          }
          leaf isis {
            description
              "Allow IS-IS traps";
            type empty;
          }
          leaf l2tun-pseudowire-status {
            description
              "Allow SNMP L2 pseudowire status traps";
            type empty;
          }
          leaf l2tun-session {
            description
              "Allow SNMP L2 session traps";
            type empty;
          }
          leaf license {
            description
              "Allow license traps";
            type empty;
          }
          leaf memory {
            description
              "Allow SNMP Mempool traps";
            type empty;
          }
          leaf mpls-fast-reroute {
            description
              "Allow SNMP MPLS traffic engineering fast reroute traps";
            type empty;
          }
          leaf mpls-ldp {
            description
              "Allow SNMP MPLS label distribution protocol traps";
            type empty;
          }
          leaf mpls-traffic-eng {
            description
              "Allow SNMP MPLS traffic engineering traps";
            type empty;
          }
          leaf mpls-vpn {
            description
              "Allow SNMP MPLS Virtual Private Network traps";
            type empty;
          }
          leaf msdp {
            description
              "Allow SNMP MSDP traps";
            type empty;
          }
          leaf mvpn {
            description
              "Allow Multicast Virtual Private Network traps";
            type empty;
          }
          leaf nhrp {
            description
              "Allow SNMP NHRP traps";
            type empty;
          }
          leaf ospf {
            description
              "Allow OSPF traps";
            type empty;
          }
          leaf ospfv3 {
            description
              "Allow OSPFv3 traps";
            type empty;
          }
          leaf pfr {
            description
              "Allow SNMP PfR traps";
            type empty;
          }
          leaf pim {
            description
              "Allow SNMP PIM traps";
            type empty;
          }
          leaf pw-vc {
            description
              "Allow SNMP Pseudowire VC traps";
            type empty;
          }
          leaf resource-policy {
            description
              "Enable CISCO-ERM-MIB notifications";
            type empty;
          }
          leaf rf {
            description
              "Allow all SNMP traps defined in CISCO-RF-MIB";
            type empty;
          }
          leaf rsrb {
            description
              "Allow rsrb event traps";
            type empty;
          }
          leaf rsvp {
            description
              "Allow RSVP flow change traps";
            type empty;
          }
          leaf sdlc {
            description
              "Allow sdlc event traps";
            type empty;
          }
          leaf sdllc {
            description
              "Allow sdllc event traps";
            type empty;
          }
          leaf snmp {
            description
              "Allow SNMP-type notifications";
            type empty;
          }
          leaf sonet {
            description
              "Allow SNMP SONET traps";
            type empty;
          }
          leaf srp {
            description
              "Allow SRP protocol traps";
            type empty;
          }
          leaf stun {
            description
              "Allow stun event traps";
            type empty;
          }
          leaf syslog {
            description
              "Allow SNMP syslog traps";
            type empty;
          }
          leaf trustsec-sxp {
            description
              "Allow SNMP CISCO-TRUSTSEC-SXP-MIB traps";
            type empty;
          }
          leaf tty {
            description
              "Allow TCP connection traps";
            type empty;
          }
          leaf udp-port {
            description
              "The notification host's UDP port number (default port 162)";
            type uint16;
          }
          leaf voice {
            description
              "Allow SNMP Voice traps";
            type empty;
          }
          leaf vrfmib {
            description
              "Allow SNMP vrfmib traps";
            type empty;
          }
          leaf vrrp {
            description
              "Allow SNMP vrrp traps";
            type empty;
          }
          leaf x25 {
            description
              "Allow x25 event traps";
            type empty;
          }
        }
      }
      // snmp-server ip
      container ip {
        description
          "IP ToS configuration for SNMP traffic";
        leaf dscp {
          description
            "IP DSCP value for SNMP traffic";
          type uint8 {
            range "0..63";
          }
        }
        // snmp-server ip precedence
        leaf precedence {
          description
            "IP Precedence value for SNMP traffic";
          tailf:cli-full-command;
          type uint8 {
            range "0..7";
          }
        }
      }
      // snmp-server ifindex
      container ifindex {
        description
          "Enable ifindex persistence";
        leaf persist {
          description
            "Persist interface indices";
          type empty;
        }
      }
      // inform            Configure SNMP Informs options

      // snmp-server location
      leaf location {
        description
          "Text for mib object sysLocation";
        tailf:cli-multi-value;
        type string;
      }
      // snmp-server manager
      container manager {
        description
          "Modify SNMP manager parameters";
        tailf:cli-display-separated;
        presence "true";
        leaf session-timeout {
          description
            "Timeout value for destroying sessions";
          type uint32 {
            range "10..2147483";
          }
        }
      }
      // snmp-server packetsize        Largest SNMP packet size
      leaf packetsize {
        description
          "Largest SNMP packet size";
        tailf:cli-full-command;
        type uint32 {
          range "484..17924";
        }
      }
      // snmp-server queue-length
      leaf queue-length {
        description
          "Message queue length for each TRAP host";
        type uint16 {
          range "1..5000";
        }
      }
      // snmp-server source-interface
      container source-interface {
        description
          "Assign an source interface";
        container informs {
          description
            "source interface for informs";
          tailf:cli-diff-dependency "/ios:native/interface";
          uses interface-grouping;
        }
        container traps {
          description
            "source interface for traps";
          tailf:cli-diff-dependency "/ios:native/interface";
          uses interface-grouping;
        }
      }
      // snmp-server system-shutdown   Enable use of the SNMP reload command
      leaf system-shutdown {
        description
          "Enable use of the SNMP reload command";
        tailf:cli-full-command;
        type empty;
      }
      // snmp-server tftp-server-list  Limit TFTP servers used via SNMP
      leaf tftp-server-list {
        description
          "Limit TFTP servers used via SNMP";
        type union {
          type uint8 {
            range "1..99";
          }
          type string;
        }
      }
      // snmp-server trap
      container trap {
        description
          "SNMP trap options";
        container link {
          description
            "Assign/Enable SNMP link traps";
          leaf ietf {
            description
              "Use IETF standard for SNMP traps";
            tailf:cli-full-command;
            type empty;
          }
          leaf switchover {
            description
              "Enable link up/down traps during switchover";
            tailf:cli-full-command;
            type empty;
          }
        }
        leaf timeout {
          description
            "Set timeout for TRAP message retransmissions";
          type uint16 {
            range "1..1000";
          }
        }
      }
      // snmp-server trap-source
      container trap-source {
        description
          "Assign an interface for the source address of all traps";
        tailf:cli-diff-dependency "/ios:native/interface";
        uses interface-grouping;
      }
      // trap-timeout      Set timeout for TRAP message retransmissions
      // user              Define a user who can access the SNMP engine

      // snmp-server view *
      list view {
        description
          "Define an SNMPv2 MIB view";
        tailf:cli-suppress-mode;
        tailf:cli-delete-when-empty;
        tailf:cli-compact-syntax;
        key "name mib";
        leaf name {
          type string;
        }
        leaf mib {
          type string;
        }
        leaf inc-exl {
          tailf:cli-drop-node-name;
          type enumeration {
            enum "excluded";
            enum "included";
          }
        }
      }
    }

    /// ========================================================================
    /// segment-routing
    /// ========================================================================
    container segment-routing {
      container mpls {
        tailf:cli-add-mode;
        tailf:cli-mode-name "config-srmpls";
        presence "true";
        container mcfg-srmpls {
          tailf:cli-drop-node-name;
          container connected-prefix-sid-map {
            tailf:cli-add-mode;
            tailf:cli-mode-name "config-srmpls-conn";
            presence "true";
            container mcfg-srmpls-conn {
              tailf:cli-drop-node-name;
              container address-family {
                container ipv4 {
                  tailf:cli-add-mode;
                  tailf:cli-mode-name "config-srmpls-conn-af";
                  presence "true";
                  tailf:cli-exit-command "exit-address-family";
                  container mcfg-srmpls-conn-af {
                    tailf:cli-drop-node-name;
                    uses srcfg-srmpls-conn-af;
                  }
                }
              }
            }
          }
          container global-block {
            tailf:cli-compact-syntax;
            tailf:cli-sequence-commands {
              tailf:cli-reset-siblings;
            }
            leaf range-start {
              tailf:cli-drop-node-name;
              type uint32 {
                range "16..1048575";
              }
            }
            leaf range-end {
              tailf:cli-drop-node-name;
              type uint32 {
                range "16..1048575";
              }
            }
          }
          container mapping-server {
            tailf:cli-add-mode;
            tailf:cli-mode-name "config-srmpls-mapserver";
            presence "true";
            container mcfg-srmpls-mapserver {
              tailf:cli-drop-node-name;
              container prefix-sid-map {
                tailf:cli-add-mode;
                tailf:cli-mode-name "config-srmpls-mapserver-sidmap";
                presence "true";
                container mcfg-srmpls-mapserver-sidmap {
                  tailf:cli-drop-node-name;
                  uses mcfg-srmpls-mapserver-sidmap;
                }
              }
            }
          }
          container set-attributes {
            tailf:cli-add-mode;
            tailf:cli-mode-name "config-srmpls-attr";
            presence "true";
            container mcfg-srmpls-attr {
              tailf:cli-drop-node-name;
              container address-family {
                container ipv4 {
                  tailf:cli-add-mode;
                  tailf:cli-mode-name "config-srmpls-attr-af";
                  presence "true";
                  container mcfg-srmpls-attr-af {
                    tailf:cli-drop-node-name;
                    uses srcfg-srmpls-attr-af;
                  }
                }
              }
            }
          }
          leaf shutdown {
            type empty;
          }
        }
      }
    }

    /// ========================================================================
    /// dot11
    /// ========================================================================
    container dot11 {
      description
        "IEEE 802.11 config commands";
      // dot11 syslog
      leaf syslog {
        description
          "Enable syslog";
        tailf:cli-full-command;
        type empty;
      }
    }

    /// ========================================================================
    /// license
    /// ========================================================================
    container license {
      description
        "Configure license features";
      // license udi
      container udi {
        tailf:cli-compact-syntax;
        tailf:cli-sequence-commands;
        tailf:cli-reset-container;
        leaf pid {
          type string;
        }
        leaf sn {
          type string;
        }
      }
      //license feature
      container feature {
        description
          "License features";
        leaf name {
          tailf:cli-drop-node-name;
          tailf:cli-disallow-value "port";
          type string;
        }
        container port {
          description
            "Enable Ports for IM";
          leaf bulk {
            description
              "Enable Bulk port licenes";
            tailf:cli-full-command;
            type empty;
          }
          leaf onegig {
            description
              "Enable 1G port bundles";
            type uint8 {
              range "1..2";
            }
          }
          leaf b-6xonegig {
            description
              "Enable 6x1G port bundles";
            tailf:alt-name "6xonegig";
            type uint8 {
              range "1..2";
            }
          }
          leaf tengig {
            description
              "Enable 10G port bundles";
            type uint8 {
              range "1..2";
            }
          }
        }
      }
      // license accept
      container accept {
        tailf:cli-compact-syntax;
        tailf:cli-sequence-commands {
          tailf:cli-reset-all-siblings;
        }
        leaf end {
          type empty;
        }
        leaf user {
          type empty;
        }
        leaf agreement {
          type empty;
        }
      }
      // license boot
      container boot {
        description
          "license boot config commands";
        container level {
          description
            "which level to boot";
	  choice license-choice {
	    case ipbase-case {
              container ipbase{
	        description
                  "ipbase level";
                tailf:cli-display-separated;
                presence "true";
                leaf switch {
                  description
                    "Switch license information";
                  type uint8;
                }
	      }
            }
	    case ipbasek9-case {
	      leaf ipbasek9 {
                description
                  "License Level IPBASEK9";
                type empty;
	      }
            }
	    case ipservices-case {
              container ipservices { 
	        description
                  "ipservices level";
                tailf:cli-display-separated;
                presence "true";
                leaf switch {
                  description
                    "Switch license information";
                  type empty;
                }
	      }
            }
	    case ipservicesk9-case {
              container ipservicesk9 {
	        description
                  "ipservicesk9 level";
                tailf:cli-display-separated;
                presence "true";
                leaf switch {
                  description
                    "Switch license information";
                  type empty;
                }
              }
	    }
	    case lanbase-case {
	      container lanbase {
                description
                  "lanbase level";
                tailf:cli-display-separated;
                presence "true";
                leaf switch {
                  description
                    "Switch license information";
                  type empty;
                }
	      }
            }
	    case lanbasek9-case {
	      leaf lanbasek9 {
                description
                  "License Level LANBASEK9";
                type empty;
	      }
            }
	    case lite-case {
	      container lite {
                description
                  "lite level";
                tailf:cli-display-separated;
                presence "true";
                leaf switch {
                  description
                    "Switch license information";
                  type empty;
                }
              }
	    }
	    case metroaggrservices-case {
	      container metroaggrservices {
                description
                  "metroaggrservices level";
                tailf:cli-display-separated;
                presence "true";
                leaf switch {
                  description
                    "Switch license information";
                  type empty;
                }
	      }
            }
	    case advancedmetroipaccess-case {
	      leaf advancedmetroipaccess {
                description
                  "Advanced Metro IP Access License Level";
                type empty;
	      }
            }
            case metroaccess-case {
	      leaf metroaccess {
                description
                  "Metro Access License Level";
                type empty;
	      }
            }
            case metroipaccess-case {
	      leaf metroipaccess {
                description
                  "Metro IP Access License Level";
                type empty;
	      }
            }
            case entservices-case {
              leaf entservices { 
	        description
                  "Entservices License Level";
                type empty;
	      }
            }
            case adventerprise-case {
              leaf adventerprise { 
	        description
                  "Adventerprise License Level";
                type empty;
	      }
            }
            case appxk9-case {
              leaf appxk9 {
	        description
                  "Appxk9 License Level";
                type empty;
	      }
            }
            case securityk9-case {
              leaf securityk9 {
	        description
                  "Securityk9 License Level";
                type empty;
	      }
            }
            case uck9-case {
              container uck9 {
	        description
                  "Uck9 License Level";
                presence "true";
                leaf disable {
                  type empty;
                }
              }	    
	    }
	  }
        }
        //license boot module
        container boot-module {
          tailf:cli-drop-node-name;
          tailf:cli-compact-syntax;
          tailf:cli-sequence-commands;
          leaf module {
            type enumeration {
              enum "c2900";
            }
          }
          container technology-package {
            leaf securityk9 {
              tailf:cli-full-command;
              type empty;
            }
            leaf uck9 {
              tailf:cli-full-command;
              type empty;
            }
            leaf datak9 {
              tailf:cli-full-command;
              type empty;
            }
          }
        }
      }
      leaf smart {
        type enumeration {
          enum "enable";
        }
      }
      //  call-home  license call-home config commands
    }

    /// ========================================================================
    /// cdp
    /// ========================================================================
    // Must be before interface * / cdp enable
    container cdp {
      description
        "Global CDP configuration subcommands";
      // no cdp run
      leaf run {
        description
          "Enable CDP";
        type empty;
      }
    }


    /// ========================================================================
    /// voice
    /// ========================================================================
    container voice {
      description
        "Global voice configuration";
      list service {
        description
          "Global packet telephony service commands";
        tailf:cli-mode-name "conf-voi-serv";
        key "type";
        leaf type {
          type enumeration {
            enum "pots";
            enum "saf";
            enum "voatm";
            enum "vofr";
            enum "voip";
          }
        }
        container fax {
          description
            "Global fax commands";
          tailf:cli-compact-syntax;
          leaf protocol {
            description
              "The system-wide fax protocol type";
            type enumeration {
              enum "cisco";
              enum "none";
              enum "pass-through";
              enum "t38";
            }
          }
          leaf fallback {
            description
              "fax transport to use if T.38 unsupported on far end";
            when "../protocol = 't38'";
            type enumeration {
              enum "cisco";
              enum "none";
              enum "pass-through";
            }
          }
          leaf codec {
            when "../protocol = 'pass-through' or ../fallback = 'pass-through'";
            tailf:cli-drop-node-name;
            type enumeration {
              enum "g711alaw";
              enum "g711ulaw";
            }
          }
          leaf ls-redundancy {
            description
              "t38 low speed redundancy";
            when "../protocol = 't38'";
            type uint8 {
              range "0..5";
            }
          }
          leaf hs-redundancy {
            description
              "t38 high speed redundancy";
            when "../protocol = 't38'";
            type uint8 {
              range "0..2";
            }
          }
          leaf version {
            description
              "t38 fax version";
            when "../protocol = 't38'";
            type enumeration {
              enum "0";
              enum "3";
            }
          }
        }
      }
    }

    /// ========================================================================
    /// voice-card
    /// ========================================================================
    list voice-card {
      description
        "Configure a specific voice-card";
      tailf:cli-mode-name "config-voicecard";
      key "slot";
      leaf slot {
        type uint8 {
          range "0..2";
        }
      }
    }
 
    /// ========================================================================
    /// card
    /// ========================================================================
    container card {
      tailf:cli-reset-container;
      tailf:cli-compact-syntax;
      tailf:cli-sequence-commands;
      leaf type {
        tailf:cli-incomplete-command;
        tailf:cli-remove-before-change;
        type enumeration {
          enum "t1";
          enum "e1";
        }
      }
      leaf slot {
        tailf:cli-drop-node-name;
        type uint32;
      }
      leaf bay {
        tailf:cli-drop-node-name;
        type uint32;
      }
    }
    


    /// ========================================================================
    /// event
    /// ========================================================================
    container event {
      description
        "Event related configuration commands";
      // event manager
      container manager {
        description
          "Event Manager configuration commands";
        // event manager environment *
        list environment {
          description
            "Set an Embedded Event Manager global environment variable";
          tailf:cli-suppress-mode;
          tailf:cli-delete-when-empty;
          key "name";
          leaf name {
            type string;
          }
          leaf value {
            tailf:cli-drop-node-name;
            type string;
          }
        }
        // event manager directory
        container directory {
          description
            "Set Embedded Event Manager directory information";
          container user {
            description
              "Set Embedded Event Manager user directory information";
            leaf policy {
              description
                "Set Embedded Event Manager user policy directory";
              type string;
            }
          }
        }
        // event manager applet *
        list applet {
          description
            "Register an Event Manager applet";
          tailf:cli-mode-name "config-applet";
          tailf:cli-exit-command "exit";
          key "name";
          leaf name {
            type string;
          }
          leaf authorization {
            description
              "Specify an authorization type for the applet";
            tailf:cli-hide-in-submode;
            type enumeration {
              enum "bypass";
            }
          }
          leaf class {
            description
              "Specify a class for the applet";
            tailf:cli-hide-in-submode;
            type string {
              pattern "[A-Z]|default";
            }
          }
          leaf trap {
            description
              "Generate an SNMP trap when applet is triggered.";
            tailf:cli-hide-in-submode;
            type empty;
          }
          container event {
            description
              "Add or modify event information";
            container snmp-notification {
              description
                "SNMP Notification Event";
              tailf:cli-compact-syntax;
              tailf:cli-reset-container;
              leaf oid {
                description
                  "Object ID of data element";
                type string;
              }
              leaf oid-val {
                description
                  "Comparison value";
                type string;
              }
              leaf op {
                description
                  "Operator";
                type operator-type;
              }
              leaf src-ip-address {
                description
                  "Source ip address";
                type union {
                  type inet:ipv4-address;
                  type inet:ipv6-address;
                }
              }
              leaf dest-ip-address {
                description
                  "Destination ip address";
                type union {
                  type inet:ipv4-address;
                  type inet:ipv6-address;
                }
              }
            }
            container syslog {
              description
                "Syslog event";
              leaf pattern {
                description
                  "Pattern match string for the entire message";
                type string;
              }
            }
          }
          list action {
            description
              "Add or modify an action statement";
            tailf:cli-suppress-mode;
            tailf:cli-delete-when-empty;
            tailf:cli-incomplete-command;
            tailf:cli-compact-syntax;
            tailf:cli-reset-container;
            ordered-by user;
            key "name";
            leaf name {
              type string;
            }
            container if {
              description
                "if conditional";
              tailf:cli-compact-syntax;
              tailf:cli-sequence-commands;
              tailf:cli-reset-container;
              leaf string-op-1 {
                tailf:cli-drop-node-name;
                tailf:cli-incomplete-command;
                type string;
              }
              leaf keyword {
                tailf:cli-drop-node-name;
                tailf:cli-incomplete-command;
                type operator-type;
              }
              leaf string-op-2 {
                tailf:cli-drop-node-name;
                type string;
              }
              leaf goto {
                description
                  "goto label";
                type string;
              }
            }
            container info {
              description
                "Obtain system specific information";
              container type {
                description
                  "Type of information to obtain";
                tailf:cli-full-no;
                container snmp {
                  description
                    "SNMP information";
                  container var {
                    description
                      "Trap variable";
                    tailf:cli-compact-syntax;
                    tailf:cli-sequence-commands;
                    tailf:cli-reset-container;
                    leaf variable-name {
                      tailf:cli-drop-node-name;
                      tailf:cli-incomplete-command;
                      type string;
                    }
                    leaf oid {
                      description
                        "SNMP object id";
                      tailf:cli-incomplete-command;
                      type string;
                    }
                    leaf oid-type {
                      tailf:cli-drop-node-name;
                      tailf:cli-incomplete-command;
                      type enumeration {
                        enum "counter";
                        enum "gauge";
                        enum "int";
                        enum "ipv4";
                        enum "octet";
                        enum "string";
                        enum "uint";
                      }
                    }
                    leaf oid-type-value {
                      tailf:cli-drop-node-name;
                      type string;
                    }
                  }
                  container trap {
                    description
                      "SNMP trap";
                    tailf:cli-compact-syntax;
                    tailf:cli-sequence-commands;
                    tailf:cli-reset-container;
                    leaf enterprise-oid {
                      description
                        "Enterprise oid";
                      tailf:cli-incomplete-command;
                      type string;
                    }
                    leaf generic-trapnum {
                      description
                        "Generic trap number";
                      tailf:cli-incomplete-command;
                      type uint32;
                    }
                    leaf specific-trapnum {
                      description
                        "Specific trap number";
                      tailf:cli-incomplete-command;
                      type uint32;
                    }
                    leaf trap-oid {
                      description
                        "Trap oid";
                      tailf:cli-incomplete-command;
                      type string;
                    }
                    leaf trap-var {
                      description
                        "Trap variable";
                      type string;
                    }
                  }
                }
              }
            }
            leaf end {
              description
                "end conditional block";
              type empty;
            }
            container regexp {
              description
                "regular expression match";
              tailf:cli-compact-syntax;
              tailf:cli-sequence-commands;
              tailf:cli-reset-container;
              leaf string-pattern {
                tailf:cli-drop-node-name;
                tailf:cli-incomplete-command;
                type string;
              }
              leaf string-input {
                tailf:cli-drop-node-name;
                type string;
              }
              leaf string-match {
                tailf:cli-drop-node-name;
                type string;
              }
              leaf string-submatch1 {
                tailf:cli-drop-node-name;
                type string;
              }
              leaf string-submatch2 {
                tailf:cli-drop-node-name;
                type string;
              }
              leaf string-submatch3 {
                tailf:cli-drop-node-name;
                type string;
              }
            }
            container snmp-trap {
              description
                "Send an SNMP trap";
              tailf:cli-compact-syntax;
              tailf:cli-delete-when-empty;
              presence "true";
              leaf intdata1 {
                description
                  "SNMP integer data1";
                type int32;
              }
              leaf intdata2 {
                description
                  "SNMP integer data2";
                type int32;
              }
              leaf strdata {
                description
                  "SNMP trap string";
                type string;
              }
            }
            container string {
              description
                "string commands";
              leaf trim {
                description
                  "trim characters from both ends of string";
                type string;
              }
            }
            container syslog {
              description
                "Log a syslog message";
              tailf:cli-compact-syntax;
              leaf facility {
                description
                  "Facility string";
                type string;
              }
              leaf msg {
                description
                  "Syslog message";
                type string;
              }
              leaf priority {
                description
                  "Priority of syslog message";
                type logging-level-type;
              }
            }
          }
          leaf description {
            description
              "Add or modify an applet description";
            tailf:cli-full-command;
            tailf:cli-multi-value;
            type string;
          }
          // event manager applet * / trigger
          container trigger {
            description
              "Enter applet trigger configuration submode";
            tailf:cli-add-mode;
            tailf:cli-mode-name "config-applet-trigger";
          }
        }
      }
    }

    /// ========================================================================
    /// disable-eadi
    /// ========================================================================

    leaf disable-eadi {
      tailf:cli-full-command;
      type empty;
    }


    /// ========================================================================
    /// memory-size
    /// ========================================================================
    container memory-size {
      description
        "Adjust memory size by percentage";
      leaf iomem {
        description
          "I/O memory";
        type uint8 {
          range "5..25" {
            tailf:step "5";
          }
        }
      }
    }


    /// ========================================================================
    /// transceiver
    /// ========================================================================
    container transceiver {
      description
        "Select from transceiver configuration commands";
      container type {
        description
          "type keyword";
        container all {
          tailf:cli-add-mode;
          tailf:cli-mode-name "config-xcvr-type";
          tailf:cli-full-command;
          container monitoring {
            description
              "Enable/disable monitoring";
            presence "true";
            leaf interval {
              description
                "Set interval for monitoring";
              type uint16 {
                range "300..3600";
              }
            }
          }
        }
      }
    }



    /// ========================================================================
    /// onep
    /// ========================================================================
    container onep {
      description
        "ONEP functionality";
      tailf:cli-add-mode;
      tailf:cli-mode-name "config-onep";
      tailf:cli-full-command;
      container service {
        description
          "ONEP service set";
        leaf set {
          description
            "ONEP service set";
          type enumeration {
            enum "vty";
            enum "advancedrouting";
            enum "mediatrace";
            enum "onefw";
          }
        }
      }
      container tls {
        description
          "TLS transport";
        tailf:cli-add-mode;
        tailf:cli-mode-name "config-onep-tls";
        container trustpoint {
          description
            "Trustpoint configuration";
          leaf client-verification {
            description
              "Client trustpoint";
            type string;
          }
          leaf server-identity {
            description
              "Server trustpoint";
            type string;
          }
        }
      }
    }


  /// ========================================================================
  /// service-insertion
  /// ========================================================================
    container service-insertion {
      description
        "Service Insertion mode";
      leaf acg-reload-delay {
        description
          "Reload delay timer for ACG";
        type uint16 {
          range "120..450";
        }
      }
      list appnav-controller-group {
        description
          "AppNav Controller Group";
        tailf:cli-mode-name "config-service-insertion-acg";
        key "group-name";
        leaf group-name {
          type string;
        }
        leaf-list appnav-controller {
          description
            "AppNav controller";
          tailf:cli-list-syntax;
          type inet:ipv4-address;
        }
        leaf description {
          description
            "ACG description";
          type string;
        }
      }
      container service-context {
        description
          "Service Context";
        list waas {
          description
            "Service controller waas";
          tailf:cli-allow-join-with-key {
            tailf:cli-display-joined;
          }
          tailf:cli-mode-name "config-service-insertion-context";
          tailf:cli-suppress-key-abbreviation;
          key "name";
          leaf name {
            type string;
          }
          leaf appnav-controller-group {
            description
              "AppNav Controller Group";
            type string;
          }
          container authentication {
            description
              "Authentication key";
            tailf:cli-sequence-commands;
            tailf:cli-compact-syntax;
            leaf sha1 {
              description
                "Authentication type";
              type empty;
            }
            leaf key {
              description
                "Authentication Key";
              type empty;
            }
            leaf encrypt {
              tailf:cli-drop-node-name;
              tailf:cli-break-sequence-commands;
              type enumeration {
                enum "0";
                enum "7";
              }
            }
            leaf string {
              tailf:cli-drop-node-name;
              type string;
            }
          }
          leaf enable {
            description
              "service context enable";
            type empty;
          }
          leaf service-node-group {
            description
              "service node Group";
            type string;
          }
          leaf service-policy {
            description
              "Specify a service policy for the service context";
            type string;
          }
          container vrf {
            description
              "VRF";
            leaf default {
              description
                "default";
              type empty;
            }
            leaf global {
              description
                "global";
              type empty;
            }
            leaf name {
              description
                "vrf name";
              type string;
            }
          }
        }
      }
      list service-node-group {
        description
          "service node Group";
        tailf:cli-mode-name "config-service-insertion-sng";
        key "name";
        leaf name {
          type string;
        }
        leaf description {
          description
            "Group Description";
          type string;
        }
        leaf node-discovery {
          description
            "service node auto discovery";
          type enumeration {
            enum "enable";
          }
        }
        leaf-list service-node {
          description
            "service node";
          tailf:cli-list-syntax;
          type inet:ipv4-address;
        }
      }
      container swap {
        description
          "Swap src-ip";
        leaf src-ip {
          description
            "Swap source-ip of service-insertion packets";
          type empty;
        }
      }
    }


  /// ========================================================================
  /// udld
  /// ========================================================================
    container udld {
      description
        "Configure global UDLD setting";
      leaf aggressive {
        description
          "Enable UDLD protocol in aggressive mode on fiber ports exceptwhere locally configured";
        type empty;
      }
      leaf enable {
        description
          "Enable UDLD protocol on fiber ports except where locally configured";
        type empty;
      }
      container message {
        description
          "Set UDLD message parameters";
        leaf time {
          description
            "Set UDLD message time period";
          type uint8 {
            range "1..90";
          }
        }
      }
      container recovery {
        description
          "Enable timer to recover from udld error disable state";
        presence "true";
        leaf interval {
          description
            "timer-interval(sec)";
          type uint32 {
            range "30..86400";
          }
        }
      }
    }
/// ========================================================================
//                          Wireless
// ========================================================================
    //wireless
    container wireless {
      description 
        "Configure wireless parameters";
      leaf mdns-bridging {
        description 
          "Enable Ethernet mDNS Support";
        tailf:cli-boolean-no;
        type boolean;
      }
    }
    
    ///=====================================================
    /// qos
    ///=====================================================
    
    container qos {
      description "Global QoS configuration subcommands";
      presence true;
      container account {
        description "Additional lengths to be accounted by QoS Features";
        container layer-all  {
          description "All layers, including L1";
          leaf encapsulation {
            description "Account Layer 1 Encapsulation when applying QoS features";
            type empty;
          }
        }
        container layer2 {
          description "Accounting Layer 2 headers";
          container encapsulation {
            description "Account Layer 2 Encapsulation when applying QoS features";
            leaf arpa {
              description "ARPA Encapsulation Size (18 bytes)";
              type empty;
            }
            leaf dot1q {
              description "IEEE 802.1q Encapsulation Size (22 bytes)";
              type empty;
            }
            leaf isl {
              description "ISL Encapsulation Size (48 bytes)";
              type empty;
            }
            container length {
              description "Layer2 Encapsulation length in bytes";
              presence true;
              leaf byte-length {
                description "Layer2 Encapsulation length in bytes, <0-0>";
                tailf:cli-drop-node-name;
                type int8;
              }
            }
          }
        }
      }
      container control-packets {
        description "Enable QoS on control packets";
        presence true;
        leaf bpdu-range {
          description "Enable QoS on BPDU-range packets";
          type empty;
        }
        leaf cdp-vtp {
          description "Enable QoS on CDP and VTP packets";
          type empty;
        }
        leaf eapol {
          description "Enable QoS on EAPOL packets";
          type empty;
        }
        leaf lldp {
          description "Enable QoS on LLDP packets";
          type empty;
        }
        leaf protocol-tunnel {
          description "Enable QoS on protocol tunneled packets";
          type empty;
        }
        leaf sstp {
          description "Enable QoS on SSTP packets";
          type empty;
        }
      }        
      container preserve {
        description "Preserve packet header bits";
        container marking  {
          description "Preserve cos/tos header bits";
          leaf hipriority {
            description "Preserve marking in high priority generated control packets";
            type empty;
          }
        }
        container mpls {
          description "Preserve MPLS packet header bits";
          leaf exp {
            description "Preserve MPLS EXP packet header bits";
            type empty;
          }
        }
      }
      container trace {
        description "QoS trace log settings";
        container resize {
          description "resize trace log";
          leaf size {
            description "buffer size in bytes";
            tailf:cli-drop-node-name;
            type int32;                        
          }
          leaf all {
            description "all trace logs";
            type int32;
          }
          leaf error   {
            description "error trace log";
            type int32;
          }        
          leaf event {
            description "event trace log";
            type int32;                    
          }  
          leaf warning {
            description "warning trace log";
            type int32;
          }
        }
      }
      leaf diffservmib {
        description "RFC3289 support for QoS policy-maps";    
        type empty;
      }
    }

    ///=================================================
    /// device-tracking
    ///=============================================
    container device-tracking {
      description 
        "Device tracking configuration commands";
      list policy {
        tailf:cli-mode-name "config-device-tracking";
        description
          "Configure a policy for feature device-tracking";
        key "word";
        leaf word {
          type string;
        }
        container protocol {
          description 
            "Set the protocol to glean (default all)";
          leaf udp {
            tailf:cli-full-command;
            tailf:cli-boolean-no;
            type boolean;
          }    
        }
        container tracking {
          description 
            "Override default tracking behavior";
          leaf tracking-on-off {
            tailf:cli-drop-node-name;
            description
              "Tracking on or off";
            type enumeration {
              enum "enable";
              enum "disable";
            }   
          }
        }
        container limit {
          description 
            "Specifies a limit";
          leaf address-count {
            description 
              "Configure maximum address per port";
            type uint16 {
              range "1..32000";
            }  
          }
        }
        container security-level {
          description 
            "setup security level";
          leaf glean {
            description 
              "glean addresses passively";
            type empty;
          }
        }
      }
    }
    
    ///=======================
    /// time-range
    ///====================
    list time-range {
      tailf:cli-mode-name "config-time-range";
      description 
        "Define time range entries";
      key "word";
      leaf word {
        type string;
      }
      container absolute {
        description 
          "absolute time and date";
        container start {
          description 
            "starting time and date";
          tailf:cli-sequence-commands;
          tailf:cli-compact-syntax;
          leaf start-time{
            description 
              "Starting time";
            tailf:cli-drop-node-name;
            type string;
          }
          leaf day-of-month{
            description 
              "<1-31>  Day of the month";
            tailf:cli-drop-node-name;
            type uint8;
          }
          leaf month {
            description 
              "Month of the year [eg: Jan for January, Jun for June]";
            tailf:cli-drop-node-name;
            type string;
          }
          leaf year {
            description 
              "Year";
            tailf:cli-drop-node-name;
            type uint16 {
              range "1993..2035";
            }
          }
        }
      }
    }
    
    ///==================================
    /// fhrp
    ///==================================
    container fhrp {
      description 
        "Configure First Hop Redundancy Protocols";
      container version {
        description 
          "Configure which FHRP version is allowed to run";
        leaf vrrp {
          description 
            "Configure Virtual Router Rendundancy Protocol";
          type enumeration {
            enum "v2";
            enum "v3";
          }        
        }
      }
    }
    
    ///=================================
    /// metadata
    ///=================================
    container metadata { 
      description 
        "Metadata Application";
      container flow {
        description 
          "Enable Metadata Flow Handling";
        presence true;
        leaf transmit {
          description 
            "Enable Metadata Flow Transmit ";
          type empty;
        }
      }    
    }
    
    ///=================================
    /// profile
    ///=================================
    container profile {
      description
        "MSP Profile";
      leaf flow {
        description
          "MSP Profile Flow";
        type empty;
      }
    }
    
    ///=================================
    /// alias
    ///=================================
    container alias {
      description
        "Create command alias";
      container exec {
        description
          "Exec mode";
        tailf:cli-compact-syntax;
        tailf:cli-sequence-commands;
        leaf alias-name {
          tailf:cli-drop-node-name;
          type string;
        }
        leaf new-alias-name {
          tailf:cli-drop-node-name;
          tailf:cli-multi-value;
          type string;
        }
      }
    }
  }
/// ========================================================================
//                          EOF
// ========================================================================
}
